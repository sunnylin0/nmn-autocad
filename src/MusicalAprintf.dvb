Attribute VB_Name = "AbsoluteElement"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit




Public typs As String
''''''''''''''''增加
Public notes As iArray      'MusicNoteItem Array
    'mfingering As String  '指法
    'mnote As String           '高低音
    'mscale As String          '音階
 Public mtempo As String             '拍子
 Public duration As Double      '拍子的延遲長度
    'mtow_fingering As String  '指法 第二個
 Public slurStart As Boolean                '連音符
 Public slurEnd As Boolean                '連音符
 Public tripStart As Boolean           '3 連音開始
 Public tripEnd As Boolean             '3 連音結束
 Public mand As Boolean                  '記錄合音 true為跟後面一音合音 ,false為沒有
 Public what As Integer                 '記錄一些不一樣的指法
 
 
 Public mete As Integer     '拍號設定改變
 Public mete2 As Integer     '拍號設定改變
 Public barsperstaff  As Integer    '設定每行幾小節
  
 Public ln As Integer       '要記錄讀進來的資料是在文件裡的第幾 "行"
 Public WD As Integer      '要記錄貢進來的資料是在文件要的第幾 "字"
 
''''''''''''''''增加

Public x As Double
Public y As Double
Public w As Double     '正位的寬度

Public extce As Double '這是前置的位置
Public children As RelativeElementList
Public heads As RelativeElementList
Public abcelem As VoiceABC
Public tuneNumber As Integer
Public durationClass As Double

Public minspacing As Double
Public extra As RelativeElementList
Public extraw As Double    '前綴元素的寬度 是負值
Public right As RelativeElementList
Public invisible As Boolean
Public bottom As Double
Public top As Double
Public fixed  As vFixedCoords  ' FixedCoords
Public specialY As Dictionary  'SpecialYProperties
Public elemset As iArray  'SVGElement[]
'    counters as  {
'        line as  number
'        measure as  number
'        measureTotal as  number
'        voice as  number
'        note as  number
'    }
Public notePositions As New PointList
Public isClef As Boolean
Public isKeySig As Boolean
Public Beam As BeamElem
Public startChar As Double
Public endChar As Double

Public hint As Boolean
Public startTie As Boolean
Public klass As String


 
Public Sub init(abcelem As VoiceABC, duration As Double, minspacing As Double, typs As String, tuneNumber As Integer, Optional options1 As Dictionary = Nothing)

    ''  console.log("Absolute:",abcelem, duration, minspacing, type, tuneNumber, options)
    If (options1 Is Nothing) Then
        Set options1 = New Dictionary
    End If
    Me.tuneNumber = tuneNumber
    Set Me.abcelem = abcelem
    Me.duration = duration
    If options1("durationClassOveride") <> 0 Then
        Me.durationClass = options1("durationClassOveride")
    Else
        Me.durationClass = Me.duration
    End If
    Me.minspacing = minspacing
    Me.x = 0
    Set Me.children = New RelativeElementList
    Set Me.heads = New RelativeElementList
    Set Me.extra = New RelativeElementList
    Me.extraw = 0
    Me.w = 0
    Set Me.right = New RelativeElementList
    Me.invisible = False
    'Me.bottom = undefined
    'Me.top = undefined
    Me.typs = typs

    '' The following are the dimensions of the fixed part of the element.
    '' That is, the chord text will be a different height depending on lot of factors, but the 8th flag will always be in the same place.
    Set Me.fixed = New vFixedCoords ' { w: 0, t: undefined, b: undefined }  '' there is no x-coord here, because that is set later.

    '' these are the heights of all of the vertical elements that can't be placed until the end of the line.
    '' the vertical order of elements that are above is: tempo, part, volume/dynamic, ending/chord, lyric
    '' the vertical order of elements that are below is: lyric, chord, volume/dynamic
        Dim spY As Dictionary
        Set spY = New Dictionary
        
        spY("tempoHeightAbove") = 0
        spY("partHeightAbove") = 0
        spY("volumeHeightAbove") = 0
        spY("dynamicHeightAbove") = 0
        spY("endingHeightAbove") = 0
        spY("chordHeightAbove") = 0
        spY("lyricHeightAbove") = 0
        spY("lyricHeightBelow") = 0
        spY("chordHeightBelow") = 0
        spY("volumeHeightBelow") = 0
        spY("dynamicHeightBelow") = 0
        Set Me.specialY = spY
    

End Sub

Public Function getFixedCoords() As vFixedCoords
    Set getFixedCoords = vFixedCoords
    getFixedCoords.x = Me.x
    getFixedCoords.w = Me.fixed.w
    getFixedCoords.t = Me.fixed.t
    getFixedCoords.B = Me.fixed.B
    
End Function

Public Sub addExtra(extra As RelativeElement)
    '' used for accidentals, multi-measure rest text,
    '' left-side decorations, gracenote heads,
    '' left annotations, gracenote stems.


    Me.fixed.w = Math.max(Me.fixed.w, extra.dx + extra.w)

    Me.fixed.t = Math.max(Me.fixed.t, extra.top)
    
    Me.fixed.B = Math.min(Me.fixed.B, extra.bottom)
    If (extra.dx < Me.extraw) Then Me.extraw = extra.dx
    Me.extra(Me.extra.Count) = extra
    Me.addChild_ extra
End Sub

Public Sub addHead(head As RelativeElement)

    If (head.dx < Me.extraw) Then Me.extraw = head.dx
    Me.heads.Push head
    Me.addRight head
End Sub

Public Sub addRight(right As RelativeElement)


    '' These are the elements that are the fixed part.
    
    Me.fixed.w = Math.max(Me.fixed.w, right.dx + right.w)
    Me.fixed.t = Math.max(Me.fixed.t, right.top)
    Me.fixed.B = Math.min(Me.fixed.B, right.bottom)
    
    '' if (isNaN(me.fixed.t) || isNaN(me.fixed.b))
    ''  debugger
    If (right.dx + right.w > Me.w) Then Me.w = right.dx + right.w
    Me.right.Push right
    Me.addChild_ right

End Sub

Public Sub addFixed(elem As RelativeElement)
    '' used for elements that can't move relative to other elements after they have been placed.
    '' used for ledger lines, bar numbers, debug msgs, clef, key sigs, time sigs
    Me.addChild_ elem

End Sub

Public Sub addFixedX(elem As RelativeElement)
    '' used for elements that can't move horizontally relative to other elements after they have been placed.
    '' used for parts, tempo, decorations
    Me.addChild_ elem

End Sub

Public Sub addCentered(elem As RelativeElement)
    Dim half As Double
    half = elem.w / 2
    If (-half < Me.extraw) Then Me.extraw = -half
    Set Me.extra(Me.extra.Count) = elem
    If (elem.dx + half > Me.w) Then Me.w = elem.dx + half
    Set Me.right(Me.right.Count) = elem
    Me.addChild_ (elem)
End Sub

'Public Sub setLimit(member, child)
'
'
'    if (!child[member]) return
'    if (!me.specialY[member])
'        me.specialY[member] = child[member]
'    Else
'        me.specialY[member] = Math.max(me.specialY[member], child[member])
'End Sub

Public Sub addChild_(child As RelativeElement)
    ''  console.log("Relative:",child)
    Set child.parent = Me
    Me.children.Push child
    Me.pushTop child.top
    Me.pushBottom child.bottom
'    Me.setLimit "tempoHeightAbove", child
'    Me.setLimit "partHeightAbove", child
'    Me.setLimit "volumeHeightAbove", child
'    Me.setLimit "dynamicHeightAbove", child
'    Me.setLimit "endingHeightAbove", child
'    Me.setLimit "chordHeightAbove", child
'    Me.setLimit "lyricHeightAbove", child
'    Me.setLimit "lyricHeightBelow", child
'    Me.setLimit "chordHeightBelow", child
'    Me.setLimit "volumeHeightBelow", child
'    Me.setLimit "dynamicHeightBelow", child
End Sub

Public Sub pushTop(top As Double)

            Me.top = Math.max(top, Me.top)

End Sub
Public Sub pushBottom(bottom As Double)
            Me.bottom = Math.min(Array(bottom, Me.bottom))
End Sub


Public Sub setX(x As Double)
    Dim i As Integer
    Me.x = x
    For i = 0 To Me.children.Length - 1
        Me.children(i).setX (x)
    Next i
End Sub

Public Sub center(before As AbsoluteElement, after As AbsoluteElement)
    '' Used to center whole rests
    Dim Midpoint As Double
    Midpoint = (after.x - before.x) / 2 + before.x
    Me.x = Midpoint - Me.w / 2
    Dim k As Integer
    For k = 0 To Me.children.Length - 1
        Me.children(k).setX (Me.x)
    Next
End Sub

Public Sub setHint()
    Me.hint = True
End Sub

Public Sub highlight(klass, color)
    'highlight.bind(this)(klass, color)
End Sub

Public Sub unhighlight(klass, color)
    'unhighlight.bind(this)(klass, color)
End Sub

Public Function clone() As AbsoluteElement
    Dim cope As New AbsoluteElement
    cope.typs = Me.typs
    cope.duration = Me.duration
    cope.x = Me.x
    cope.y = Me.y
    cope.w = Me.w
Set cope.children = Me.children
Set cope.heads = Me.heads
Set cope.abcelem = Me.abcelem
    cope.tuneNumber = Me.tuneNumber
    cope.durationClass = Me.durationClass
    
    cope.minspacing = Me.minspacing
Set cope.extra = Me.extra
    cope.extraw = Me.extraw
Set cope.right = Me.right
    cope.invisible = Me.invisible
    cope.bottom = Me.bottom
    cope.top = Me.top
Set cope.fixed = Me.fixed
Set cope.specialY = Me.specialY
Set cope.elemset = Me.elemset

Set cope.notePositions = Me.notePositions
    cope.isClef = Me.isClef
    cope.isKeySig = Me.isKeySig
Set cope.Beam = Me.Beam
    cope.startChar = Me.startChar
    cope.endChar = Me.endChar
    
    cope.hint = Me.hint
    cope.startTie = Me.startTie
    cope.klass = Me.klass
    
    Set clone = cope
    
End Function

Attribute VB_Name = "AbsoluteElementList"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
'MIT License
'
'Copyright (c) 2019-2021 Petr Katerinak
'
'Permission is hereby granted, free of charge, to any person obtaining a copy
'of this software and associated documentation files (the "Software"), to deal
'in the Software without restriction, including without limitation the rights
'to use, copy, modify, merge, publish, distribute, sublicense, and/or sell
'copies of the Software, and to permit persons to whom the Software is
'furnished to do so, subject to the following conditions:
'
'The above copyright notice and this permission notice shall be included in all
'copies or substantial portions of the Software.
'
'THE SOFTWARE IS PROVIDED "AS IS", WITHOUT WARRANTY OF ANY KIND, EXPRESS OR
'IMPLIED, INCLUDING BUT NOT LIMITED TO THE WARRANTIES OF MERCHANTABILITY,
'FITNESS FOR A PARTICULAR PURPOSE AND NONINFRINGEMENT. IN NO EVENT SHALL THE
'AUTHORS OR COPYRIGHT HOLDERS BE LIABLE FOR ANY CLAIM, DAMAGES OR OTHER
'LIABILITY, WHETHER IN AN ACTION OF CONTRACT, TORT OR OTHERWISE, ARISING FROM,
'OUT OF OR IN CONNECTION WITH THE SOFTWARE OR THE USE OR OTHER DEALINGS IN THE
'SOFTWARE.
'
' Version of iArray: 1.0
''修正 元素從 0 開始

Private mainArray As New Collection
Private i As Long ' Counter

' #####################
' #    CONSTRUCTOR    #
' #####################
'Private Sub Class_Initialize()
'  Set mainArray = New Collection
'End Sub

' #####################
' #  Getter / Setter  #
' #####################
'Attribute Element.VB_UserMemId = 0 saved in both procedures

'@DefaultMember
Public Property Get element(ByVal index As Long) As AbsoluteElement
Attribute element.VB_UserMemId = 0
    If index + 1 < 1 Or index + 1 > mainArray.Count Then
        Set element = Nothing
        Exit Property
    End If
    If IsObject(mainArray(index + 1)) = True Then
        Set element = mainArray(index + 1)
    Else
        element = mainArray(index + 1)
    End If

 
End Property

'@DefaultMember
Public Property Let element(ByVal index As Long, ByVal val As AbsoluteElement)
Attribute element.VB_UserMemId = 0
  If index = 0 And mainArray.Count = 0 Then
    Me.Push val
    Exit Property
  End If
  ElseIf index + 1 > mainArray.Count Then
    Dim eMsg As String
    eMsg = IIf(mainArray.Count > 0, _
               "Index (" & index + 1 & ") out of iArray bounds (1-" & mainArray.Count & ")", _
               "iArray doesn't have any indexes")
    err.Raise Number:=9, Description:=eMsg
    Exit Property
  End If
  mainArray.Add val, after:=index + 1
  mainArray.Remove index + 1
End Property

' #############################
' # COMMON COLLECTION METHODS #
' #############################
Public Function Count() As Long
  Count = mainArray.Count
End Function
Public Sub Add(ByVal val As AbsoluteElement, Optional ByVal bef As Variant = Empty, Optional ByVal aft As Variant = Empty)
  If IsEmpty(bef) And IsEmpty(aft) Then
    mainArray.Add val
  ElseIf IsEmpty(bef) Then
    mainArray.Add val, , , aft
  ElseIf IsEmpty(aft) Then
    mainArray.Add val, , bef
  Else
    mainArray.Add val, , bef, aft
  End If
End Sub
Public Sub Remove(index As Long)
  mainArray.Remove index + 1
End Sub

' ####################
' #  PUBLIC METHODS  #
' ####################

'AddAfter
' Adds element after given index.
' {1,2,3} -> index >= 3 -> Push val
' {1,2,3} -> index < 1 -> Unshift val
' {} -> index = any -> Push val
' @param Long index | Index after which will be added an element
' @param Variant val | One element (String, number, ...) to add into iArray
' @return Long | Count of elements inside iArray
Public Function AddAfter(ByVal index As Long, ByVal val As AbsoluteElement) As Long
  If Me.Count < 1 Or index + 1 >= Me.Count Then
    Me.Push val
  ElseIf index + 1 < 1 Then
    Me.Unshift val
  Else
    Me.Add val, aft:=index + 1
  End If
  AddAfter = Me.Count
End Function

'AddArrayAfter
' Adds elements after given index.
' {1,2,3} -> index >= 3 -> PushArray val
' {1,2,3} -> index < 1 -> UnshiftArray val
' {} -> index = any -> PushArray val
' @param Long index | Index after which will be added an element
' @param Variant val | Array() or iArray of elements to add into iArray
' @return Long | Count of elements inside iArray
Public Function AddArrayAfter(ByVal index As Long, ByVal val As Variant) As Long
  If Me.Count < 1 Or index + 1 >= Me.Count Then
    Me.PushArray val
  ElseIf index + 1 < 1 Then
    Me.UnshiftArray val
  Else
    If TypeOf val Is AbsoluteElementList Then
      For i = 0 To val.Count - 1
        Me.Add val(i), aft:=index + 1
        Inc index
      Next i
    Else
      For i = LBound(val) To UBound(val)
        Me.Add val(i), aft:=index + 1
        Inc index
      Next i
    End If
  End If
  AddArrayAfter = Me.Count
End Function

'AddArrayBefore
' Adds elements before given index.
' {1,2,3} -> index > 3 -> PushArray val
' {1,2,3} -> index <= 1 -> UnshiftArray val
' {} -> index = any -> PushArray val
' @param Long index | Index after which will be added an element
' @param Variant val | Array() or iArray of elements to add into iArray
' @return Long | Count of elements inside iArray
Public Function AddArrayBefore(ByVal index As Long, ByVal val As Variant) As Long
  If Me.Count < 1 Or index + 1 > Me.Count Then
    Me.PushArray val
  ElseIf index <= 0 Then
    Me.UnshiftArray val
  Else
    If TypeOf val Is AbsoluteElementList Then
      For i = val.Count - 1 To 0 Step -1
        Me.Add val(i), bef:=index + 1
      Next i
    Else
      For i = UBound(val) To LBound(val) Step -1
        Me.Add val(i), bef:=index + 1
      Next i
    End If
  End If
  AddArrayBefore = Me.Count
End Function

'AddBefore
' Adds element before given index.
' {1,2,3} -> index > 3 -> Push val
' {1,2,3} -> index <= 1 -> Unshift val
' {} -> index = any -> Push val
' @param Long index | Index before which will be added an element
' @param Variant val | One element (String, number, ...) to add into iArray
' @return Long | Count of elements inside iArray
Public Function AddBefore(ByVal index As Long, ByVal val As AbsoluteElement) As Long
  If Me.Count < 1 Or index + 1 > Me.Count Then
    Me.Push val
  ElseIf index + 1 <= 1 Then
    Me.Unshift val
  Else
    Me.Add val, bef:=index + 1
  End If
  AddBefore = Me.Count
End Function

'Avg
' Calculates the average of the numeric mainArray.
' @return Variant | Average value / "NaN" if iArray contains non-numeric value(s)
Public Function Avg() As Variant
  If Not Me.ContainsOnlyNumeric Then Avg = "NaN": Exit Function
  Avg = Me.sum / Me.Count
End Function

'Clear
' Empties iArray
Public Function Clear() As Boolean
  For i = mainArray.Count - 1 To 0 Step -1
    mainArray.Remove i + 1
  Next i
  Clear = IIf(mainArray.Count = 0, True, False)
End Function

'Clone
' Makes a hard copy of the mainArray
' @return mainArray | Return exact copy of itself
Public Function clone() As AbsoluteElementList
  Set clone = New AbsoluteElementList
  For i = 0 To Me.Count - 1
    clone.Push Me(i)
  Next i
End Function

'Contains
' Checks if given value is used inside mainArray.
' @param Variant val | One element (String, number, ...) to by checked if it exists in iArray
' $return Boolean | True = exists, False = doesn't exists
Public Function Contains(ByVal val As AbsoluteElement) As Boolean
  Contains = False
  Dim el As Variant
  For Each el In mainArray
    If IsObject(val) = True Or VarType(val) And 8192 Then
        If (VarType(el) And 8192) And (VarType(val) And 8192) Then
            If ArrayDifference(el, val) Then
                Contains = True: Exit Function
            End If
        ElseIf IsObject(el) = True And IsObject(val) = True Then
            If el Is val Then
                Contains = True: Exit Function
            End If
        End If
    Else
        If IsObject(el) = False And (VarType(el) And 8192) <> 8192 Then
            If el = val Then
            Contains = True: Exit Function
            End If
        End If
    End If
  Next el
End Function

'ContainsAll
' Checks if all given values are used inside mainArray.
' @param Variant val | values to by checked if it exists in iArray
' $return Boolean | True = all exists, False = one ore more values doesn't exists
Public Function ContainsAll(ByVal val As AbsoluteElementList) As Boolean
  ContainsAll = False
  Dim foundOccurrences As Integer: foundOccurrences = 0
  Dim values As New AbsoluteElementList
  If Not TypeOf val Is AbsoluteElementList Then
    If IsArray(val) Then
      values.PushArray (val)
    Else
      values.Push (val)
    End If
  Else
    Set values = val
  End If
  For i = 0 To values.Count - 1
    If Me.Contains(values(i)) Then Inc foundOccurrences
  Next i
  If foundOccurrences = values.Count Then ContainsAll = True
End Function

'CountOccurrences
' Checks how many times is given value used inside mainArray.
' @param Variant val | One element (String, number, ...) to by checked
' @return Long | Count of matched occurrences
Public Function CountOccurrences(val As Variant) As Long
  CountOccurrences = 0
  Dim el As Variant
  For Each el In mainArray
  
    If IsObject(val) = True Or VarType(val) And 8192 Then
        If VarType(el) And 8192 And VarType(val) And 8192 Then
            If ArrayDifference(el, val) Then
                Inc CountOccurrences
                Exit Function
            End If
        ElseIf IsObject(el) = True And IsObject(val) = True Then
            If el Is val Then
                Inc CountOccurrences
                Exit Function
            End If
        End If
    Else
        If IsObject(el) = False And Not (VarType(el) And 8192) Then
            If el = val Then
                Inc CountOccurrences
                Exit Function
            End If
        End If
    End If
  
     'If el = val Then Inc CountOccurrences
  Next el
End Function

'Dequeue
' Removes an element from the begining of the mainArray.
' @return Variant | Removed element or Empty, if iArray is empty
'刪除開頭一個元素。
Public Function Dequeue() As AbsoluteElement
  Dequeue = Empty
  If mainArray.Count > 0 Then
    If VarType(Me(0)) = vbString Then
        Dequeue = Me(0)
    ElseIf TypeOf Me(0) Is AbsoluteElementList Then
        Set Dequeue = Me(0)
    ElseIf VarType(Me(0)) = vbArray Then
        Set Dequeue = Me(0)
    ElseIf VarType(Me(0)) = vbObject Then
        Set Dequeue = Me(0)
    Else
        Dequeue = Me(0)
    End If
    
    mainArray.Remove 1
  End If
End Function

'Difference
' Checks for number of differences between two arrays, what was added/deleted or combination.
' @param iArray oldArray | Old iArray to be compared with current iArray
' @param String retType | �dd= deleted from old iArray, �aa= added in current iArray, �cc= combination of both (default)
' @return iArray | iArray with differences found
Public Function Difference(ByRef oldArray As AbsoluteElementList, Optional ByVal retType As String = "c") As AbsoluteElementList
  Set Difference = New AbsoluteElementList
  Select Case LCase(retType)
    Case "d"
      For i = 0 To oldArray.Count - 1
        If Me.Contains(oldArray(i)) = False Then Difference.Push oldArray(i)
      Next i
    Case "a"
      For i = 0 To Count - 1
        If oldArray.Contains(Me(i)) = False Then Difference.Push Me(i)
      Next i
    Case "c"
      For i = 0 To oldArray.Count - 1
        If Me.Contains(oldArray(i)) = False Then Difference.Push oldArray(i)
      Next i
      For i = 0 To Count - 1
        If oldArray.Contains(Me(i)) = False Then Difference.Push Me(i)
      Next i
    Case Else
      err.Raise Number:=5, Description:="Unknown Difference return type attribute:" & vbCrLf & _
                                        "Allowed are 'A'dded/'D'eleted/'C'ombination of both"
  End Select
End Function

'DropLeft
' Remove n elements from the beginning of the mainArray. If n > count of iArray elements, all elements are removed.
' @param Long n | Number of elements to be removed
' @return iArray | Array of the removed elements
Public Function DropLeft(ByRef N As Long) As AbsoluteElementList
  Set DropLeft = New AbsoluteElementList
  If N > Me.Count Then N = Me.Count
  For i = 0 To N - 1
    DropLeft.Push Me(i)
  Next i
  For i = N - 1 To 0 Step -1
    Me.Remove (i)
  Next i
End Function

'DropRight
' Remove n elements from the end of the mainArray. If n > count of iArray elements, all elements are removed.
' @param Long n | Number of elements to be removed
' @return iArray | Array of the removed elements
Public Function DropRight(ByRef N As Long) As AbsoluteElementList
  Set DropRight = New AbsoluteElementList
  If N > Me.Count Then N = Me.Count
  For i = Me.Count - N To Me.Count - 1
    DropRight.Push Me(i)
  Next i
  For i = Me.Count - 1 To Me.Count - N Step -1
    Me.Remove (i)
  Next i
End Function

'Enqueue
' Adds an element at the end of the mainArray.
' @param Variant val | One element (String, number, ...) to add into iArray
' @return Long | Count of elements inside iArray
Public Function Enqueue(ByVal val As Variant) As Long
  Enqueue = Push(val)
End Function

'EnqueueArray
' Adds elements at the end of the iArray
' @param Variant val | Array() or iArray of elements to add into iArray
' @return Long | Count of elements inside array
Public Function EnqueueArray(ByVal val As Variant) As Long
  EnqueueArray = PushArray(val)
End Function

'First
' Returns value of the first element of the mainArray.
' @return Variant | Value of the first element or Empty if iArray is Empty
Public Function First() As AbsoluteElement
  Set First = IIf(Me.Count > 0, Me(0), Empty)
End Function

'Head
' Returns all elements of iArray, except last one.
' @return iArray | Copy of original array, without last element
Public Function head() As AbsoluteElementList
  Set head = Me.clone
  head.Pop
End Function

'Intersect
' Search for element that exists in both iArrays.
' @param iArray intArray | iArray to be intersected with current iArray
' @return iArray | Intersected values
Public Function Intersect(ByRef intersectedArr As AbsoluteElementList) As AbsoluteElementList
  Set Intersect = New AbsoluteElementList
  Dim el As Variant
  For Each el In mainArray
    If intersectedArr.Contains(el) Then
      If Not Intersect.Contains(el) Then Intersect.Push (el)
    End If
  Next el
End Function

'ContainsOnlyNumeric
' Verify that all elements are numbers or convertable to numbers
' $return Boolean | True = contains only numeric values, False = contains inconvertible values
Public Function ContainsOnlyNumeric() As Boolean
  ContainsOnlyNumeric = True
  Dim el As Variant
  For Each el In mainArray
    If Not IsNumeric(el) Then ContainsOnlyNumeric = False: Exit Function
  Next el
End Function

'Join
' Joins two iArrays.
' @param iArray jArray | iArray to be joined with current iArray
' @return iArray | Joined iArray
Public Function Join(ByRef joinArr As AbsoluteElementList) As AbsoluteElementList
  Set Join = New AbsoluteElementList
  Join.PushArray Me
  Join.PushArray joinArr
End Function

'Last
' Returns value of the last element of the mainArray.
' @return Variant | Value of the last element or Empty if iArray is Empty
Public Function Last() As AbsoluteElement
  Set Last = IIf(Me.Count > 0, Me(Me.Count - 1), Empty)
End Function

'OccurrenceIndexes
' Returns all indexes of a value in mainArray.
' @return iArray | iArray containing indexes of occurrence
Public Function OccurenceIndexes(val As Variant) As AbsoluteElementList
  Set OccurenceIndexes = New AbsoluteElementList
  For i = 0 To Me.Count - 1
    If Me(i) = val Then
        OccurenceIndexes.Push (i)
    End If
  Next i
End Function

'Pop
' Removes an element from the end of the mainArray.
' @return Variant | Removed element or Empty, if iArray is empty
Public Function Pop() As AbsoluteElement
  If mainArray.Count > 0 Then
    If VarType(Me(mainArray.Count - 1)) = vbObject Then
       Set Pop = Me(mainArray.Count - 1)
    Else
        Pop = Me(mainArray.Count - 1)
    End If
    mainArray.Remove mainArray.Count
  End If
End Function
  
  

'Push
' Adds an element at the end of the mainArray.
' @param Variant val | One element (String, number, ...) to add into iArray
' @return Long | Count of elements inside iArray
Public Function Push(ByVal val As AbsoluteElement) As Long
  mainArray.Add val
  Push = mainArray.Count
End Function

'PushArray
' Adds elements at the end of the mainArray.
' @param Variant val | Array() or iArray of elements to add into iArray
' @return Long | Count of elements inside array
Public Function PushArray(ByVal val As Variant) As Long
  If TypeOf val Is AbsoluteElementList Then
    For i = 0 To val.Count - 1
      Me.Push val(i)
    Next i
  Else
    For i = LBound(val) To UBound(val)
      Me.Push val(i)
    Next i
  End If
  PushArray = Me.Count
End Function

'RemoveDuplicates
' Keeps only the first occurrence of the value. Affects original array
' @return Long | Count of the removed elements
Public Function RemoveDuplicates() As Long
  RemoveDuplicates = 0
  For i = Me.Count - 1 To 0 Step -1
    If Me.CountOccurrences(Me(i)) > 1 Then
      Me.Remove i
      Inc RemoveDuplicates
    End If
  Next i
End Function

'Reverse
' Reverses the content of the iArray
' @return iArray | Reversed iArray
Public Function Reverse() As AbsoluteElementList
  Set Reverse = New AbsoluteElementList
  For i = 0 To Me.Count - 1
    Reverse.Unshift Me(i)
  Next i
End Function

'Shift
' Removes an element from the begining of the mainArray.
' @return Variant | Removed element or Empty, if iArray is empty
'轉移
' 從 iArray 的開頭刪除一個元素。
' @返回第一個元素 | 如果 iArray 為空，則刪除元素或為空
Public Function shift() As AbsoluteElement
  shift = Empty
  If mainArray.Count > 0 Then
    If VarType(Me(0)) = vbString Then
        shift = Me(0)
    ElseIf TypeOf Me(0) Is AbsoluteElementList Then
        Set shift = Me(0)
    ElseIf VarType(Me(0)) = vbArray Then
        Set shift = Me(0)
    ElseIf VarType(Me(0)) = vbObject Then
        Set shift = Me(0)
    Else
        shift = Me(0)
    End If
    
    mainArray.Remove 1
  End If
End Function

'Shuffle
' Randomly mixes content of the iArray
' @return iArray | Shuffled iArray
' 隨機播放
' 隨機混合 iArray 的內容
'@return iArray | 打亂iArray
Public Function Shuffle() As AbsoluteElementList
  Set Shuffle = New AbsoluteElementList
  Dim keys As New AbsoluteElementList
  For i = 0 To Me.Count - 1
    keys.Push (i)
  Next i
  Dim rndNo As Long
  Do While keys.Count > 0
    rndNo = randomFromTo(0, keys.Count - 1)
    Shuffle.Push Me(keys(rndNo))
    keys.Remove (rndNo)
  Loop
End Function

'Sum
' Calculates the sum of the numeric mainArray.
' @return Variant | Sum value / "NaN" if iArray contains non-numeric value(s)
Public Function sum() As Variant
  If Not Me.ContainsOnlyNumeric Then sum = "NaN": Exit Function
  sum = 0
  Dim el As Variant
  For Each el In mainArray
    sum = sum + el
  Next el
End Function

'Tail
' Returns all elements of iArray, except first one.
' @return iArray | Copy of original array, without first element
'返回陣列中除了第一個元素的剩余元素陣列
Public Function Tail() As AbsoluteElementList
  Set Tail = Me.clone
  Tail.Dequeue
End Function

Public Function ToList()
  If Me.Count = 0 Then ToList = Null: Exit Function
  Dim tarr()
  ReDim tarr(Me.Count - 1)
  For i = 0 To Me.Count - 1
    If VarType(Me(i)) = vbString Then
        tarr(i) = Me(i)
    ElseIf TypeOf Me(i) Is AbsoluteElementList Then
        Set tarr(i) = Me(i)
    ElseIf VarType(Me(i)) = vbObject Then
        Set tarr(i) = Me(i)
    Else
        tarr(i) = Me(i)
    End If
  Next i
  ToList = tarr
End Function

'ToString
' Creates string representation of the mainArray.
' @param String delimiter | Optional character to separate the iArray's elements (default = " ")
' @return String | Formated representation of tha iArray
Public Function ToString(Optional ByVal delimiter As String = " ") As String
  If Me.Count = 0 Then ToString = "{}": Exit Function
  ToString = vbNullString
  For i = 0 To Me.Count - 1
    If i = 0 Then ToString = ToString + "{"
    If i > 0 Then ToString = ToString + delimiter
    If VarType(Me(i)) = vbString Then
        ToString = ToString + Chr$(34)
        ToString = ToString + CStr(Me(i))
        ToString = ToString + Chr$(34)
    ElseIf TypeOf Me(i) Is AbsoluteElementList Then
        ToString = ToString + Me(i).ToString(delimiter)
    ElseIf (VarType(Me(i)) And vbArray) = vbArray Then
        ToString = ToString + "[Array]"
    ElseIf VarType(Me(i)) = vbObject Then
        ToString = ToString + "[Object]"
    Else
        ToString = ToString + CStr(Me(i))
    End If
    
    If i = mainArray.Count - 1 Then ToString = ToString + "}"
  Next i
End Function

'Union
' Combines both iArrays and removes duplicities
' @param iArray uArray | iArray to be unioned with current iArray
' @return iArray | Combined values without duplicities
Public Function Union(ByRef uArr As AbsoluteElementList) As AbsoluteElementList
  Set Union = Me.clone
  Union.PushArray uArr
  Union.RemoveDuplicates
End Function

'Unique
' Returns copy of iArray without duplicated values. Original array is not affected
' @return iArray | iArray with unique values
Public Function Unique() As AbsoluteElementList
  Set Unique = New AbsoluteElementList
  Dim el As Variant
  For Each el In mainArray
    If Not Unique.Contains(el) Then Unique.Push (el)
  Next el
End Function

'Unshift
' Add an element at the begining of the mainArray.
' @param Variant val | One element (String, number, ...) to add into iArray
' @return Long | Count of elements inside iArray
Public Function Unshift(ByVal val As Variant) As Long
  If mainArray.Count = 0 Then
    Unshift = Push(val)
  Else
    mainArray.Add val, before:=1
    Unshift = mainArray.Count
  End If
End Function

'UnshiftArray
' Add elements at the begining of the mainArray.
' @param Variant val | Array() or iArray of elements to add into iArray
' @return Long | Count of elements inside iArray
Public Function UnshiftArray(ByVal val As Variant) As Long
  If TypeOf val Is AbsoluteElementList Then
    For i = val.Count - 1 To 0 Step -1
      Unshift val(i)
    Next i
  Else
    For i = UBound(val) To LBound(val) Step -1
      Unshift val(i)
    Next i
  End If
  UnshiftArray = mainArray.Count
End Function


' #####################
' # PRIVATE FUNCTIONS #
' #####################
Sub Inc(ByRef i)
   i = i + 1
End Sub

'Private Function rangeToArray(ByVal rng As Range) As Variant
'  rangeToArray = rng.Value
'End Function

Private Function randomFromTo(ByVal from As Long, ByVal upTo As Long) As Long
  Randomize
  randomFromTo = Int(from + Rnd() * (upTo - from + 1))
End Function

'比對 兩個陣列是否一樣
Private Function ArrayDifference(arr1 As Variant, arr2 As Variant) As Boolean

    Dim i As Integer
    If UBound(arr1) = UBound(arr2) Then
        For i = 0 To UBound(arr1)
            If arr1(i) = arr2(i) Then
                ArrayDifference = True
            Else
                ArrayDifference = False
                Exit Function
            End If
        Next
    Else
        ArrayDifference = False
    End If

End Function

'@Description("changes the contents of the array by removing or replacing existing elements and/or adding new elements in place.")
Public Function Splice( _
        ByVal StartIndex As Long, _
        ParamArray Args() As Variant _
    ) As Variant()
    'Dim LocalItems() As Variant
    Dim ActualStart As Long
    Dim ActualDeleteCount As Long
    Dim ArgsCount As Long
    Dim LocalLength As Long
    Dim LocalArgs() As Variant
    Dim result() As Variant
    Dim i As Long
    Dim TempArray() As Variant
    Dim ItemCount As Long
    Dim TempItems() As Variant
    
    LocalArgs = Args
    'LocalItems = mainArray
    LocalLength = Me.Count
    If StartIndex < LocalLength Then
        ActualStart = StartIndex
    Else
        ActualStart = min(StartIndex, LocalLength)
    End If
    
    ArgsCount = UBound(LocalArgs) + 1
    If ArgsCount = 0 Then
        ' only a start index has been supplied
        ' we're gonna delete everything
        ' 僅提供了起始索引
         '我們要刪除所有內容
        ItemCount = 0
        ActualDeleteCount = LocalLength - ActualStart
    Else
        ' first arg in args is delete count, second onwards are insertion items
        ' args 中的第一個參數是刪除計數，第二個之後是插入項
        ItemCount = ArgsCount - 1
        'deleteCount is first element in args.
        'deleteCount 是 args 中的第一個元素。
        ActualDeleteCount = min(max(Args(LBound(Args)), 0), LocalLength - ActualStart)
    End If
    

    ' get items to be deleted for return val
    ' 取得和刪除
    If ActualDeleteCount > 0 Then
        ReDim result(0 To ActualDeleteCount - 1)
        i = 0
        Do While i < ActualDeleteCount
            If IsObject(Me(ActualStart)) Then
                Set result(i) = Me(ActualStart)
                Me.Remove ActualStart
            Else
                result(i) = Me(ActualStart)
                Me.Remove ActualStart
            End If
            Inc i
        Loop
    Else
        ' return empty array if nothing to be deleted
        ReDim result(0)
    End If
    
    '取得要插入的陣列資料
    If ItemCount > 0 Then
        ReDim TempItems(0 To ItemCount - 1)
        For i = 0 To ItemCount - 1
            If IsObject(LocalArgs(i + 1)) Then
                Set TempItems(i) = LocalArgs(i + 1)
            Else
                TempItems(i) = LocalArgs(i + 1)
            End If
        Next
    Me.AddArrayBefore ActualStart, TempItems
    End If
    
    
    Splice = result
End Function

Attribute VB_Name = "AbstractEngraver"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public decoration As Variant  ' decoration        ''裝飾模組
Public gTextSize As getTextSize  'getTextSize        ''這是計算文字的大小
Public tuneNumber As Double
Public isBagpipes
Public flatBeams
Public graceSlurs As Boolean         ''倚音／Grace notes 圓滑線
Public percmap
Public initialClef As Variant
Public jazzchords As Boolean
Public germanAlphabet As Boolean

Public slurs As TieElemList
Public ties As TieElemList
Public voiceScale As Double
Public voiceColor
Public slursbyvoice     'as  {
'        s0v0?
'        s1v0?
'        s2v0?
'    }
Public tiesbyvoice     'as  {
'        s0v0 As []
'        s1v0 As []
'        s2v0 As []
'    }
Public endingsbyvoice     'as  {
'        s0v0?
'        s1v0?
'        s2v0?
'    }
Public scaleByVoice     'as  {
'        s0v0 As Double
'        s1v0 As Double
'        s2v0 As Double
'    }
'    colorByVoice?
Public tripletMultiplier As Double

Public abcLine As VoiceABCList  'voiceItem []
Public accidentalSlot            ''將保存該和弦上所有臨時記號的清單。
Public accidentalshiftx
Public dotshiftx
Public hasVocals As Boolean
Public minY As Double
Public partstartelem
Public startLimitElem As AbsoluteElement
Public stemdir
Public stemHeight As Double
Public measureLength As Double
Public tempoSet As Boolean
Public tiesSave As TieElemList
Public slursSave As TieElemList
Public slursbyvoiceSave
Public tiesbyvoiceSave
Public triplet As Object 'TripletElem           ''三連音模組

Public style As String

Private isJianpu As Double
Private hint  As Double
Private chartable As Dictionary
Private glyphs As New GlyphsModule




Private Function getDuration(elem As VoiceABC) As Double
    getDuration = elem.duration
End Function

Public Function cloneObject(dest, src)

    Dim prop
    For Each prop In src
'        if (src.hasOwnProperty(prop)) {
'            if (!(Array.isArray(src[prop]) || isObject(src[prop]))) {
'                dest[prop] = src[prop]
'            }
'        }
    Next
End Function


Public Function cloneAbsolute(absSrc As AbsoluteElement)
    Dim returned As New AbsoluteElement
'    Call returned.init("", 0, 0, "", 0)
'    cloneObject(returned, absSrc)
'    returned.top = 0
'    returned.bottom = -1
'    If (absSrc.abcelem) Then
'        returned.abcelem = {}
'        Call cloneObject(returned.abcelem, absSrc.abcelem)
'    End If
    Set cloneAbsolute = returned
End Function

'{
'    jianpu: { 0: "jianpu.0", 1: "jianpu.1", 2: "jianpu.2", 3: "jianpu.3", 4: "jianpu.4", 5: "jianpu.5", 6: "jianpu.6", 7: "jianpu.7", 8: "jianpu.8", 9: "jianpu.9" },
'    rest: { 0: "rests.whole", 1: "rests.half", 2: "rests.quarter", 3: "rests.8th", 4: "rests.16th", 5: "rests.32nd", 6: "rests.64th", 7: "rests.128th", "multi": "rests.multimeasure" },
'    note: { "-1": "noteheads.dbl", 0: "noteheads.whole", 1: "noteheads.half", 2: "noteheads.quarter", 3: "noteheads.quarter", 4: "noteheads.quarter", 5: "noteheads.quarter", 6: "noteheads.quarter", 7: "noteheads.quarter", 'nostem': "noteheads.quarter" },
'    rhythm: { "-1": "noteheads.slash.whole", 0: "noteheads.slash.whole", 1: "noteheads.slash.whole", 2: "noteheads.slash.quarter", 3: "noteheads.slash.quarter", 4: "noteheads.slash.quarter", 5: "noteheads.slash.quarter", 6: "noteheads.slash.quarter", 7: "noteheads.slash.quarter", nostem: "noteheads.slash.nostem" },
'    x: { "-1": "noteheads.indeterminate", 0: "noteheads.indeterminate", 1: "noteheads.indeterminate", 2: "noteheads.indeterminate", 3: "noteheads.indeterminate", 4: "noteheads.indeterminate", 5: "noteheads.indeterminate", 6: "noteheads.indeterminate", 7: "noteheads.indeterminate", nostem: "noteheads.indeterminate" },
'    harmonic: { "-1": "noteheads.harmonic.quarter", 0: "noteheads.harmonic.quarter", 1: "noteheads.harmonic.quarter", 2: "noteheads.harmonic.quarter", 3: "noteheads.harmonic.quarter", 4: "noteheads.harmonic.quarter", 5: "noteheads.harmonic.quarter", 6: "noteheads.harmonic.quarter", 7: "noteheads.harmonic.quarter", nostem: "noteheads.harmonic.quarter" },
'    triangle: { "-1": "noteheads.triangle.quarter", 0: "noteheads.triangle.quarter", 1: "noteheads.triangle.quarter", 2: "noteheads.triangle.quarter", 3: "noteheads.triangle.quarter", 4: "noteheads.triangle.quarter", 5: "noteheads.triangle.quarter", 6: "noteheads.triangle.quarter", 7: "noteheads.triangle.quarter", nostem: "noteheads.triangle.quarter" },
'    uflags: { 3: "flags.u8th", 4: "flags.u16th", 5: "flags.u32nd", 6: "flags.u64th" },
'    dflags: { 3: "flags.d8th", 4: "flags.d16th", 5: "flags.d32nd", 6: "flags.d64th" }
'}

Private Sub Class_Initialize()

    isJianpu = True
    hint = False

    Set chartable = New Dictionary
    Dim dd As New Dictionary
    dd.Add "jianpu", Array("0:jianpu.0", "1:jianpu.1", "2:jianpu.2", "3:jianpu.3", "4:jianpu.4", "5:jianpu.5", "6:jianpu.6", "7:jianpu.7", "8:jianpu.8", "9:jianpu.9")
    dd.Add "rest", Array("0:rests.whole", "1:rests.half", "2:rests.quarter", "3:rests.8th", "4:rests.16th", "5:rests.32nd", "6:rests.64th", "7:rests.128th", "multi:rests.multimeasure")
    dd.Add "note", Array("-1:noteheads.dbl", "0:noteheads.whole", "1:noteheads.half", "2:noteheads.quarter", "3:noteheads.quarter", "4:noteheads.quarter", "5:noteheads.quarter", "6:noteheads.quarter", "7:noteheads.quarter", "nostem:noteheads.quarter")
    dd.Add "rhythm", Array("-1:noteheads.slash.whole", "0:noteheads.slash.whole", "1:noteheads.slash.whole", "2:noteheads.slash.quarter", "3:noteheads.slash.quarter", "4:noteheads.slash.quarter", "5:noteheads.slash.quarter", "6:noteheads.slash.quarter", "7:noteheads.slash.quarter", "nostem:noteheads.slash.nostem")
    dd.Add "x", Array("-1:noteheads.indeterminate", "0:noteheads.indeterminate", "1:noteheads.indeterminate", "2:noteheads.indeterminate", "3:noteheads.indeterminate", "4:noteheads.indeterminate", "5:noteheads.indeterminate", "6:noteheads.indeterminate", "7:noteheads.indeterminate", "nostem:noteheads.indeterminate")
    dd.Add "harmonic", Array("-1:noteheads.harmonic.quarter", "0:noteheads.harmonic.quarter", "1:noteheads.harmonic.quarter", "2:noteheads.harmonic.quarter", "3:noteheads.harmonic.quarter", "4:noteheads.harmonic.quarter", "5:noteheads.harmonic.quarter", "6:noteheads.harmonic.quarter", "7:noteheads.harmonic.quarter", "nostem:noteheads.harmonic.quarter")
    dd.Add "triangle", Array("-1:noteheads.triangle.quarter", "0:noteheads.triangle.quarter", "1:noteheads.triangle.quarter", "2:noteheads.triangle.quarter", "3:noteheads.triangle.quarter", "4:noteheads.triangle.quarter", "5:noteheads.triangle.quarter", "6:noteheads.triangle.quarter", "7:noteheads.triangle.quarter", "nostem:noteheads.triangle.quarter")
    dd.Add "uflags", Array("3:flags.u8th", "4:flags.u16th", "5:flags.u32nd", "6:flags.u64th")
    dd.Add "dflags", Array("3:flags.d8th", "4:flags.d16th", "5:flags.d32nd", "6:flags.d64th")
    
    Dim ii As Integer
    Dim jj As Integer
    Dim distChild As New Dictionary
    Dim arr, arrK
    
    Dim tmpll
    For ii = 0 To dd.Count - 1
        distChild.RemoveAll
        arr = dd.Items(ii)
        For jj = 0 To UBound(arr)
            tmpll = Split(arr(jj), ":")
            distChild.Add tmpll(0), tmpll(1)
        Next
        chartable.Add dd.keys(ii), distChild
    Next
End Sub


''/** 這是取得 note 有連音線的集合，如果不用連音線，則傳回一個元素 */
Public Function getBeamGroup(abcLine As VoiceABCList, pos As Integer) As VoiceABCList
    '' If there are notes beamed together, they are handled as a group, so find all of them here.
    Dim elem As VoiceABC
    Dim group As New VoiceABCList
    Set elem = abcLine(pos)
    If (elem.el_typs <> "note" And Not elem.startBeam And elem.endBeam) Then
        group.Push elem
        Set getBeamGroup = group
        Exit Function
    End If
        
    
    While (pos < abcLine.Count And abcLine(pos).el_typs = "note")
        group.Push abcLine(pos)
        If (abcLine(pos).endBeam) Then
            Exit Function
        End If
        pos = pos + 1
    Wend
    'return { count: group.length, elem: group }
        Set getBeamGroup = group
End Function


Public Sub init(gTextSize As getTextSize, tuneNumber As Integer, options As Dictionary)
        Set Me.decoration = Nothing ' New decoration
        Set Me.gTextSize = gTextSize
        Me.tuneNumber = tuneNumber
'        Me.isBagpipes = options.bagpipes
'        Me.flatBeams = options.flatBeams
'        Me.graceSlurs = options.graceSlurs
'        Me.percmap = options.percmap
'        Me.initialClef = options.initialClef
'        me.jazzchords = !!options.jazzchords
'        me.germanAlphabet = !!options.germanAlphabet
        Me.reset
 End Sub

Public Sub reset()

        Set Me.slurs = New TieElemList
        Set Me.ties = New TieElemList
        Me.voiceScale = 1
'        Me.voiceColor =
'        me.slursbyvoice = {}
'        me.tiesbyvoice = {}
'        me.endingsbyvoice = {}
'        me.scaleByVoice = {}
'        me.colorByVoice = {}
        Me.tripletMultiplier = 1
'
'        Me.abcline = undefined
'        Me.accidentalSlot = undefined
'        Me.accidentalshiftx = undefined
'        Me.dotshiftx = undefined
'        Me.hasVocals = False
'        Me.minY = undefined
'        Me.partstartelem = undefined
'        Me.startlimitelem = undefined
'        Me.stemdir = undefined
End Sub
  
Public Sub setStemHeight(heightInPixels As Double)
        Me.stemHeight = CInt(heightInPixels * 10 / spacing.Step) / 10
End Sub

Public Function getCurrentVoiceId(s As Double, v As Double)
        getCurrentVoiceId = "s" + s + "v" + v
End Function

Public Sub pushCrossLineElems(s As Double, v As Double)
        Set Me.slursbyvoice(Me.getCurrentVoiceId(s, v)) = Me.slurs
        Set Me.tiesbyvoice(Me.getCurrentVoiceId(s, v)) = Me.ties
        Set Me.endingsbyvoice(Me.getCurrentVoiceId(s, v)) = Me.partstartelem
        Set Me.scaleByVoice(Me.getCurrentVoiceId(s, v)) = Me.voiceScale
        If (Me.voiceColor) Then
            Set Me.colorByVoice(Me.getCurrentVoiceId(s, v)) = Me.voiceColor
        End If
End Sub

Public Sub popCrossLineElems(s, v)
        Set Me.slurs = Me.slursbyvoice(Me.getCurrentVoiceId(s, v)) ' || {}
        Set Me.ties = Me.tiesbyvoice(Me.getCurrentVoiceId(s, v)) ' || []
        Set Me.partstartelem = Me.endingsbyvoice(Me.getCurrentVoiceId(s, v))
        Me.voiceScale = Me.scaleByVoice(Me.getCurrentVoiceId(s, v))
        If (Me.voiceScale = 0) Then Me.voiceScale = 1
        Me.voiceColor = Me.colorByVoice(Me.getCurrentVoiceId(s, v))
End Sub

Public Function containsLyrics(staves)   ':Staff[])
        Dim i As Integer, j As Integer, k As Integer
        Dim el As VoiceABC
        For i = 0 To staves.Count - 1
            For j = 0 To staves(i).voices.Count - 1
                For k = 0 To staves(i).voices(j).Count - 1
                    Set el = staves(i).voices(j)(k)
                    If Not (el.lyric Is Nothing) Then
                        '' We just want to see if there are vocals below the music to know where to put the dynamics.
                        If Not (el.positioning Is Nothing) Then
                            If (el.positioning("vocalPosition") = "below") Then Me.hasVocals = True
                        End If
                        Return
                    End If
                Next
            Next
        Next
End Function

Public Function createABCLine(Staffs As StaffList, tempo As vtempoProperties, l As Integer) As StaffGroupElement
        '' PER: This will be the lowest that any note reaches. It will be used to set the dynamics row.
        '' PER：這將是任何音符達到的最低值。 它將用於設定動態行。
        Me.minY = 2
        '' See if there are any lyrics on this line.
        '' 看看這一行是否有歌詞。
        Me.containsLyrics Staffs
        
        Me.tempoSet = False
        Dim staffGroup As StaffGroupElement
        Dim s As Integer
        Set staffGroup = N.StaffGroupElem(Me.gTextSize)
        
        For s = 0 To Staffs.Count - 1
            If (hint) Then Me.restoreState
            hint = False
            ''if (staffs[s].isJianpu == true)
            Me.createABCJianpu staffGroup, Staffs(s), tempo, s, l
            ''else
            ''    me.createABCStaff(staffgroup, staffs[s], tempo, s, l)
        Next
        Set createABCLine = staffGroup
End Function
Public Sub createABCJianpu(staffGroup As StaffGroupElement, abcStaff As Staff, tempo As vtempoProperties, s As Integer, l As Integer)
        '' If the tempo is passed in, then the first element should get the tempo attached to it.
        '' 如果傳入速度，則第一個元素應取得附加的速度。
        staffGroup.gTextSize.updateFonts abcStaff
        Dim v As Integer
        Dim voice As VoiceElement
        Dim clef As AbsoluteElement, keySig As AbsoluteElement, ts As AbsoluteElement
        
        For v = 0 To abcStaff.voices.Count
            Set voice = New VoiceElement
            voice.init v, abcStaff.voices.Count
            voice.isJianpu = True
            If (v = 0) Then
                voice.barfrom = (abcStaff.connectBarLines = "start" And abcStaff.connectBarLines = "continue")
                voice.barto = (abcStaff.connectBarLines = "continue" And abcStaff.connectBarLines = "end")
            Else
                '' duplicate = true  bar lines and other duplicate info need not be created
                '' duplicate = true  空白無資料 無需創建條線和其他重複訊息
                voice.duplicate = True
            End If
            If Not (abcStaff.title Is Nothing) Then
                If (abcStaff.title(v)) Then
                    'line voice.header = abcstaff.title(v).replace(/\\n/g, "\n")
                    voice.headerPosition = 6 + staffGroup.gTextSize.baselineToCenter(voice.header, "voicefont", "staff-extra voice-name", v, abcStaff.voices.Count) / spacing.Step
                End If
            End If
            If Not (abcStaff.clef Is Nothing) Then
                If (abcStaff.clef.typs = "perc") Then voice.isPercussion = True
                If (abcStaff.clef.typs = "jianpu") Then voice.isJianpu = True
            End If
            
            'set clef = (!me.initialClef || l === 0) && createClef(abcstaff.clef, me.tuneNumber)
            If (Me.initialClef = False Or l = 0) Then
             Set clef = createClef(abcStaff.clef, Me.tuneNumber)
            End If
            If Not (clef Is Nothing) Then
                If (v = 0 And abcStaff.barNumber) Then
                    Me.addMeasureNumber abcStaff.barNumber, clef
                End If
                voice.addChild clef
                Set Me.startLimitElem = clef  '' limit ties here
            End If
            Set keySig = createKeySignature(abcStaff.key, Me.tuneNumber)
            If Not (keySig Is Nothing) Then
                voice.addChild keySig
                Set Me.startLimitElem = keySig  '' limit ties here
            End If
            If Not (abcStaff.meter Is Nothing) Then
                If (abcStaff.meter.typs = "specified") Then
                    Me.measureLength = abcStaff.meter.value(0).num / abcStaff.meter.value(0).den
                 Else
                    Me.measureLength = 1
                End If
                Set ts = createTimeSignature(abcStaff.meter, Me.tuneNumber)
                voice.addChild ts
                Set Me.startLimitElem = ts  '' limit ties here
            End If
            If (voice.duplicate) Then
                voice.children = New AbsoluteElementList  '' we shouldn't reprint the above if we're reusing the same staff. We just created them to get the right spacing.
            End If
            Dim stafflines As Integer
            Dim isSingleLineStaff As Boolean
            stafflines = IIf((abcStaff.clef.stafflines And abcStaff.clef.stafflines = 0), abcStaff.clef.stafflines, 5)
            staffGroup.addVoice voice, s, stafflines
            isSingleLineStaff = (stafflines = 1)
            Me.createABCVoice abcStaff.voices(v), tempo, s, v, isSingleLineStaff, voice
            staffGroup.setStaffLimits (voice)
            If (v = 0) Then
                '' only do brace and bracket processing on the first voice, otherwise it would be done twice.
                '' 只對第一個語音進行大括號和方括號處理，否則會進行兩次。
                If (abcStaff.brace = "start" And ((staffGroup.brace Is Nothing) And abcStaff.brace)) Then
                    If (staffGroup.brace Is Nothing) Then
                        Set staffGroup.brace = New BraceElemList
                    End If
                    staffGroup.brace.Push N.BraceElem(voice, "brace")
                 ElseIf (abcStaff.brace = "end" And Not (staffGroup.brace Is Nothing)) Then
                    staffGroup.brace(staffGroup.brace.Count - 1).setBottomStaff voice
                 ElseIf (abcStaff.brace = "continue" And Not (staffGroup.brace Is Nothing)) Then
                    staffGroup.brace(staffGroup.brace.Count - 1).continuing voice
                End If
                If (abcStaff.bracket = "start" Or (staffGroup.bracket Is Nothing And abcStaff.bracket)) Then
                    If (staffGroup.bracket Is Nothing) Then
                        Set staffGroup.bracket = New BraceElemList
                    End If
                    staffGroup.bracket.Push N.BraceElem(voice, "bracket")
                 ElseIf (abcStaff.bracket = "end" And (Not staffGroup.bracket Is Nothing)) Then
                    staffGroup.bracket(staffGroup.bracket.Count - 1).setBottomStaff voice
                 ElseIf (abcStaff.bracket = "continue" And (Not staffGroup.bracket Is Nothing)) Then
                    staffGroup.bracket(staffGroup.bracket.Count - 1).continuing voice
                End If
            End If
        Next
End Sub

Public Sub createABCStaff(staffGroup As StaffGroupElement, abcStaff As vStaffInfo, tempo As vtempoProperties, s As Double, l As Double)
        '' If the tempo is passed in, then the first element should get the tempo attached to it.
        staffGroup.getTextSize.updateFonts (abcStaff)
        Dim v, isSingleLineStaff As Boolean
        Dim voice As VoiceElement, keySig, ts, stafflines
        
        For v = 0 To abcStaff.voices.Count
            Set voice = New VoiceElement
            voice.init v, abcStaff.voices.Count
            If (v = 0) Then
                voice.barfrom = (abcStaff.connectBarLines = "start" And abcStaff.connectBarLines = "continue")
                voice.barto = (abcStaff.connectBarLines = "continue" And abcStaff.connectBarLines = "end")
            Else
                voice.duplicate = True  '' bar lines and other duplicate info need not be created
            End If
            
            If (abcStaff.title) Then
                If (abcStaff.title(v)) Then
                    'line voice.header = abcstaff.title[v].replace(/\\n/g, "\n")
                    'line voice.headerPosition = 6 + staffgroup.getTextSize.baselineToCenter(voice.header, "voicefont", 'staff-extra voice-name', v, abcstaff.voices.length) / spacing.STEP
                End If
            End If
            If Not (abcStaff.clef Is Nothing) Then
                If (abcStaff.clef.typs = "perc") Then
                    voice.isPercussion = True
                End If
                If (abcStaff.clef.typs = "jianpu") Then
                    voice.isJianpu = True
                End If
            End If
            If (Me.initialClef = False Or l = 0) Then
             Set clef = createClef(abcStaff.clef, Me.tuneNumber)
            End If
            If Not (clef Is Nothing) Then
                If (v = 0 And abcStaff.barNumber) Then
                    Me.addMeasureNumber abcStaff.barNumber, clef
                End If
                voice.addChild (clef)
                Me.startLimitElem = clef  '' limit ties here
            End If
            Set keySig = createKeySignature(abcStaff.key, Me.tuneNumber)
            If Not (keySig Is Nothing) Then
                voice.addChild keySig
                Me.startLimitElem = keySig  '' limit ties here
            End If
            If Not (abcStaff.meter Is Nothing) Then
                If (abcStaff.meter.typs = "specified") Then
                    Me.measureLength = abcStaff.meter.value(0).num / abcStaff.meter.value(0).den
                 Else
                    Me.measureLength = 1
                End If
                Set ts = createTimeSignature(abcStaff.meter, Me.tuneNumber)
                voice.addChild (ts)
                Me.startLimitElem = ts  '' limit ties here
            End If
            If (voice.duplicate) Then
               Set voice.children = New AbsoluteElementList  '' we shouldn't reprint the above if we're reusing the same staff. We just created them to get the right spacing.
            End If
            Dim stafflines As Double
            Dim isSingleLineStaff As Boolean
            
            stafflines = IIf((abcStaff.clef.stafflines And abcStaff.clef.stafflines = 0), abcStaff.clef.stafflines, 5)
            staffGroup.addVoice voice, s, stafflines
            isSingleLineStaff = (stafflines = 1)
            Me.createABCVoice abcStaff.voices(v), tempo, s, v, isSingleLineStaff, voice
            staffGroup.setStaffLimits voice
            
  
            If (v = 0) Then
                '' only do brace and bracket processing on the first voice, otherwise it would be done twice.
                '' 只對第一個語音進行大括號和方括號處理，否則會進行兩次。
                If (abcStaff.brace = "start" And Not (staffGroup.brace And abcStaff.brace)) Then
                    If (staffGroup.brace = False) Then
                        Set staffGroup.brace = New iArray
                    End If
                    Dim bEle As New BeamElem
                    bEle.init voice, "brace"
                    staffGroup.brace.Push bEle
                 ElseIf (abcStaff.brace = "end" And staffGroup.brace) Then
                    staffGroup.brace(staffGroup.brace.Length - 1).setBottomStaff voice
                 ElseIf (abcStaff.brace = "continue" And staffGroup.brace) Then
                    staffGroup.brace(staffGroup.brace.Length - 1).continuing voice
                End If
                If (abcStaff.bracket = "start" Or (staffGroup.bracket = False And abcStaff.bracket)) Then
                    If (staffGroup.bracket = False) Then
                        Set staffGroup.bracket = New iArray
                    End If
                    Dim bEle As New BeamElem
                    bEle.init voice, "bracket"
                    staffGroup.bracket.Push bEle
                 ElseIf (abcStaff.bracket = "end" And staffGroup.bracket) Then
                    staffGroup.bracket(staffGroup.bracket.Length - 1).setBottomStaff voice
                 ElseIf (abcStaff.bracket = "continue" And staffGroup.bracket) Then
                    staffGroup.bracket(staffGroup.bracket.Count - 1).continuing voice
                End If
            End If
        Next
End Sub


  Public Sub createABCVoice(abcLine As VoiceABCList, tempo As vtempoProperties, s As Integer, v As Integer, isSingleLineStaff As Boolean, voice As VoiceElement)
'        me.popCrossLineElems(s, v)
'        me.stemdir = (me.isBagpipes) ? "down" : null
        Set Me.abcLine = abcLine
'        if (me.partstartelem) {
'            me.partstartelem = new EndingElem("", null, null)
'            voice.addOther(me.partstartelem)
'        }
'        var voiceNumber = voice.voicetotal < 2 ? -1 : voice.voicenumber
'        for (var slur in me.slurs) {
'            if (me.slurs.hasOwnProperty(slur)) {
'                '' this is already a slur element, but it was created for the last line, so recreate it.
'                '' 這已經是一個 slur 元素，但它是為最後一行建立的，因此重新建立它。
'                me.slurs[slur] = new TieElem({ force: me.slurs[slur].force, voiceNumber: voiceNumber, stemDir: me.slurs[slur].stemDir, style: me.slurs[slur].dotted })
'                if (hint) me.slurs[slur].setHint()
'                voice.addOther(me.slurs[slur])
'            }
'        }
'        for (var i = 0  i < me.ties.length  i++) {
'            '' this is already a tie element, but it was created for the last line, so recreate it.
'            '' 這已經是一個 tie 元素，但它是為最後一行創建的，因此重新創建它。
'            me.ties[i] = new TieElem({ force: me.ties[i].force, stemDir: me.ties[i].stemDir, voiceNumber: voiceNumber, style: me.ties[i].dotted })
'            if (hint) me.ties[i].setHint()
'            voice.addOther(me.ties[i])
'        }
        Dim j As Integer
        For j = 0 To Me.abcLine.Count - 1
            setAveragePitch Me.abcLine(j)
            Me.minY = Math.min(Me.abcLine(j).minPitch, Me.minY)
        Next

        Dim isFirstStaff As Boolean
        If s = 0 Then
            isFirstStaff = True
        Else
            isFirstStaff = False
        End If
        Dim pos As Integer
        Dim elemList As VoiceABCList
        Dim i As Integer
        While (pos < Me.abcLine.Count - 1)
            Debug.Print pos
            If pos = 84 Then
                pos = 84
            End If
            Set elemList = getBeamGroup(Me.abcLine, pos)
            Dim abselems As AbsoluteElementList
            Dim TempoElem As AbsoluteElement
            Set abselems = Me.createABCElement(isFirstStaff, isSingleLineStaff, voice, elemList)
            If Not abselems Is Nothing Then
                For i = 0 To i < abselems.Count
                    If Me.tempoSet <> 0 Or tempo Or tempo.suppress <> 0 Then
                        Me.tempoSet = True
                        
                        Set TempoElem = N.AbsoluteElem(tempo, 0, 0, "tempo", Me.tuneNumber, Nothing)
                        TempoElem.addFixedX N.TempoElem(tempo, Me.tuneNumber)
                        

                        '''' ************
                        'line tempoElement.addFixedX(new TempoElement(tempo, me.tuneNumber, createNoteHead))
                        voice.addChild TempoElem
                    End If
                    voice.addChild abselems(i)
                Next
            End If
            pos = pos + elemList.Count
        Wend
        'me.pushCrossLineElems(s, v)
    End Sub

Public Sub saveState()
'        set me.tiesSave = parseCommon.cloneArray(set me.ties);
'        set me.slursSave = parseCommon.cloneHashOfHash(set me.slurs);
'        set me.slursbyvoiceSave = parseCommon.cloneHashOfHash(set me.slursbyvoice);
'        set me.tiesbyvoiceSave = parseCommon.cloneHashOfArrayOfHash(set me.tiesbyvoice);
End Sub

Public Sub restoreState()
'        set me.ties = parseCommon.cloneArray(set me.tiesSave);
'        set me.slurs = parseCommon.cloneHashOfHash(set me.slursSave);
'        set me.slursbyvoice = parseCommon.cloneHashOfHash(set me.slursbyvoiceSave);
'        set me.tiesbyvoice = parseCommon.cloneHashOfArrayOfHash(set me.tiesbyvoiceSave);
End Sub



    '' return an array of AbsoluteElement
Public Function createABCElement(isFirstStaff As Boolean, isSingleLineStaff As Boolean, voice As VoiceElement, elems As VoiceABCList) As AbsoluteElementList
        Dim elemset As New AbsoluteElementList
        
        If elems.Count > 1 Then
                '' it is undefined if we were passed an array in - an array means a set of notes that should be beamed together.
            Set elemset = Me.createBeam(isSingleLineStaff, voice, elems)
            Set createABCElement = elemset
            Exit Function
        End If
        Dim elem As VoiceABC
        
        Set elem = elems(0)
            
        Select Case elem.el_typs

            Case "note":
                If voice.isJianpu = True Then
                    ''簡譜是否是長拍子
                    
                    ''console.log(`test d.ts Constants.COLORS.SILVER-> ${Constants.COLORS.SILVER}`)
                    ''Object.keys(Constants.COLORS).forEach((ths) => {
                    ''    console.log(`test d.ts Constants.COLORS.SILVER for-> ${ths}`)
                    ''})
                    
                    Set elemset = Me.createLongNote(isSingleLineStaff, voice, elem)
                 Else
                    ''elemset = me.createBeam(isSingleLineStaff, voice, [elem])
                    elemset(0) = Me.createNote(elem, False, isSingleLineStaff, voice)
                    If Not Me.triplet Is Nothing And Me.triplet.isClosed() Then
                        voice.addOther (Me.triplet)
                        Me.triplet = Null
                        Me.tripletMultiplier = 1
                    End If
                End If
            Case "bar":
                elemset(0) = Me.createBarLine(voice, elem, isFirstStaff)
                If (voice.duplicate = True And elemset.Count > 0) Then
                    elemset(0).invisible = True
                
                End If
            Case "meter":
                Set elemset(0) = createTimeSignature(elem, Me.tuneNumber)
                Set Me.startLimitElem = elemset(0)  '' limit ties here
                If (voice.duplicate = True And elemset.Count > 0) Then
                    elemset(0).invisible = True
                End If
            Case "clef":
                 Set elemset(0) = createClef(elem, Me.tuneNumber)
                If (elemset(0) Is Nothing) Then
                    Set createABCElement = Nothing
                    Exit Function
                End If
                If (voice.duplicate = True And elemset.Count > 0) Then
                    elemset(0).invisible = True
                End If
            Case "key":
                Dim absKey As AbsoluteElement
                Set absKey = createKeySignature(elem, Me.tuneNumber)
                If Not (absKey Is Nothing) Then
                    Set elemset(0) = absKey
                    Set Me.startLimitElem = elemset(0)  '' limit ties here
                End If
                If (voice.duplicate = True And elemset.Count > 0) Then elemset(0).invisible = True
                
            Case "stem":
                Me.stemdir = IIf(elem.Direction = "auto", "", elem.Direction)
                
            Case "part":
                Dim abselem As New AbsoluteElement
                Call abselem.init(elem, 0, 0, "part", Me.tuneNumber)
                Dim calsize As size
                calsize = Me.gTextSize.calc(elem.title, "partsfont", "part")
                
                Dim option2 As oRelativeOptions
                option2.typs = "part"
                option2.height = calsize.height / spacing.Step
                
                abselem.addFixedX N.RelativeElem(elem.title, 0, 0, 0, option2)
                Set elemset(0) = abselem
                
'            Case tempo:
'                Dim abselem3 As New AbsoluteElement
'                Dim tEle As New TempoElement
'                abselem3.init elem, 0, 0, "tempo", Me.tuneNumber
'                tEle.init elem, Me.tuneNumber, createNoteHead
'                abselem3.addFixedX tEle
'                Set elemset(0) = abselem3
'            Case VoiceElemTYPS.style:
'                if (elem.head === "normal")
'                    delete Me.style
'                Else
'                    Me.style = elem.head
'                break
'            Case VoiceElemTYPS.hint:
'                hint = True
'                me.saveState()
'                break
'            Case VoiceElemTYPS.midi:
'                '' This has no effect on the visible music, so just skip it.
'                break
'            Case VoiceElemTYPS.scale:
'                Me.voiceScale = elem.Size
'                break
'            Case VoiceElemTYPS.color:
'                Me.voiceColor = elem.color
'                voice.color = Me.voiceColor
'                break

            Case Else
                Dim abselem2 As AbsoluteElement
                Dim tmpDic As New oRelativeOptions
                
                Set abselem2 = N.AbsoluteElem(elem, 0, 0, "unsupported", Me.tuneNumber)
                tmpDic.typs = "debug"
                
                
                abselem2.addFixed N.RelativeElem("element typs " + elem.el_typs, 0, 0, 0, tmpDic)
                Set elemset(0) = abselem2
        End Select
    Set createABCElement = elemset
End Function
Public Function createBeam(isSingleLineStaff As Boolean, voice As VoiceElement, elems As VoiceABCList) As AbsoluteElementList
        Dim abselemset As AbsoluteElementList
        Dim i As Integer
        Dim beamEle As BeamElem
        Dim elem As VoiceABC
        Dim abselem As AbsoluteElement
        Dim tempStemDir As String
        
        Set abselemset = New AbsoluteElementList
        Set beamEle = N.BeamElem(Me.stemHeight * Me.voiceScale, Me.stemdir, Me.flatBeams, elems(0))
        
        For i = 0 To elems.Count - 1
            '' Do a first pass to figure out the stem direction before creating the notes, so that staccatos and other decorations can be placed correctly.
            beamEle.runningDirection elems(i)
        Next
        beamEle.setStemDirection
         tempStemDir = Me.stemdir
        Me.stemdir = IIf(beamEle.stemsUp, "up", "down")
        For i = 0 To elems.Count - 1
            Set elem = elems(i)
            Set abselem = Me.createNote(elem, True, isSingleLineStaff, voice)
            abselemset.Push abselem
            beamEle.Add abselem
            If (Not Me.triplet Is Nothing) Then
                If (Me.triplet.isClosed()) Then
                    voice.addOther (Me.triplet)
                    Me.triplet = Null
                    Me.tripletMultiplier = 1
                End If
            End If
        Next
        beamEle.calcDir
        voice.addBeam beamEle
        Me.stemdir = tempStemDir
        Set createBeam = abselemset
   End Function

'/** 簡譜  超過1拍要加入長拍子 */
Public Function createLongNote(isSingleLineStaff As Boolean, voice As VoiceElement, elem As VoiceABC) As AbsoluteElementList
        Dim abselemset As AbsoluteElementList
        Dim abselem As AbsoluteElement
        Dim longelem As AbsoluteElement
        Dim totalduration As Double
        Dim durlog As Double
        Dim dot As Integer
        Dim cloneelem As VoiceABC
        Dim rOpt As oRelativeOptions
        
        Dim tmpR As RelativeElement
        

        totalduration = getDuration(elem)
        durlog = Math.Floor(Log(totalduration) / Log(2))  ''TODO use getDurlog
        dot = 0
        Set abselemset = New AbsoluteElementList
        If (totalduration < 0.5) Then
           Set abselem = Me.createNote(elem, True, isSingleLineStaff, voice)
            abselemset.Push abselem
         Else
            '' 超過二拍加入長拍子
            Set cloneelem = elem.clone
            cloneelem.duration = 0.25
            Set abselem = Me.createNote(cloneelem, True, isSingleLineStaff, voice)
            abselemset.Push abselem
            totalduration = totalduration - 0.25
            For totalduration = totalduration / 0.25 To 0 Step -1
            
                longelem = cloneAbsolute(abselem)
                Set rOpt = New oRelativeOptions
                rOpt.typs = "beatline"
                rOpt.pitch2 = 2
                rOpt.lineWidth = 2
                rOpt.bottom = 1
                
                longelem.addFixed N.RelativeElem("", 0, 14, 5, rOpt)
                abselemset.Push longelem
      
            Next

        End If

        '' 計算符點音符數量 dot
        ''for (var tot = Math.pow(2, durlog), inc = tot / 2
        ''    tot < duration
        ''    dot++, tot += inc, inc /= 2)

        ''for (durlog  durlog > -2  durlog--) {
        ''    var index = -durlog - 3
        ''    longelem = cloneAbsolute(abselem)
        ''    longelem.addFixed(new RelativeElement(null, 0, 14, 1.5 - index *3, { typs: "beatline", pitch2: 1, linewidth: 1.2, bottom: 1 }))
        ''    abselemset.push(longelem)
        ''}
        If Not (Me.triplet Is Nothing) Then
            If (Me.triplet.isClosed()) Then
                voice.addOther (Me.triplet)
                Me.triplet = Null
                Me.tripletMultiplier = 1
            End If
        End If
        Set createLongNote = abselemset
End Function

Public Function addGraceNotes(elem As VoiceABC, voice As VoiceElement, abselem As AbsoluteElement, notehead As RelativeElement, stemHeight As Double, isBagpipes As Boolean, roomTaken As Double) As Double
        Dim gracescale  As Double
        Dim graceScaleStem  As Double
        Dim gracebeam  As BeamElem
        Dim flag
        Dim i  As Integer
        Dim graceoffsets  As iArray  'number
        Dim tmpRel As RelativeElement
        Dim tmpDic As Dictionary
        
         gracescale = 3 / 5
        graceScaleStem = 3.5 / 5  '' TODO-PER: empirically found constant.
        stemHeight = Math.Round(stemHeight * graceScaleStem)
         
    

        If (elem.gracenotes.Count > 1) Then
            Set gracebeam = New BeamElem
            gracebeam.init stemHeight, "grace", isBagpipes
            If (hint) Then gracebeam.setHint
            Set gracebeam.mainNote = abselem    '' this gives us a reference back to the note this is attached to so that the stems can be attached somewhere.
        End If

        
        Set graceoffsets = New iArray
        For i = elem.gracenotes.Count - 1 To 0 Step -1   '' figure out where to place each gracenote
            roomTaken = roomTaken + 10
            graceoffsets(i) = roomTaken
            If (elem.gracenotes(i).accidental) Then
                roomTaken = roomTaken + 7
            End If
        Next
        Dim gracepitch As Double
        Dim accidentalSlot As iArray
        Dim ret As Double
        Dim pos As Double
        Dim dAcciaccatura As Double
        Dim graceDuration As Double
        Dim pseudoabselem As Double
        Dim isInvisibleRest As Double
        Dim graceDuration As Double
        Dim grace

        For i = 0 To elem.gracenotes.Count - 1
            gracepitch = elem.gracenotes(i).verticalPos

            flag = IIf((Not gracebeam Is Nothing), Empty, chartable.uflags(IIf(isBagpipes, 5, 3)))
            Set accidentalSlot = New iArray
            Set tmpDic = New Dictionary
            tmpDic("dir") = "up"
            tmpDic("headx") = -graceoffsets(i)
            tmpDic("extrax") = -graceoffsets(i)
            tmpDic("flag") = flag
            tmpDic("scale") = gracescale * Me.voiceScale
            tmpDic("accidentalSlot") = accidentalSlot
            
            Set ret = createNoteHead(abselem, "noteheads.quarter", elem.gracenotes(i), tmpDic)
            ret.notehead.highestVert = ret.notehead.pitch + stemHeight
            Set grace = ret.notehead
            Me.addSlursAndTies abselem, elem.gracenotes(i), grace, voice, "up", True

            abselem.addExtra grace
            '' PER: added acciaccatura slash
            If (elem.gracenotes(i).acciaccatura) Then
                pos = elem.gracenotes(i).verticalPos + 7 * gracescale         '' the same formula that determines the flag position.
                dAcciaccatura = IIf(Not gracebeam Is Nothing, 5, 6)         '' just an offset to make it line up correctly.
                
                Set tmpR = New RelativeElement
                Set tmpDic = New Dictionary
                tmpDic("scalex") = gracescale
                tmpDic("scaley") = gracescale
                
                tmpR.init "flags.ugrace", -graceoffsets(i) + dAcciaccatura, 0, pos, tmpDic
                abselem.addRight tmpR
            End If
            If Not (gracebeam Is Nothing) Then '' give the beam the necessary info
                graceDuration = elem.gracenotes(i).duration / 2
                If (isBagpipes) Then graceDuration = graceDuration / 2
                    Set pseudoabselem = New Dictionary
                    Set tmpDic = New Dictionary
                    tmpDic("averagepitch") = gracepitch
                    tmpDic("minpitch") = gracepitch
                    tmpDic("maxpitch") = gracepitch
                    tmpDic("duration") = graceDuration
                    pseudoabselem("heads") = Array(grace)
                    pseudoabselem("abcelem") = tmpDic
                    
                End If
                gracebeam.Add (pseudoabselem)
             Else  '' draw the stem
                Dim p1, p2, dx, width
                p1 = gracepitch + 1 / 3 * gracescale
                p2 = gracepitch + 7 * gracescale
                dx = grace.dx + grace.w
                width = -0.6
                Set tmpR = New RelativeElement
                Set tmpDic = New Dictionary
                tmpDic("typs") = "stem"
                tmpDic("pitch2") = p2
                tmpDic("linewidth") = width
                tmpR.init Null, dx, 0, p1, tmpDic
                abselem.addExtra tmpR
            End If
            ledgerLines abselem, gracepitch, gracepitch, False, glyphs.getSymbolWidth("noteheads.quarter"), Array(), True, grace.dx - 1, 0.6

            '' if this is the first grace note, we might want to start a slur.
            '' there is a slur if graceSlurs is specifically set.
            '' there is no slur if it is bagpipes.
            '' there is not a slur if the element is a spacer or invisible rest.
            Dim isInvisibleRest As Boolean
            If Not elem.rest Is Nothing Then
                isInvisibleRest = (elem.rest.typs = "spacer" Or elem.rest.typs = "invisible")
            Else
                isInvisibleRest = False
            End If
            
            Dim tieE As TieElem
            If (i = 0 And Not isBagpipes And Me.graceSlurs And Not isInvisibleRest) Then
                '' This is the overall slur that is under the grace notes.
                Set tieE = New TieElem
                Set tmpDic = New Dictionary
                tmpDic("anchor1") = grace
                tmpDic("anchor2") = notehead
                tmpDic("isGrace") = True
                tieE.init tmpDic
                
                voice.addOther tieE
            End If
        Next

        If Not (gracebeam Is Nothing) Then
            gracebeam.calcDir
            voice.addBeam gracebeam
        End If
        addGraceNotes = roomTaken
End Function

Public Function addNoteToAbcElement(abselem As AbsoluteElement, elem As VoiceABC, dot As Integer, stemdir As String, style As String, zeroDuration As Boolean, durlog As Double, nostem, voice As VoiceElement) As Dictionary
        Dim dotshiftx As Double '' room taken by chords with displaced noteheads which cause dots to shift
        Dim notehead As RelativeElement
        Dim roomTaken As Double
        Dim roomTakenRight As Double
        Dim min As Double
        Dim i As Double
        Dim additionalLedgers As New iArray
        Dim accidentalSlot As New iArray
        Dim symbolWidth As Double
        Dim dir As String
        Dim noteSymbol As String
        Dim tmpR As RelativeElement
        Dim tmpDic As Dictionary
        
        '' The accidentalSlot will hold a list of all the accidentals on this chord. Each element is a vertical place,
        '' and contains a pitch, which is the last pitch that contains an accidental in that slot. The slots are numbered
        '' from closest to the note to farther left. We only need to know the last accidental we placed because
        '' we know that the pitches are sorted by now.
        ''accidentalSlot 將保存該和弦上所有臨時記號的清單。 每個元素都是一個垂直的地方，
        '' 並包含一個音高，這是該插槽中包含臨時記號的最後一個音高。 插槽已編號
        '' 從最靠近音符到最左邊。 我們只需要知道我們放置的最後一個意外項，因為
        '' 我們知道現在音高已經排序了。

         dir = IIf((elem.averagepitch >= 6), "down", "up")
        If (stemdir <> "") Then dir = stemdir

        style = IIf(elem.style <> "", elem.style, style)  '' get the style of note head.
        If (style = "" Or style = "normal") Then style = "note"

        If (zeroDuration) Then
            noteSymbol = chartable(style).nostem
        Else
            noteSymbol = chartable(style)(CStr(-durlog))
        End If
        If IsEmpty(noteSymbol) Then
            Debug.Print "noteSymbol:"  ''console.log("noteSymbol:", style, durlog, zeroDuration)
        End If
        '' determine elements of chords which should be shifted
        '' 決定應該要移動的和弦元素
        Dim p As Integer
        Dim prev
        Dim curr
        Dim delta As Double
        Dim pp As Integer
        Dim st, stmax, stepa
        st = IIf(dir = "down", elem.pitches.Count - 2, 1)
        stmax = IIf((dir = "down"), p >= 0, p < elem.pitches.Count)
        stepa = IIf((dir = "down"), -1, 1)
        For p = st To stmax Step p = p + stepa
        
            Set prev = elem.pitches(IIf((dir = "down"), p + 1, p - 1))
            Set curr = elem.pitches(p)
            delta = IIf((dir = "down"), prev.pitch - curr.pitch, curr.pitch - prev.pitch)
            If (delta <= 1 And Not prev.printer_shift) Then
                curr.printer_shift = IIf(delta, "different", "same")
                If (curr.verticalPos > 11 Or curr.verticalPos < 1) Then        '' PER: add extra ledger line
                    additionalLedgers.Push curr.verticalPos - (curr.verticalPos Mod 2)
                End If
                If (dir = "down") Then
                    roomTaken = glyphs.getSymbolWidth(noteSymbol) + 2
                 Else
                    dotshiftx = glyphs.getSymbolWidth(noteSymbol) + 2
                End If
            End If
        Next

        '' 疊音製作
        
        Dim flag
        Dim c As String
        Dim percHead
        Dim isTopWhenStemIsDown As Boolean
        Dim isBottomWhenStemIsUp As Boolean
        pp = elem.pitches.Count
        For p = 0 To elem.pitches.Count - 1

            If (Not nostem) Then
                
                If ((dir = "down" And p <> 0) Or (dir = "up" And p <> pp - 1)) Then '' not the stemmed elem of the chord
                    flag = Empty
                 Else
                    flag = chartable(IIf((dir = "down"), "dflags", "uflags"))(-durlog)
                End If
            End If
            c = "0"
            '' There is a style for the whole group of pitches, but there could also be an override for a particular pitch.
            '' 整個音高組都有一個樣式，但也可能有一個特定音高的覆蓋。
            If (elem.pitches(p).style <> "") Then
                c = chartable(elem.pitches(p).style)(-durlog)
             ElseIf (voice.isPercussion And Me.percmap) Then
                c = noteSymbol
                percHead = Me.percmap(pitchesToPerc(elem.pitches(p)))
                If (percHead And percHead.notehead) Then
                    If (chartable(percHead.notehead)) Then
                        c = chartable(percHead.notehead)(-durlog)
                End If
             Else
                c = noteSymbol
            End If
            ''jianpu 改數字譜
            c = (elem.pitches(p).pitch Mod 7) + 1
            elem.pitches(p).verticalPos = 2 + p * 4.5     ''y位置

            '' The highest position for the sake of placing slurs is itself if the slur is internal. It is the highest position possible if the slur is for the whole chord.
            '' If the note is the only one in the chord, then any slur it has counts as if it were on the whole chord.
            '' 如果連線是內部的，則放置連線的最高位置就是連線本身。 如果連線針對整個和弦，則這是可能的最高位置。
            '' 如果該音符是和弦中唯一的音符，則它所具有的任何連線都將被視為在整個和弦上。
            elem.pitches(p).highestVert = elem.pitches(p).verticalPos
            isTopWhenStemIsDown = (stemdir = "up" Or dir = "up") And p = 0
            isBottomWhenStemIsUp = (stemdir = "down" Or dir = "down") And p = pp - 1
            
            If (isTopWhenStemIsDown Or isBottomWhenStemIsUp) Then '' place to put slurs if not already on pitches

                If (Not elem.startSlur Is Nothing And pp = 1) Then
                    elem.pitches(p).highestVert = elem.pitches(pp - 1).verticalPos
                    If (getDuration(elem) < 1 And (stemdir = "up" Or dir = "up")) Then
                        elem.pitches(p).highestVert = elem.pitches(p).highestVert + 6       '' If the stem is up, then compensate for the length of the stem
                    End If
                End If
                If (Not elem.startSlur Is Nothing) Then
                    If (elem.pitches(p).startSlur Is Nothing) Then elem.pitches(p).startSlur = New vSlur  ''TODO possibly redundant, provided array is not optional
                    For i = 0 To elem.startSlur.Count
                        addIfNotExist elem.pitches(p).startSlur, elem.startSlur(i)
                    Next
                End If

                If Not (elem.endSlur Is Nothing) Then
                    elem.pitches(p).highestVert = elem.pitches(pp - 1).verticalPos
                    If (getDuration(elem) < 1 And (stemdir = "up" Or dir = "up")) Then
                        elem.pitches(p).highestVert = elem.pitches(p).highestVert + 6       '' If the stem is up, then compensate for the length of the stem
                    End If
                    If (elem.pitches(p).endSlur Is Nothing) Then elem.pitches(p).endSlur = New iArray    ''TODO possibly redundant, provided array is not optional
                        For i = 0 To elem.endSlur.Count - 1
                            addIfNotExist elem.pitches(p).endSlur, elem.endSlur(i)
                        Next
                    End If
                End If
            End If
            
            Dim hasStem As Boolean
            Dim ret As Dictionary
            Dim noteOpt As oNoteHeadOptions
            hasStem = Not nostem And durlog <= -1
            If (isJianpu) Then
                Set noteOpt = New oNoteHeadOptions
                noteOpt.dir = "down"
                noteOpt.extrax = --roomTaken
                noteOpt.flag = flag
                noteOpt.dot = dot
                noteOpt.dotshiftx = dotshiftx
                noteOpt.scale_ = Me.voiceScale
                Set noteOpt.accidentalSlot = accidentalSlot
                noteOpt.shouldExtendStem = (stemdir <> "")
                noteOpt.printAccidentals = Not voice.isPercussion
                
                Set ret = createNoteHead(abselem, c, elem.pitches(p), noteOpt)
            Else
                Set noteOpt = New oNoteHeadOptions
                noteOpt.dir = "down"
                noteOpt.extrax = --roomTaken
                noteOpt.flag = flag
                noteOpt.dot = dot
                noteOpt.dotshiftx = dotshiftx
                noteOpt.scale_ = Me.voiceScale
                Set noteOpt.accidentalSlot = accidentalSlot
                noteOpt.shouldExtendStem = (stemdir <> "")
                noteOpt.printAccidentals = Not voice.isPercussion
                
                Set ret = createNoteHead(abselem, c, elem.pitches(p), noteOpt)
            End If
            symbolWidth = Math.max(glyphs.getSymbolWidth(c), symbolWidth)
            abselem.extraw = abselem.extraw - ret("extraLeft")
            Set notehead = ret("notehead")
            If Not (notehead Is Nothing) Then
                Me.addSlursAndTies abselem, elem.pitches(p), notehead, voice, IIf(hasStem, dir, ""), False

                If Not (elem.gracenotes Is Nothing) Then
                    If elem.gracenotes.Count > 0 Then
                        '' If there is a tie to the grace notes, leave a little more room for the note to avoid collisions.
                        '' 如果裝飾音有聯繫，請為音符留出更多空間以避免衝突。
                        notehead.bottom = notehead.bottom - 1
                    End If
                End If
                abselem.addHead notehead
            End If
            roomTaken = roomTaken + ret("accidentalshiftx")
            roomTakenRight = Math.max(roomTakenRight, ret("dotshiftx"))
        Next

        '' draw stem from the furthest note to a pitch above/below the stemmed note
        '' 將詞幹從最遠的音符繪製到高於/低於詞幹音符的音高
        '' 繪製符桿
        Dim stemHeight As Double
        Dim p1 As Double, p2 As Double
        Dim dx As Double, width As Double
        If (Not isJianpu And hasStem) Then
            stemHeight = CInt(70 * Me.voiceScale) / 10
            p1 = IIf((dir = "down"), elem.minPitch - stemHeight, elem.minPitch + 1 / 3)
            '' PER added stemdir test to make the line meet the note.
            '' PER新增了stemdir測試以使該行符合註解。
            If (p1 > 6 And Not stemdir) Then p1 = 6
            p2 = IIf((dir = "down"), elem.maxPitch - 1 / 3, elem.maxPitch + stemHeight)
            '' PER added stemdir test to make the line meet the note.
            '' PER新增了stemdir測試以使該行符合註解。
            If (p2 < 6 And Not stemdir) Then p2 = 6
            dx = IIf((dir = "down" And abselem.heads.Count = 0), 0, abselem.heads(0).w)
            width = IIf((dir = "down"), 1, -1)
            '' TODO-PER-HACK: One typs of note head has a different placement of the stem. This should be more generically calculated:
            '' TODO-PER-HACK：一種類型的符頭具有不同的符幹位置。 這應該更通用地計算：

            If (notehead And notehead.c = "noteheads.slash.quarter") Then
                If (dir = "down") Then
                    p2 = p2 - 1
                Else
                    p1 = p1 + 1
                End If
            End If
            Dim rOpt As New oRelativeOptions
            rOpt.typs = "stem"
            rOpt.pitch2 = p2
            rOpt.lineWidth = width
            rOpt.bottom = p1 - 1
             
            abselem.addRight N.RelativeElem("", dx, 0, p1, rOpt)

            min = Math.min(p1, p2)
        End If

        Set tmpDic = New Dictionary
        Set tmpDic("noteHead") = notehead
        tmpDic("roomTaken") = roomTaken
        tmpDic("roomTakenRight") = roomTakenRight
        tmpDic("min") = min
        Set tmpDic("additionalLedgers") = additionalLedgers
        tmpDic("dir") = dir
        tmpDic("symbolWidth") = symbolWidth
        Set addNoteToAbcElement = tmpDic
End Function

'    addNoteToAbcElementOld(abselem: AbsoluteElement, elem: VoiceItem, dot: number, stemdir: StemDirection, style, zeroDuration, durlog, nostem, voice: VoiceElement) {
'        var dotshiftx = 0  '' room taken by chords with displaced noteheads which cause dots to shift
'        var notehead: RelativeElement
'        var roomtaken = 0
'        var roomtakenright = 0
'        var Min
'        var i
'        var additionalLedgers = []
'        '' The accidentalSlot will hold a list of all the accidentals on this chord. Each element is a vertical place,
'        '' and contains a pitch, which is the last pitch that contains an accidental in that slot. The slots are numbered
'        '' from closest to the note to farther left. We only need to know the last accidental we placed because
'        '' we know that the pitches are sorted by now.
'        ''accidentalSlot 將保存該和弦上所有臨時記號的清單。 每個元素都是一個垂直的地方，
'        '' 並包含一個音高，這是該插槽中包含臨時記號的最後一個音高。 插槽已編號
'        '' 從最靠近音符到最左邊。 我們只需要知道我們放置的最後一個意外項，因為
'        '' 我們知道現在音高已經排序了。
'        var accidentalSlot = []
'        var symbolWidth = 0
'
'        var dir = (elem.averagepitch >= 6) ? "down" : "up"
'        if (stemdir) dir = stemdir
'
'        style = elem.style ? elem.style : style  '' get the style of note head.
'        if (!style || style === "normal") style = "note"
'        var noteSymbol
'        if (zeroDuration)
'            noteSymbol = chartable[style].nostem
'        Else
'            noteSymbol = chartable[style][-durlog]
'        if (!noteSymbol)
'            console.log("noteSymbol:", style, durlog, zeroDuration)
'
'        '' determine elements of chords which should be shifted
'        '' 決定應該要移動的和弦元素
'        var p
'        for (p = (dir === "down") ? elem.pitches.length - 2 : 1  (dir === "down") ? p >= 0 : p < elem.pitches.length  p = (dir === "down") ? p - 1 : p + 1) {
'            var prev = elem.pitches[(dir === "down") ? p + 1 : p - 1]
'            var curr = elem.pitches[p]
'            var delta = (dir === "down") ? prev.pitch - curr.pitch : curr.pitch - prev.pitch
'            if (delta <= 1 && !prev.printer_shift) {
'                curr.printer_shift = (delta) ? "different" : "same"
'                if (curr.verticalPos > 11 || curr.verticalPos < 1) {        '' PER: add extra ledger line
'                    additionalLedgers.push(curr.verticalPos - (curr.verticalPos % 2))
'                }
'                if (dir === "down") {
'                    roomtaken = glyphs.getSymbolWidth(noteSymbol) + 2
'                } else {
'                    dotshiftx = glyphs.getSymbolWidth(noteSymbol) + 2
'                }
'            }
'        }
'
'        var pp = elem.pitches.length
'        for (p = 0  p < elem.pitches.length  p++) {
'
'            if (!nostem) {
'                var flag
'                if ((dir === "down" && p !== 0) || (dir === "up" && p !== pp - 1)) { '' not the stemmed elem of the chord
'                    flag = Null
'                } else {
'                    flag = chartable[(dir === "down") ? "dflags" : "uflags"][-durlog]
'                }
'            }
'            var c
'            '' There is a style for the whole group of pitches, but there could also be an override for a particular pitch.
'            '' 整個音高組都有一個樣式，但也可能有一個特定音高的覆蓋。
'            if (elem.pitches[p].style) {
'                c = chartable[elem.pitches[p].style][-durlog]
'            } else if (voice.isPercussion && me.percmap) {
'                c = noteSymbol
'                var percHead = me.percmap[pitchesToPerc(elem.pitches[p])]
'                if (percHead && percHead.noteHead) {
'                    if (chartable[percHead.noteHead])
'                        c = chartable[percHead.noteHead][-durlog]
'                }
'            } else
'                c = noteSymbol
'            ''jianpu 改數字譜
'            c = `jianpu.${(elem.verticalPos % 7) + 1}`
'            elem.pitches [p].verticalPos = 2
'
'            '' The highest position for the sake of placing slurs is itself if the slur is internal. It is the highest position possible if the slur is for the whole chord.
'            '' If the note is the only one in the chord, then any slur it has counts as if it were on the whole chord.
'            '' 如果連線是內部的，則放置連線的最高位置就是連線本身。 如果連線針對整個和弦，則這是可能的最高位置。
'            '' 如果該音符是和弦中唯一的音符，則它所具有的任何連線都將被視為在整個和弦上。
'            elem.pitches[p].highestVert = elem.pitches[p].verticalPos
'            var isTopWhenStemIsDown = (stemdir === "up" || dir === "up") && p === 0
'            var isBottomWhenStemIsUp = (stemdir === "down" || dir === "down") && p === pp - 1
'            if (isTopWhenStemIsDown || isBottomWhenStemIsUp) { '' place to put slurs if not already on pitches
'
'                if (elem.startSlur || pp === 1) {
'                    elem.pitches[p].highestVert = elem.pitches[pp - 1].verticalPos
'                    if (getDuration(elem) < 1 && (stemdir === "up" || dir === "up"))
'                        elem.pitches[p].highestVert += 6         '' If the stem is up, then compensate for the length of the stem
'                }
'                if (elem.startSlur) {
'                    if (!elem.pitches[p].startSlur) elem.pitches[p].startSlur = []  ''TODO possibly redundant, provided array is not optional
'                    for (i = 0  i < elem.startSlur.length  i++) {
'                        addIfNotExist(elem.pitches[p].startSlur, elem.startSlur[i])
'                    }
'                }
'
'                if (elem.endSlur) {
'                    elem.pitches[p].highestVert = elem.pitches[pp - 1].verticalPos
'                    if (getDuration(elem) < 1 && (stemdir === "up" || dir === "up"))
'                        elem.pitches[p].highestVert += 6         '' If the stem is up, then compensate for the length of the stem
'                    if (!elem.pitches[p].endSlur) elem.pitches[p].endSlur = []  ''TODO possibly redundant, provided array is not optional
'                    for (i = 0  i < elem.endSlur.length  i++) {
'                        addIfNotExist(elem.pitches[p].endSlur, elem.endSlur[i])
'                    }
'                }
'            }
'
'            var hasStem = !nostem && durlog <= -1
'            var ret = createNoteHead(abselem, c, elem.pitches[p],
'                { dir: dir, extrax: -roomTaken, flag: flag, dot: dot, dotshiftx: dotshiftx, scale: me.voiceScale, accidentalSlot: accidentalSlot, shouldExtendStem: !stemdir, printAccidentals: !voice.isPercussion })
'            symbolWidth = Math.Max(glyphs.getSymbolWidth(c), symbolWidth)
'            abselem.extraw -= ret.extraLeft
'            notehead = ret.notehead
'            if (noteHead) {
'                me.addSlursAndTies(abselem, elem.pitches[p], noteHead, voice, hasStem ? dir : null, false)
'
'                if (elem.gracenotes && elem.gracenotes.length > 0) {
'                    '' If there is a tie to the grace notes, leave a little more room for the note to avoid collisions.
'                    '' 如果裝飾音有聯繫，請為音符留出更多空間以避免衝突。
'                    notehead.bottom = notehead.bottom - 1
'                }
'                abselem.addHead (notehead)
'            }
'            roomTaken += ret.accidentalshiftx
'            roomtakenright = Math.Max(roomtakenright, ret.dotshiftx)
'        }
'
'        '' draw stem from the furthest note to a pitch above/below the stemmed note
'        '' 將詞幹從最遠的音符繪製到高於/低於詞幹音符的音高
'        '' 繪製符桿
'        if (hasStem) {
'            var stemheight = Math.Round(70 * Me.voiceScale) / 10
'            var p1 = (dir === "down") ? elem.minpitch - stemHeight : elem.minpitch + 1 / 3
'            '' PER added stemdir test to make the line meet the note.
'            '' PER新增了stemdir測試以使該行符合註解。
'            if (p1 > 6 && !stemdir) p1 = 6
'            var p2 = (dir === "down") ? elem.maxpitch - 1 / 3 : elem.maxpitch + stemHeight
'            '' PER added stemdir test to make the line meet the note.
'            '' PER新增了stemdir測試以使該行符合註解。
'            if (p2 < 6 && !stemdir) p2 = 6
'            var dx = (dir === "down" || abselem.heads.length === 0) ? 0 : abselem.heads[0].w
'            var width = (dir === "down") ? 1 : -1
'            '' TODO-PER-HACK: One typs of note head has a different placement of the stem. This should be more generically calculated:
'            '' TODO-PER-HACK：一種類型的符頭具有不同的符幹位置。 這應該更通用地計算：
'
'            if (noteHead && noteHead.c === 'noteheads.slash.quarter') {
'                if (dir === 'down')
'                    p2 -= 1
'                Else
'                    p1 += 1
'            }
'            abselem.addRight(new RelativeElement(null, dx, 0, p1, { typs: "stem", pitch2: p2, linewidth: width, bottom: p1 - 1 }))
'            ''var RelativeElement = function RelativeElement(c, dx, w, pitch, opt) {
'            Min = Math.Min(p1, p2)
'        }
'        return { noteHead: noteHead, roomTaken: roomTaken, roomTakenRight: roomTakenRight, min: min, additionalLedgers: additionalLedgers, dir: dir, symbolWidth: symbolWidth }
'    }

Public Sub addLyric(abselem As AbsoluteElement, elem As VoiceABC)
        Dim lyricStr As String
        Dim div As String
        Dim lyricDim As String
        Dim position As String
        Dim ly
        Dim tmpRel As RelativeElement
        Dim tmpDic As Dictionary
        lyricStr = ""
        
        For Each ly In elem.lyric
            div = IIf(ly.divider = " ", "", ly.divider)
            lyricStr = lyricStr & ly.syllable & div & vbCrLf
        Next
         lyricDim = Me.getTxtSize.calc(lyricStr, "vocalfont", "lyric")
         position = IIf(elem.positioning, elem.positioning.vocalPosition, "below")
        Set tmpRel = New RelativeElement
        Set tmpDic = New Dictionary
        tmpDic("typs") = "lyric"
        tmpDic("position") = position
        tmpDic("height") = lyricDim.height / spacing.Step
        tmpDic("dim") = Me.getTxtSize.attr("vocalfont", "lyric")
        tmpR.init lyricStr, 0, lyricDim.width, Nothing, tmpDic
        
        abselem.addCentered tmpRel
End Sub
'    /**
'         * stem presence: true for drawing stemless notehead
'         * 符幹存在：適用於繪製無符符頭
'         */
Public Function createNote(elem As VoiceABC, nostem As Boolean, isSingleLineStaff As Boolean, voice As VoiceElement) As AbsoluteElement
        Dim notehead As RelativeElement
        Dim roomTaken As Double
        Dim roomTakenRight As Double
        Dim symbolWidth As Double
        Dim additionalLedgers As iArray
        Dim dir As String
        Dim duration As Double
        Dim zeroDuration As Boolean
        Dim durlog As Double
        Dim dot As Integer
        Dim ret3
        
        Set notehead = Nothing
        roomTaken = 0  '' room needed to the left of the note
        roomTakenRight = 0  '' room needed to the right of the note
        symbolWidth = 0
        Set additionalLedgers = New iArray  '' PER: handle the case of [bc'], where the b doesn't have a ledger line

        duration = getDuration(elem)
        zeroDuration = False
        If (duration = 0) Then ''PER: zero duration will draw a quarter note head.
            zeroDuration = True
            duration = 0.25
            nostem = True
        End If
         durlog = Math.Floor(Log(duration) / Log(2))  ''TODO use getDurlog
         dot = 0

        '' 計算符點音符數量 dot
        Dim tot As Double
        Dim Inc As Double
        For tot = Math.Pow(2, durlog) To duration - 1
            Inc = tot / 2
            dot = dot + 1
            tot = tot + Inc
            Inc = Inc / 2
        Next


        If (elem.startTriplet <> 0) Then
            Me.tripletMultiplier = elem.tripletMultiplier
        End If

        Dim durationForSpacing As Double
        Dim abstyps As String
        Dim abselem As AbsoluteElement
        Dim ret1
        Dim ret2
        Dim rOpt As oRelativeOptions
        Dim tmpDic As Dictionary
        Dim tmpRelem As RelativeElement
        
        durationForSpacing = duration * Me.tripletMultiplier
        If Not (elem.rest Is Nothing) Then
            If (elem.rest.typs = "multimeasure") Then
                durationForSpacing = 1
            ElseIf (elem.rest.typs = "invisible-multimeasure") Then
                durationForSpacing = Me.measureLength * elem.rest.text
            End If
        End If
        
        abstyps = IIf(Not elem.rest Is Nothing, "rest", "note")
        
        Set tmpDic = New Dictionary
        tmpDic("durationClassOveride") = elem.duration * Me.tripletMultiplier
        Set abselem = N.AbsoluteElem(elem, durationForSpacing, 1, abstyps, Me.tuneNumber, tmpDic)
        If (hint = True) Then abselem.setHint

        If Not (elem.rest Is Nothing) Then
            If (Me.measureLength = duration And elem.rest.typs <> "invisible" And elem.rest.typs <> "spacer" And InStr(1, elem.rest.typs, "multimeasure") = 0) Then
                '' If the rest is exactly a measure, always use a whole rest
                '' 如果休止符恰好是一個度量，則始終使用整個休止符
                elem.rest.typs = "whole"  '' If the rest is exactly a measure, always use a whole rest
            End If
            Set ret1 = addRestToAbsElement(abselem, elem, duration, dot, voice.voicetotal > 1, Me.stemdir, isSingleLineStaff, durlog, Me.voiceScale)
            Set notehead = ret1.notehead
            roomTaken = ret1.roomTaken
            roomTakenRight = ret1.roomTakenRight
         Else
            '' 重要加入 音符
            Set ret2 = Me.addNoteToAbcElement(abselem, elem, dot, Me.stemdir, Me.style, zeroDuration, durlog, nostem, voice)
            If (ret2("min") <> 0) Then
                Me.minY = Math.min(ret2.min, Me.minY)
            End If
            Set notehead = ret2("noteHead")
            roomTaken = ret2("roomtaken")
            roomTakenRight = ret2("roomtakenright")
            Set additionalLedgers = ret2("additionalLedgers")
            dir = ret2("dir")
            symbolWidth = ret2("symbolWidth")
        End If

        If Not (elem.lyric Is Nothing) Then Me.addLyric abselem, elem
        

        If Not (elem.gracenotes Is Nothing) Then
            roomTaken = roomTaken + Me.addGraceNotes(elem, voice, abselem, notehead, Me.stemHeight * Me.voiceScale, Me.isBagpipes, roomTaken)
        End If
        '' 繪製裝飾
        If Not (elem.decoration Is Nothing) Then
            'line me.decoration.createDecoration(voice, elem.decoration, abselem.top, (notehead) ? notehead.w : 0, abselem, roomtaken, dir, abselem.bottom, elem.positioning, me.hasVocals)
        End If

        If (elem.barNumber <> 0) Then
            Set rOpt = New oRelativeOptions
            rOpt.typs = "barNumber"
            abselem.addFixed N.RelativeElem(elem.barNumber, -10, 0, 0, rOpt)
        End If

        '' ledger lines
        ledgerLines abselem, elem.minPitch, elem.maxPitch, Not (elem.rest Is Nothing), symbolWidth, additionalLedgers, dir, -2, 1

        If Not (elem.chord Is Nothing) Then
            Set ret3 = addChord(Me.gTextSize, abselem, elem, roomTaken, roomTakenRight, symbolWidth, Me.jazzchords, Me.germanAlphabet)
            roomTaken = ret3.roomTaken
            roomTakenRight = ret3.roomTakenRight
        End If

        '' 開始繪製圓滑線
        If (elem.startTriplet = True) Then
            'line me.triplet = new TripletElem(elem.startTriplet, notehead, { flatBeams: me.flatBeams })  '' above is opposite from case of slurs
        End If

        '' 結束圓滑線
        If (elem.endTriplet = True And Not Me.triplet Is Nothing) Then
            'line Me.triplet.setCloseAnchor (notehead)
        End If
        '' 結束圓滑線後加入
        If Not (Me.triplet Is Nothing) And Not elem.startTriplet And Not elem.endTriplet And Not (elem.rest Is Nothing) Then
            If (elem.rest.typs = "spacer") Then
                Me.triplet.middleNote notehead
            End If
        End If

        Set createNote = abselem
End Function

Public Sub addSlursAndTies(abselem As AbsoluteElement, pitchelem, notehead As RelativeElement, voice As VoiceElement, dir As String, isGrace As Boolean)
        Dim found As Boolean
        Dim i, j
        Dim voicenumber As Integer
        Dim tie As TieElem
        
        If (pitchelem.endTie) Then
            If (Me.ties.Count > 0) Then
                '' If there are multiple open ties, find the one that applies by matching the pitch, if possible.
                found = False
                For j = 0 To Me.ties.Count - 1
                    If Not (Me.ties(j).anchor1 Is Nothing) Then
                        If (Me.ties(j).anchor1.pitch = notehead.pitch) Then
                            Me.ties(j).setEndAnchor notehead
                            voice.setRange Me.ties(j)
                            Me.ties.Splice j, 1
                            found = True
                            Exit For
                        End If
                    End If
                Next
                If (Not found) Then
                    Me.ties(0).setEndAnchor notehead
                    voice.setRange Me.ties(0)
                    Me.ties.Splice 0, 1
                End If
            End If
        End If

         voicenumber = IIf(voice.voicetotal < 2, -1, voice.voicenumber)
        If Not (pitchelem.startTie Is Nothing) Then
            Dim tmpDic As Dictionary
            Set tie = New TieElem
            Set tmpDic = New Dictionary
            tmpDic("anchor1") = notehead
            tmpDic("force") = (Me.stemdir = "down" Or Me.stemdir = "up")
            tmpDic("stemDir") = Me.stemdir
            tmpDic("isGrace") = isGrace
            tmpDic("voiceNumber") = voicenumber
            tmpDic("style") = pitchelem.startTie.style
            
            tie.init tmpDic
            If (hint) Then tie.setHint

            Me.ties.Push tie
            voice.addOther tie
            '' HACK-PER: For the animation, we need to know if a note is tied to the next one, so here's a flag.
            '' Unfortunately, only some of the notes in the current event might be tied, but this will consider it
            '' tied if any one of them is. That will work for most cases.
            abselem.startTie = True
        End If

        Dim slur As TieElem
        Dim slurid As Integer
        
        If Not (pitchelem.endSlur Is Nothing) Then
            For i = 0 To pitchelem.endSlur.Count - 1
                slurid = pitchelem.endSlur(i)
                If Not (Me.slurs(slurid) Is Nothing) Then
                    Set slur = Me.slurs(slurid)
                    slur.setEndAnchor notehead
                    voice.setRange slur
                    Set Me.slurs(slurid) = Nothing
                 Else
                    Set slur = New TieElem
                    Set tmpDic = New Dictionary
                    tmpDic("anchor2") = notehead
                    tmpDic("stemDir") = Me.stemdir
                    tmpDic("voiceNumber") = voicenumber
                    
                    slur.init tmpDic
                    If (hint) Then slur.setHint
                    voice.addOther (slur)
                End If
                If Not (Me.startLimitElem Is Nothing) Then
                    slur.setStartX Me.startLimitElem
                End If
            Next
         ElseIf (Not isGrace) Then
'            Dim s
'            For Each s In Me.slurs
'
'                If Not s Is Nothing Then
'                'line 不知如何寫 'if (me.slurs.hasOwnProperty(s)) {
'                    Me.slurs(s).addInternalNote (notehead)
'                End If
'            Next
        End If

        If Not (pitchelem.startSlur Is Nothing) Then
            For i = 0 To pitchelem.startSlur.Count - 1
                slurid = pitchelem.startSlur(i).label
                Set slur = New TieElem
                
                Set slur = New TieElem
                Set tmpDic = New Dictionary
                tmpDic("anchor2") = notehead
                tmpDic("stemDir") = Me.stemdir
                tmpDic("voiceNumber") = voicenumber
                tmpDic("style") = pitchelem.startSlur(i).style
                
                slur.init tmpDic
                
              
                If (hint) Then slur.setHint
                Set Me.slurs(slurid) = slur
                voice.addOther (slur)
            Next
        End If
End Sub

Public Sub addMeasureNumber(Number As Integer, abselem As AbsoluteElement)
        Dim measureNumDim As size
        Dim dx  As Double
        Dim vert As Double
        Dim tmpR As New RelativeElement
        Dim tmpDic As New Dictionary
        measureNumDim = Me.getTxtSize.calc(Number, "measurefont", "bar-number")
        dx = 0
        If (abselem.isClef = True) Then '' If this is a clef rather than bar line, then the number shouldn't be centered because it could overlap the left side. This is an easy way to let it be centered but move it over, too.
            dx = dx + measureNumDim.width / 2
        End If
        vert = IIf(measureNumDim.width > 10 And abselem.abcelem.typs = "treble", 13, 11)
        tmpDic("typs") = "barNumber"
        tmpDic("dim") = Me.getTxtSize.attr("measurefont", "bar-number")
        Call tmpR.init(Number, dx, measureNumDim.width, vert + measureNumDim.height / spacing.Step, tmpDic)
        
        abselem.addFixed tmpR
End Sub

Public Function createBarLine(voice As VoiceElement, elem As VoiceABC, isFirstStaff As Boolean) As AbsoluteElement
        '' bar_thin, bar_thin_thick, bar_thin_thin, bar_thick_thin, bar_right_repeat, bar_left_repeat, bar_double_repeat
        Dim abselem As New AbsoluteElement
        Dim anchor As RelativeElement   '' place to attach part lines
        Dim anchor2 As RelativeElement
        Dim dx As Double
        Dim tmpDic As Dictionary
         dx = 0
         Call abselem.init(elem, 0, 10, "bar", Me.tuneNumber)
        If (elem.barNumber <> Empty) Then
            Call Me.addMeasureNumber(elem.barNumber, abselem)
        End If
        
        Dim firstdots As Boolean
        Dim firstthin As Boolean
        Dim thick As Boolean
        Dim secondthin As Boolean
        Dim seconddots As Boolean
        
         firstdots = (elem.typs = "bar_right_repeat" Or elem.typs = "bar_dbl_repeat")
         firstthin = (elem.typs <> "bar_left_repeat" And elem.typs <> "bar_thick_thin" And elem.typs <> "bar_invisible")
         thick = (elem.typs = "bar_right_repeat" Or elem.typs = "bar_dbl_repeat" Or elem.typs = "bar_left_repeat" Or _
            elem.typs = "bar_thin_thick" Or elem.typs = "bar_thick_thin")
         secondthin = (elem.typs = "bar_left_repeat" Or elem.typs = "bar_thick_thin" Or elem.typs = "bar_thin_thin" Or elem.typs = "bar_dbl_repeat")
         seconddots = (elem.typs = "bar_left_repeat" Or elem.typs = "bar_dbl_repeat")
        
        Dim slur
        '' limit positioning of slurs
        If (firstdots <> Empty Or seconddots <> Empty) Then
            For Each slur In Me.slurs
                If (Me.slurs.hasOwnProperty(slur)) Then
                    Me.slurs [slur].setEndX(abselem)
                End If
            Next
          Set Me.startLimitElem = abselem
        End If

        If (firstdots = True) Then
            anchor = New RelativeElement
            anchor2 = New RelativeElement
            Call anchor.init("dots.dot", dx, 1, 7)
            Call anchor2.init("dots.dot", dx, 1, 5)
            abselem.addRight anchor
            abselem.addRight anchor2
            dx = dx + 6 ''2 hardcoded, twice
        End If

        If (firstthin = True) Then
            anchor = New RelativeElement
            tmpDic = New Dictionary
            tmpDic("typs") = "bar"
            tmpDic("pitch2") = 10
            tmpDic("linewidth") = 0.6
            anchor.init Null, dx, 1, 2, tmpDic
            abselem.addRight anchor
        End If

        If (elem.typs = "bar_invisible") Then
            anchor = New RelativeElement
            tmpDic = New Dictionary
            tmpDic("typs") = "none"
            tmpDic("pitch2") = 10
            tmpDic("linewidth") = 0.6
            anchor.init Null, dx, 1, 2, tmpDic
            abselem.addRight (anchor)
        End If

        If (elem.decoration <> Empty) Then
            'line me.decoration.createDecoration(voice, elem.decoration, 12, (thick) ? 3 : 1, abselem, 0, "down", 2, elem.positioning, me.hasVocals)
        End If

        If (thick = True) Then
            dx = dx + 4 ''3 hardcoded
            anchor = New RelativeElement
            tmpDic = New Dictionary
            tmpDic("typs") = "bar"
            tmpDic("pitch2") = 10
            tmpDic("linewidth") = 4
            anchor.init Null, dx, 4, 2, tmpDic
            abselem.addRight anchor
            dx = dx + 5
        End If

        '' if (me.partstartelem && (thick || (firstthin && secondthin))) { '' means end of nth part
        '' me.partstartelem.anchor2=anchor
        '' me.partstartelem = null
        '' }

        If (Me.partstartelem <> Empty And elem.endEnding <> Empty) Then
            Me.partstartelem.anchor2 = anchor
            Me.partstartelem = Nothing
        End If

        If (secondthin = True) Then
            dx = dx + 3 ''3 hardcoded
            anchor = New RelativeElement
            tmpDic = New Dictionary
            tmpDic("typs") = "bar"
            tmpDic("pitch2") = 10
            tmpDic("linewidth") = 0.6
            anchor.init Nothing, dx, 1, 2, tmpDic
            abselem.addRight anchor '' 3 is hardcoded
        End If

        If (seconddots = True) Then
            dx = dx + 3 ''3 hardcoded
            anchor = New RelativeElement
            anchor2 = New RelativeElement
            Call anchor.init("dots.dot", dx, 1, 7)
            Call anchor2.init("dots.dot", dx, 1, 5)
            abselem.addRight anchor
            abselem.addRight anchor2
        End If '' 2 is hardcoded
        
'line
'        if (elem.startEnding && isFirstStaff) { '' only put the first & second ending marks on the first staff
'            var textWidth = me.GetTxtSize.calc(elem.startEnding, "repeatfont", '').width
'            abselem.minspacing += textWidth + 10  '' Give plenty of room for the ending number.
'            me.partstartelem = new EndingElem(elem.startEnding, anchor, null)
'            voice.addOther (Me.partstartelem)
'        }

        '' Add a little space to the left of the bar line so that nothing can crowd it.
        abselem.extraw = abselem.extraw - 5

        If Not (elem.chord Is Nothing) Then
          'line   var ret3 = addChord(Me.GetTxtSize, abselem, elem, 0, 0, 0, False, Me.germanAlphabet)
        End If

        Set createBarLine = abselem

End Function


'''''''''**************************************************** down function is private

Private Sub setAveragePitch(elem)
    Dim sum As Integer
    Dim p As Integer
    If Not (elem.pitches Is Nothing) Then
        For p = 0 To elem.pitches.Count - 1
            sortPitch elem
        Next
        sum = 0
        For p = 0 To elem.pitches.Count - 1
            sum = sum + elem.pitches(p).verticalPos
        Next
        elem.averagepitch = sum / elem.pitches.Count
        elem.minPitch = elem.pitches(0).verticalPos
        elem.maxPitch = elem.pitches(elem.pitches.Count - 1).verticalPos
    End If
End Sub
Public Sub sortPitch(elem)
    Dim sorted As Boolean
    Dim p As Integer
    Dim tmp As vpitchesNote
    Do
        sorted = True
        For p = 0 To elem.pitches.Count - 1
            If p + 1 >= elem.pitches.Count Then
                sorted = True
            ElseIf (elem.pitches(p).pitch > elem.pitches(p + 1).pitch) Then
                sorted = False
                Set tmp = elem.pitches(p)
                elem.pitches(p) = elem.pitches(p + 1)
                elem.pitches(p + 1) = tmp
            End If
        Next
    Loop While (Not (sorted))
End Sub

Public Sub ledgerLines(abselem As AbsoluteElement, minPitch As Double, maxPitch As Double, isRest As Boolean, _
    symbolWidth As Double, additionalLedgers, dir As String, dx As Double, scale_ As Double)
    Dim i As Double
    Dim ofs As Double
    Dim rOpt As oRelativeOptions
    For i = maxPitch To 11 Step -1
        If (i Mod 2 = 0 And Not isRest) Then
            Set rOpt = New oRelativeOptions
            rOpt.typs = "ledger"
            abselem.addFixed N.RelativeElem("", dx, (symbolWidth + 4) * scale_, i, rOpt)
        End If
    Next

    For i = minPitch To 1
        If (i Mod 2 = 0 And Not isRest) Then
            Set rOpt = New oRelativeOptions
            rOpt.typs = "ledger"
            abselem.addFixed N.RelativeElem("", dx, (symbolWidth + 4) * scale_, i, rOpt)
        End If
    Next

    For i = 0 To additionalLedgers.Count - 1 '' PER: draw additional ledgers
        ofs = symbolWidth
        If (dir = "down") Then ofs = -ofs
            Set rOpt = New oRelativeOptions
            rOpt.typs = "ledger"
        Dim ledger As Double
        ledger = additionalLedgers(i)
        abselem.addFixed N.RelativeElem("", ofs + dx, (symbolWidth + 4) * scale_, ledger, rOpt)
    Next
End Sub

'
'function addRestToAbsJianpuElement(abselem: AbsoluteElement, elem, duration: number, dot: number, isMultiVoice, stemdir:string, isSingleLineStaff, durlog, voiceScale) {
'    var c;
'    var restpitch = 7;
'    var noteHead: RelativeElement;
'    var roomTaken: number;
'    var roomTakenRight: number;
'
'    if (isMultiVoice) {
'        if (stemdir === "down") restpitch = 3;
'        if (stemdir === "up") restpitch = 11;
'    }
'    // There is special placement for the percussion staff. If there is one staff line, then move the rest position.
'    if (isSingleLineStaff) {
'        // The half and whole rests are attached to different lines normally, so we need to tweak their position to get them to both be attached to the same one.
'        if (duration < 0.5)
'            restpitch = 7;
'        else if (duration < 1)
'            restpitch = 7;  // half rest
'        Else
'            restpitch = 5; // whole rest
'    }
'    switch (elem.rest.type) {
'        Case "whole":
'            c = chartable.rest[0];
'            elem.averagepitch = restpitch;
'            elem.minpitch = restpitch;
'            elem.maxpitch = restpitch;
'            dot = 0;
'            break;
'        Case "rest":
'            if (elem.style === "rhythm") // special case for rhythm: rests are a handy way to express the rhythm.
'                c = chartable.rhythm[-durlog];
'            Else
'                c = chartable.rest[-durlog];
'            elem.averagepitch = restpitch;
'            elem.minpitch = restpitch;
'            elem.maxpitch = restpitch;
'            break;
'        Case "invisible":
'        Case "invisible-multimeasure":
'        Case "spacer":
'            c = "";
'            elem.averagepitch = restpitch;
'            elem.minpitch = restpitch;
'            elem.maxpitch = restpitch;
'            break;
'        Case "multimeasure":
'            c = chartable.rest['multi'];
'            elem.averagepitch = restpitch;
'            elem.minpitch = restpitch;
'            elem.maxpitch = restpitch;
'            dot = 0;
'            var mmWidth = glyphs.getSymbolWidth(c);
'            abselem.addHead(new RelativeElement(c, mmWidth, mmWidth * 2, 7));
'            var numMeasures = new RelativeElement("" + elem.rest.text, mmWidth, mmWidth, 16, { type: "multimeasure-text" });
'            abselem.addExtra(numMeasures);
'    }
'    if (elem.rest.type.indexOf("multimeasure") < 0 && elem.rest.type !== "invisible") {
'        var ret = createNoteHead(abselem, c, { verticalPos: restpitch },
'            { dot: dot, scale: voiceScale });
'        noteHead = ret.notehead;
'        if (noteHead) {
'            abselem.addHead(noteHead);
'            roomTaken = ret.accidentalshiftx;
'            roomTakenRight = ret.dotshiftx;
'        }
'    }
'    return { noteHead: noteHead, roomTaken: roomTaken, roomTakenRight: roomTakenRight };
'}

Public Function addRestToAbsElement(abselem As AbsoluteElement, elem, duration As Double, dot As Integer, isMultiVoice As Boolean, stemdir As String, isSingleLineStaff As Boolean, durlog, voiceScale) As Dictionary
    Dim c As String
    Dim restpitch As Integer
    Dim notehead As RelativeElement
    Dim roomTaken As Double
    Dim roomTakenRight As Double
    Dim mmWidth As Double
    Dim numMeasures As RelativeElement
    Dim rOpt As oRelativeOptions
    restpitch = 7

    If (isMultiVoice) Then
        If (stemdir = "down") Then restpitch = 3
        If (stemdir = "up") Then restpitch = 11
    End If
    '' There is special placement for the percussion staff. If there is one staff line, then move the rest position.
    If (isSingleLineStaff) Then
        '' The half and whole rests are attached to different lines normally, so we need to tweak their position to get them to both be attached to the same one.
        If (duration < 0.5) Then
            restpitch = 7
        ElseIf (duration < 1) Then
            restpitch = 7   '' half rest
        Else
            restpitch = 5  '' whole rest
        End If
    End If
    Select Case (elem.rest.typs)
        Case "whole":
            c = chartable.rest(0)
            elem.averagepitch = restpitch
            elem.minPitch = restpitch
            elem.maxPitch = restpitch
            dot = 0
        Case "rest":
            If (elem.style = "rhythm") Then '' special case for rhythm: rests are a handy way to express the rhythm.
                c = chartable.rhythm(-durlog)
            Else
                c = chartable.rest(-durlog)
            End If
            elem.averagepitch = restpitch
            elem.minPitch = restpitch
            elem.maxPitch = restpitch
        Case "invisible":
        Case "invisible-multimeasure":
        Case "spacer":
            c = ""
            elem.averagepitch = restpitch
            elem.minPitch = restpitch
            elem.maxPitch = restpitch
        Case "multimeasure":
            c = chartable.rest("multi")
            elem.averagepitch = restpitch
            elem.minPitch = restpitch
            elem.maxPitch = restpitch
            dot = 0
            mmWidth = glyphs.getSymbolWidth(c)
            abselem.addHead N.RelativeElem(c, mmWidth, mmWidth * 2, 7)
            Set rOpt = New oRelativeOptions
            rOpt.typs = "multimeasure-text"
            Set numMeasures = N.RelativeElem("" + elem.rest.text, mmWidth, mmWidth, 16, rOpt)
            abselem.addExtra numMeasures
    End Select
    If (InStr(1, elem.rest.typs, "multimeasure") < 0 And elem.rest.typs <> "invisible") Then
        Dim ret As Dictionary
        Dim noteOpt As New oNoteHeadOptions
        Dim pitchOpt As New vpitchesNote
        pitchOpt.verticalPos = restpitch
        noteOpt.dot = dot
        noteOpt.scale_ = voiceScale
        Set ret = createNoteHead(abselem, c, pitchOpt, noteOpt)
        notehead = ret.notehead
        If Not (notehead Is Nothing) Then
            abselem.addHead (notehead)
            roomTaken = ret.accidentalshiftx
            roomTakenRight = ret.dotshiftx
        End If
    End If
    Dim outret As New Dictionary
    outret("noteHead") = notehead
    outret("roomTaken") = roomTaken
    outret("roomTakenRight") = roomTakenRight
    Set addRestToAbsElement = outret
    
End Function

Public Sub addIfNotExist(arr, item)
    Dim i As Integer
    For i = 0 To UBound(arr) - 1
        'line 不知要如何改 if (JSON.stringify(arr(i)) === JSON.stringify(item))             Return
    Next
    arr.Push (item)
End Sub

Attribute VB_Name = "AttribCode"
Option Explicit

Function ACAD_Ver() As Integer
'傳回AutoCAD 的版本號碼
    ' This example returns AutoCAD version as a string
    
    Dim version As String
    version = ThisDrawing.Application.version
    ACAD_Ver = val(version)
    
End Function
Function GetAttribTextString(entAttrib As AcadEntity, title As String) As String
'找 屬性(titile)的文字
    Dim Array1 As Variant
    Dim Pnt As Variant
    'Dim entObj As AcadEntity
    Dim Count As Integer
        With entAttrib
            '當一個塊引用表行被找到後，檢查它是否有屬性
            If StrComp(.EntityName, "AcDbBlockReference", 1) = 0 Then
                '如果有屬性
                If .HasAttributes = True Then
                    '提取塊引用中的屬性
                    Array1 = .GetAttributes
                    '這一輪迴圈用來查找標題，如果有填在第1行
                    For Count = LBound(Array1) To UBound(Array1)
                        '如果還沒有標題
                        If Array1(Count).TagString = title Then
                            GetAttribTextString = Array1(Count).textString
                            Exit Function
                        End If
                    Next Count
                    'MsgBox """" & title & """屬性未找到"
                End If
            End If
        End With
End Function

Function SetAttribTextString(entAttrib As AcadEntity, title As String, sval As String) As String
'設定 屬性(titile)的文字
    Dim Array1 As Variant
    Dim Pnt As Variant
    'Dim entObj As AcadEntity
    Dim Count As Integer
        With entAttrib
            '當一個塊引用表行被找到後，檢查它是否有屬性
            If StrComp(.EntityName, "AcDbBlockReference", 1) = 0 Then
                '如果有屬性
                If .HasAttributes = True Then
                    '提取塊引用中的屬性
                    Array1 = .GetAttributes
                    '這一輪迴圈用來查找標題，如果有填在第1行
                    For Count = LBound(Array1) To UBound(Array1)
                        '如果還沒有標題
                        If Array1(Count).TagString = title Then
                            Array1(Count).textString = sval
                            Exit Function
                        End If
                    Next Count
                    'MsgBox """" & title & """屬性未找到"
                    SetAttribTextString = ""
                End If
            Else
                'MsgBox "這不是屬性圖元"
                SetAttribTextString = ""
            End If
        End With
End Function

Function SetTowAttrib(entAttrib As AcadEntity, towAttrib As AcadEntity) As String
'設定 屬性(titile)的文字
    Dim Array1 As Variant
    Dim Pnt As Variant
    Dim title As String
    Dim sval As String
    'Dim entObj As AcadEntity
    Dim Count As Integer
        With entAttrib
            '當一個塊引用表行被找到後，檢查它是否有屬性
            If StrComp(.EntityName, "AcDbBlockReference", 1) = 0 Then
                '如果有屬性
                If .HasAttributes = True Then
                    '提取塊引用中的屬性
                    Array1 = .GetAttributes
                    '這一輪迴圈用來查找標題，如果有填在第1行
                    For Count = LBound(Array1) To UBound(Array1)
                       
                        title = Array1(Count).TagString
                        sval = Array1(Count).textString
                        
                        Call SetAttribTextString(towAttrib, title, sval)
                        
                    Next Count
                    
                    
                End If
            Else
                'MsgBox "這不是屬性圖元"
            End If
        End With
End Function

Function GetAttribList(entAttrib As AcadEntity) As String
'取得 屬性列表
    Dim Array1 As Variant
    Dim Pnt As Variant
    Dim strList As String
    Dim Count As Integer
    strList = ""
        With entAttrib
            '當一個塊引用表行被找到後，檢查它是否有屬性
            If StrComp(.EntityName, "AcDbBlockReference", 1) = 0 Then
                '如果有屬性
                If .HasAttributes = True Then
                    '提取塊引用中的屬性
                    Array1 = .GetAttributes
                    '這一輪迴圈用來查找標題，如果有填在第1行
                    For Count = LBound(Array1) To UBound(Array1)
                        strList = strList & Array1(Count).TagString & vbCrLf
                    Next Count
                    GetAttribList = strList
                    Exit Function
                End If
            End If
        End With
End Function

Attribute VB_Name = "BeamElem"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public typs As String
Public duration As Double
Public isflat As Boolean
Public isGrace As Boolean
Public forceup As Boolean
Public forcedown As Boolean
Public elems As AbsoluteElementList
Public total As Double
Public average As Double
Public allrests As Boolean
Public stemHeight As Double
Public beams As vbeamRangeList    'BeamRange[]
Public stemsUp As Boolean
Public min As Double
Public max As Double

Public hint As Boolean
Public Count As Double
Public mainNote As AbsoluteElement
Public Sub init(stemHeight As Double, typs As String, flat, Optional firstElement As VoiceABC = Nothing)
        '' type is "grace", "up", "down", or undefined. flat is used to force flat beams, as it commonly found in the grace notes of bagpipe music.
        Me.typs = "BeamElem"
        Me.isflat = IIf(flat, True, False)
        Me.isGrace = IIf(typs = "grace", True, False)
        Me.forceup = IIf(Me.isGrace = True Or (typs = "up"), True, False)
        Me.forcedown = IIf(typs = "down", True, False)
        Set Me.elems = New AbsoluteElementList '' all the AbsoluteElements that this beam touches. It may include embedded rests.
        Me.total = 0
        Me.average = 6  '' use middle line as start for average.
        Me.allrests = True
        Me.stemHeight = stemHeight
        Set Me.beams = New vbeamRangeList   '' During the layout phase, this will become a list of the beams that need to be drawn.
        If Not (firstElement Is Nothing) Then
            If firstElement.duration > 0 Then
                Me.duration = firstElement.duration
                If (firstElement.startTriplet = True) Then
                    Me.duration = Me.duration * firstElement.tripletMultiplier
                End If
                Me.duration = CInt(Me.duration * 1000) / 1000
            End If
        Else
            Me.duration = 0
        End If
End Sub

Public Sub setHint()
        Me.hint = True
End Sub

Public Sub runningDirection(abcelem As VoiceABC)
        Dim pitch As Double
        pitch = abcelem.averagepitch
        If (pitch = 0) Then Exit Sub '' don't include elements like spacers in beams
        Me.total = CInt(Me.total + pitch)

        Me.Count = Me.Count + 1
End Sub

Public Sub Add(abselem)
        Dim pitch As Double
        pitch = abselem.abcelem.averagepitch
        If (pitch = 0) Then Exit Sub  '' don't include elements like spacers in beams
        If Not (abselem.abcelem Is Nothing) Then
            If Not (abselem.abcelem.rest Is Nothing) Then
                Me.allrests = False
            End If
        End If
        Set abselem.Beam = Me
        Me.elems.Push abselem
        Me.total = CInt(Me.total + pitch)
        If (abselem.abcelem.minPitch < Me.min) Then Me.min = abselem.abcelem.minPitch
        
        If (abselem.abcelem.maxPitch > Me.max) Then Me.max = abselem.abcelem.maxPitch
        
End Sub

Public Sub addBeam(Beam As vbeamRange)
        Me.beams.Push Beam
End Sub

Public Sub setStemDirection()
        '' Have to figure this out before the notes are placed because placing the notes also places the decorations.
        Me.average = calcAverage(Me.total, Me.Count)
        If (Me.forceup = True) Then
            Me.stemsUp = True
        ElseIf (Me.forcedown = True) Then
            Me.stemsUp = False
        Else
            'var middleLine = 6  '' hardcoded 6 is B
            Me.stemsUp = Me.average < 6  '' true is up, false is down
        End If
        Me.Count = 0
        Me.total = 0
End Sub

Public Sub calcDir()

        Me.average = calcAverage(Me.total, Me.elems.Count)
        If (Me.forceup = True) Then
            Me.stemsUp = True
         ElseIf (Me.forcedown = True) Then
            Me.stemsUp = False
         Else
            'var middleLine = 6  '' hardcoded 6 is B
            Me.stemsUp = Me.average < 6  '' true is up, false is down
        End If
        Dim dir As String
        Dim i As Integer, j As Integer
        dir = IIf(Me.stemsUp = True, "up", "down")
        For i = 0 To Me.elems.Count - 1
            For j = 0 To Me.elems(i).heads.Count - 1
                Me.elems(i).heads(j).stemdir = dir
            Next
        Next
    
End Sub
Private Function calcAverage(total As Double, numElements As Double) As Double
    If (numElements = 0) Then calcAverage = 0
    calcAverage = total / numElements
End Function


Public Function clone() As BeamElem
    Dim cope As New BeamElem
    cope.typs = Me.typs
    cope.duration = Me.duration
    cope.isflat = Me.isflat
    cope.isGrace = Me.isGrace
    cope.forceup = Me.forceup
    cope.forcedown = Me.forcedown
Set cope.elems = Me.elems
    cope.total = Me.total
    cope.average = Me.average
    cope.allrests = Me.allrests
    cope.stemHeight = Me.stemHeight
Set cope.beams = Me.beams
    cope.stemsUp = Me.stemsUp
    cope.min = Me.min
    cope.max = Me.max
    
    cope.hint = Me.hint
    cope.Count = Me.Count
Set cope.mainNote = Me.mainNote
    Set clone = cope
End Function

Attribute VB_Name = "BeamElemList"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
'MIT License
'
'Copyright (c) 2019-2021 Petr Katerinak
'
'Permission is hereby granted, free of charge, to any person obtaining a copy
'of this software and associated documentation files (the "Software"), to deal
'in the Software without restriction, including without limitation the rights
'to use, copy, modify, merge, publish, distribute, sublicense, and/or sell
'copies of the Software, and to permit persons to whom the Software is
'furnished to do so, subject to the following conditions:
'
'The above copyright notice and this permission notice shall be included in all
'copies or substantial portions of the Software.
'
'THE SOFTWARE IS PROVIDED "AS IS", WITHOUT WARRANTY OF ANY KIND, EXPRESS OR
'IMPLIED, INCLUDING BUT NOT LIMITED TO THE WARRANTIES OF MERCHANTABILITY,
'FITNESS FOR A PARTICULAR PURPOSE AND NONINFRINGEMENT. IN NO EVENT SHALL THE
'AUTHORS OR COPYRIGHT HOLDERS BE LIABLE FOR ANY CLAIM, DAMAGES OR OTHER
'LIABILITY, WHETHER IN AN ACTION OF CONTRACT, TORT OR OTHERWISE, ARISING FROM,
'OUT OF OR IN CONNECTION WITH THE SOFTWARE OR THE USE OR OTHER DEALINGS IN THE
'SOFTWARE.
'
' Version of iArray: 1.0
''修正 元素從 0 開始

Private mainArray As New Collection
Private i As Long ' Counter

' #####################
' #    CONSTRUCTOR    #
' #####################
'Private Sub Class_Initialize()
'  Set mainArray = New Collection
'End Sub

' #####################
' #  Getter / Setter  #
' #####################
'Attribute Element.VB_UserMemId = 0 saved in both procedures

'@DefaultMember
Public Property Get element(ByVal index As Long) As BeamElem
Attribute element.VB_UserMemId = 0
    If index + 1 < 1 Or index + 1 > mainArray.Count Then
        Set element = Nothing
        Exit Property
    End If
    If IsObject(mainArray(index + 1)) = True Then
        Set element = mainArray(index + 1)
    Else
        element = mainArray(index + 1)
    End If

 
End Property

'@DefaultMember
Public Property Let element(ByVal index As Long, ByVal val As BeamElem)
Attribute element.VB_UserMemId = 0
  If index = 0 And mainArray.Count = 0 Then
    Me.Push val
    Exit Property
  End If
  If index + 1 > mainArray.Count Then
    Dim eMsg As String
    eMsg = IIf(mainArray.Count > 0, _
               "Index (" & index + 1 & ") out of iArray bounds (1-" & mainArray.Count & ")", _
               "iArray doesn't have any indexes")
    err.Raise Number:=9, Description:=eMsg
    Exit Property
  End If
  mainArray.Add val, after:=index + 1
  mainArray.Remove index + 1
End Property

' #############################
' # COMMON COLLECTION METHODS #
' #############################
Public Function Count() As Long
  Count = mainArray.Count
End Function
Public Sub Add(ByVal val As BeamElem, Optional ByVal bef As Variant = Empty, Optional ByVal aft As Variant = Empty)
  If IsEmpty(bef) And IsEmpty(aft) Then
    mainArray.Add val
  ElseIf IsEmpty(bef) Then
    mainArray.Add val, , , aft
  ElseIf IsEmpty(aft) Then
    mainArray.Add val, , bef
  Else
    mainArray.Add val, , bef, aft
  End If
End Sub
Public Sub Remove(index As Long)
  mainArray.Remove index + 1
End Sub

' ####################
' #  PUBLIC METHODS  #
' ####################

'AddAfter
' Adds element after given index.
' {1,2,3} -> index >= 3 -> Push val
' {1,2,3} -> index < 1 -> Unshift val
' {} -> index = any -> Push val
' @param Long index | Index after which will be added an element
' @param Variant val | One element (String, number, ...) to add into iArray
' @return Long | Count of elements inside iArray
Public Function AddAfter(ByVal index As Long, ByVal val As BeamElem) As Long
  If Me.Count < 1 Or index + 1 >= Me.Count Then
    Me.Push val
  ElseIf index + 1 < 1 Then
    Me.Unshift val
  Else
    Me.Add val, aft:=index + 1
  End If
  AddAfter = Me.Count
End Function

'AddArrayAfter
' Adds elements after given index.
' {1,2,3} -> index >= 3 -> PushArray val
' {1,2,3} -> index < 1 -> UnshiftArray val
' {} -> index = any -> PushArray val
' @param Long index | Index after which will be added an element
' @param Variant val | Array() or iArray of elements to add into iArray
' @return Long | Count of elements inside iArray
Public Function AddArrayAfter(ByVal index As Long, ByVal val As Variant) As Long
  If Me.Count < 1 Or index + 1 >= Me.Count Then
    Me.PushArray val
  ElseIf index + 1 < 1 Then
    Me.UnshiftArray val
  Else
    If TypeOf val Is BeamElemList Then
      For i = 0 To val.Count - 1
        Me.Add val(i), aft:=index + 1
        Inc index
      Next i
    Else
      For i = LBound(val) To UBound(val)
        Me.Add val(i), aft:=index + 1
        Inc index
      Next i
    End If
  End If
  AddArrayAfter = Me.Count
End Function

'AddArrayBefore
' Adds elements before given index.
' {1,2,3} -> index > 3 -> PushArray val
' {1,2,3} -> index <= 1 -> UnshiftArray val
' {} -> index = any -> PushArray val
' @param Long index | Index after which will be added an element
' @param Variant val | Array() or iArray of elements to add into iArray
' @return Long | Count of elements inside iArray
Public Function AddArrayBefore(ByVal index As Long, ByVal val As Variant) As Long
  If Me.Count < 1 Or index + 1 > Me.Count Then
    Me.PushArray val
  ElseIf index <= 0 Then
    Me.UnshiftArray val
  Else
    If TypeOf val Is BeamElemList Then
      For i = val.Count - 1 To 0 Step -1
        Me.Add val(i), bef:=index + 1
      Next i
    Else
      For i = UBound(val) To LBound(val) Step -1
        Me.Add val(i), bef:=index + 1
      Next i
    End If
  End If
  AddArrayBefore = Me.Count
End Function

'AddBefore
' Adds element before given index.
' {1,2,3} -> index > 3 -> Push val
' {1,2,3} -> index <= 1 -> Unshift val
' {} -> index = any -> Push val
' @param Long index | Index before which will be added an element
' @param Variant val | One element (String, number, ...) to add into iArray
' @return Long | Count of elements inside iArray
Public Function AddBefore(ByVal index As Long, ByVal val As BeamElem) As Long
  If Me.Count < 1 Or index + 1 > Me.Count Then
    Me.Push val
  ElseIf index + 1 <= 1 Then
    Me.Unshift val
  Else
    Me.Add val, bef:=index + 1
  End If
  AddBefore = Me.Count
End Function

'Avg
' Calculates the average of the numeric mainArray.
' @return Variant | Average value / "NaN" if iArray contains non-numeric value(s)
Public Function Avg() As Variant
  If Not Me.ContainsOnlyNumeric Then Avg = "NaN": Exit Function
  Avg = Me.sum / Me.Count
End Function

'Clear
' Empties iArray
Public Function Clear() As Boolean
  For i = mainArray.Count - 1 To 0 Step -1
    mainArray.Remove i + 1
  Next i
  Clear = IIf(mainArray.Count = 0, True, False)
End Function

'Clone
' Makes a hard copy of the mainArray
' @return mainArray | Return exact copy of itself
Public Function clone() As BeamElemList
  Set clone = New BeamElemList
  For i = 0 To Me.Count - 1
    clone.Push Me(i)
  Next i
End Function

'Contains
' Checks if given value is used inside mainArray.
' @param Variant val | One element (String, number, ...) to by checked if it exists in iArray
' $return Boolean | True = exists, False = doesn't exists
Public Function Contains(ByVal val As BeamElem) As Boolean
  Contains = False
  Dim el As Variant
  For Each el In mainArray
    If IsObject(val) = True Or VarType(val) And 8192 Then
        If (VarType(el) And 8192) And (VarType(val) And 8192) Then
            If ArrayDifference(el, val) Then
                Contains = True: Exit Function
            End If
        ElseIf IsObject(el) = True And IsObject(val) = True Then
            If el Is val Then
                Contains = True: Exit Function
            End If
        End If
    Else
        If IsObject(el) = False And (VarType(el) And 8192) <> 8192 Then
            If el = val Then
            Contains = True: Exit Function
            End If
        End If
    End If
  Next el
End Function

'ContainsAll
' Checks if all given values are used inside mainArray.
' @param Variant val | values to by checked if it exists in iArray
' $return Boolean | True = all exists, False = one ore more values doesn't exists
Public Function ContainsAll(ByVal val As BeamElemList) As Boolean
  ContainsAll = False
  Dim foundOccurrences As Integer: foundOccurrences = 0
  Dim values As New BeamElemList
  If Not TypeOf val Is BeamElemList Then
    If IsArray(val) Then
      values.PushArray (val)
    Else
      values.Push (val)
    End If
  Else
    Set values = val
  End If
  For i = 0 To values.Count - 1
    If Me.Contains(values(i)) Then Inc foundOccurrences
  Next i
  If foundOccurrences = values.Count Then ContainsAll = True
End Function

'CountOccurrences
' Checks how many times is given value used inside mainArray.
' @param Variant val | One element (String, number, ...) to by checked
' @return Long | Count of matched occurrences
Public Function CountOccurrences(val As Variant) As Long
  CountOccurrences = 0
  Dim el As Variant
  For Each el In mainArray
  
    If IsObject(val) = True Or VarType(val) And 8192 Then
        If VarType(el) And 8192 And VarType(val) And 8192 Then
            If ArrayDifference(el, val) Then
                Inc CountOccurrences
                Exit Function
            End If
        ElseIf IsObject(el) = True And IsObject(val) = True Then
            If el Is val Then
                Inc CountOccurrences
                Exit Function
            End If
        End If
    Else
        If IsObject(el) = False And Not (VarType(el) And 8192) Then
            If el = val Then
                Inc CountOccurrences
                Exit Function
            End If
        End If
    End If
  
     'If el = val Then Inc CountOccurrences
  Next el
End Function

'Dequeue
' Removes an element from the begining of the mainArray.
' @return Variant | Removed element or Empty, if iArray is empty
'刪除開頭一個元素。
Public Function Dequeue() As BeamElem
  Dequeue = Empty
  If mainArray.Count > 0 Then
    If VarType(Me(0)) = vbString Then
        Dequeue = Me(0)
    ElseIf TypeOf Me(0) Is BeamElemList Then
        Set Dequeue = Me(0)
    ElseIf VarType(Me(0)) = vbArray Then
        Set Dequeue = Me(0)
    ElseIf VarType(Me(0)) = vbObject Then
        Set Dequeue = Me(0)
    Else
        Dequeue = Me(0)
    End If
    
    mainArray.Remove 1
  End If
End Function

'Difference
' Checks for number of differences between two arrays, what was added/deleted or combination.
' @param iArray oldArray | Old iArray to be compared with current iArray
' @param String retType | �dd= deleted from old iArray, �aa= added in current iArray, �cc= combination of both (default)
' @return iArray | iArray with differences found
Public Function Difference(ByRef oldArray As BeamElemList, Optional ByVal retType As String = "c") As BeamElemList
  Set Difference = New BeamElemList
  Select Case LCase(retType)
    Case "d"
      For i = 0 To oldArray.Count - 1
        If Me.Contains(oldArray(i)) = False Then Difference.Push oldArray(i)
      Next i
    Case "a"
      For i = 0 To Count - 1
        If oldArray.Contains(Me(i)) = False Then Difference.Push Me(i)
      Next i
    Case "c"
      For i = 0 To oldArray.Count - 1
        If Me.Contains(oldArray(i)) = False Then Difference.Push oldArray(i)
      Next i
      For i = 0 To Count - 1
        If oldArray.Contains(Me(i)) = False Then Difference.Push Me(i)
      Next i
    Case Else
      err.Raise Number:=5, Description:="Unknown Difference return type attribute:" & vbCrLf & _
                                        "Allowed are 'A'dded/'D'eleted/'C'ombination of both"
  End Select
End Function

'DropLeft
' Remove n elements from the beginning of the mainArray. If n > count of iArray elements, all elements are removed.
' @param Long n | Number of elements to be removed
' @return iArray | Array of the removed elements
Public Function DropLeft(ByRef N As Long) As BeamElemList
  Set DropLeft = New BeamElemList
  If N > Me.Count Then N = Me.Count
  For i = 0 To N - 1
    DropLeft.Push Me(i)
  Next i
  For i = N - 1 To 0 Step -1
    Me.Remove (i)
  Next i
End Function

'DropRight
' Remove n elements from the end of the mainArray. If n > count of iArray elements, all elements are removed.
' @param Long n | Number of elements to be removed
' @return iArray | Array of the removed elements
Public Function DropRight(ByRef N As Long) As BeamElemList
  Set DropRight = New BeamElemList
  If N > Me.Count Then N = Me.Count
  For i = Me.Count - N To Me.Count - 1
    DropRight.Push Me(i)
  Next i
  For i = Me.Count - 1 To Me.Count - N Step -1
    Me.Remove (i)
  Next i
End Function

'Enqueue
' Adds an element at the end of the mainArray.
' @param Variant val | One element (String, number, ...) to add into iArray
' @return Long | Count of elements inside iArray
Public Function Enqueue(ByVal val As Variant) As Long
  Enqueue = Push(val)
End Function

'EnqueueArray
' Adds elements at the end of the iArray
' @param Variant val | Array() or iArray of elements to add into iArray
' @return Long | Count of elements inside array
Public Function EnqueueArray(ByVal val As Variant) As Long
  EnqueueArray = PushArray(val)
End Function

'First
' Returns value of the first element of the mainArray.
' @return Variant | Value of the first element or Empty if iArray is Empty
Public Function First() As BeamElem
  Set First = IIf(Me.Count > 0, Me(0), Empty)
End Function

'Head
' Returns all elements of iArray, except last one.
' @return iArray | Copy of original array, without last element
Public Function head() As BeamElemList
  Set head = Me.clone
  head.Pop
End Function

'Intersect
' Search for element that exists in both iArrays.
' @param iArray intArray | iArray to be intersected with current iArray
' @return iArray | Intersected values
Public Function Intersect(ByRef intersectedArr As BeamElemList) As BeamElemList
  Set Intersect = New BeamElemList
  Dim el As Variant
  For Each el In mainArray
    If intersectedArr.Contains(el) Then
      If Not Intersect.Contains(el) Then Intersect.Push (el)
    End If
  Next el
End Function

'ContainsOnlyNumeric
' Verify that all elements are numbers or convertable to numbers
' $return Boolean | True = contains only numeric values, False = contains inconvertible values
Public Function ContainsOnlyNumeric() As Boolean
  ContainsOnlyNumeric = True
  Dim el As Variant
  For Each el In mainArray
    If Not IsNumeric(el) Then ContainsOnlyNumeric = False: Exit Function
  Next el
End Function

'Join
' Joins two iArrays.
' @param iArray jArray | iArray to be joined with current iArray
' @return iArray | Joined iArray
Public Function Join(ByRef joinArr As BeamElemList) As BeamElemList
  Set Join = New BeamElemList
  Join.PushArray Me
  Join.PushArray joinArr
End Function

'Last
' Returns value of the last element of the mainArray.
' @return Variant | Value of the last element or Empty if iArray is Empty
Public Function Last() As BeamElem
  Set Last = IIf(Me.Count > 0, Me(Me.Count - 1), Empty)
End Function

'OccurrenceIndexes
' Returns all indexes of a value in mainArray.
' @return iArray | iArray containing indexes of occurrence
Public Function OccurenceIndexes(val As Variant) As BeamElemList
  Set OccurenceIndexes = New BeamElemList
  For i = 0 To Me.Count - 1
    If Me(i) = val Then
        OccurenceIndexes.Push (i)
    End If
  Next i
End Function

'Pop
' Removes an element from the end of the mainArray.
' @return Variant | Removed element or Empty, if iArray is empty
Public Function Pop() As BeamElem
  If mainArray.Count > 0 Then
    If VarType(Me(mainArray.Count - 1)) = vbObject Then
       Set Pop = Me(mainArray.Count - 1)
    Else
        Pop = Me(mainArray.Count - 1)
    End If
    mainArray.Remove mainArray.Count
  End If
End Function
  
  

'Push
' Adds an element at the end of the mainArray.
' @param Variant val | One element (String, number, ...) to add into iArray
' @return Long | Count of elements inside iArray
Public Function Push(ByVal val As BeamElem) As Long
  mainArray.Add val
  Push = mainArray.Count
End Function

'PushArray
' Adds elements at the end of the mainArray.
' @param Variant val | Array() or iArray of elements to add into iArray
' @return Long | Count of elements inside array
Public Function PushArray(ByVal val As Variant) As Long
  If TypeOf val Is BeamElemList Then
    For i = 0 To val.Count - 1
      Me.Push val(i)
    Next i
  Else
    For i = LBound(val) To UBound(val)
      Me.Push val(i)
    Next i
  End If
  PushArray = Me.Count
End Function

'RemoveDuplicates
' Keeps only the first occurrence of the value. Affects original array
' @return Long | Count of the removed elements
Public Function RemoveDuplicates() As Long
  RemoveDuplicates = 0
  For i = Me.Count - 1 To 0 Step -1
    If Me.CountOccurrences(Me(i)) > 1 Then
      Me.Remove i
      Inc RemoveDuplicates
    End If
  Next i
End Function

'Reverse
' Reverses the content of the iArray
' @return iArray | Reversed iArray
Public Function Reverse() As BeamElemList
  Set Reverse = New BeamElemList
  For i = 0 To Me.Count - 1
    Reverse.Unshift Me(i)
  Next i
End Function

'Shift
' Removes an element from the begining of the mainArray.
' @return Variant | Removed element or Empty, if iArray is empty
'轉移
' 從 iArray 的開頭刪除一個元素。
' @返回第一個元素 | 如果 iArray 為空，則刪除元素或為空
Public Function shift() As BeamElem
  shift = Empty
  If mainArray.Count > 0 Then
    If VarType(Me(0)) = vbString Then
        shift = Me(0)
    ElseIf TypeOf Me(0) Is BeamElemList Then
        Set shift = Me(0)
    ElseIf VarType(Me(0)) = vbArray Then
        Set shift = Me(0)
    ElseIf VarType(Me(0)) = vbObject Then
        Set shift = Me(0)
    Else
        shift = Me(0)
    End If
    
    mainArray.Remove 1
  End If
End Function

'Shuffle
' Randomly mixes content of the iArray
' @return iArray | Shuffled iArray
' 隨機播放
' 隨機混合 iArray 的內容
'@return iArray | 打亂iArray
Public Function Shuffle() As BeamElemList
  Set Shuffle = New BeamElemList
  Dim keys As New BeamElemList
  For i = 0 To Me.Count - 1
    keys.Push (i)
  Next i
  Dim rndNo As Long
  Do While keys.Count > 0
    rndNo = randomFromTo(0, keys.Count - 1)
    Shuffle.Push Me(keys(rndNo))
    keys.Remove (rndNo)
  Loop
End Function

'Sum
' Calculates the sum of the numeric mainArray.
' @return Variant | Sum value / "NaN" if iArray contains non-numeric value(s)
Public Function sum() As Variant
  If Not Me.ContainsOnlyNumeric Then sum = "NaN": Exit Function
  sum = 0
  Dim el As Variant
  For Each el In mainArray
    sum = sum + el
  Next el
End Function

'Tail
' Returns all elements of iArray, except first one.
' @return iArray | Copy of original array, without first element
'返回陣列中除了第一個元素的剩余元素陣列
Public Function Tail() As BeamElemList
  Set Tail = Me.clone
  Tail.Dequeue
End Function

Public Function ToList()
  If Me.Count = 0 Then ToList = Null: Exit Function
  Dim tarr()
  ReDim tarr(Me.Count - 1)
  For i = 0 To Me.Count - 1
    If VarType(Me(i)) = vbString Then
        tarr(i) = Me(i)
    ElseIf TypeOf Me(i) Is BeamElemList Then
        Set tarr(i) = Me(i)
    ElseIf VarType(Me(i)) = vbObject Then
        Set tarr(i) = Me(i)
    Else
        tarr(i) = Me(i)
    End If
  Next i
  ToList = tarr
End Function

'ToString
' Creates string representation of the mainArray.
' @param String delimiter | Optional character to separate the iArray's elements (default = " ")
' @return String | Formated representation of tha iArray
Public Function ToString(Optional ByVal delimiter As String = " ") As String
  If Me.Count = 0 Then ToString = "{}": Exit Function
  ToString = vbNullString
  For i = 0 To Me.Count - 1
    If i = 0 Then ToString = ToString + "{"
    If i > 0 Then ToString = ToString + delimiter
    If VarType(Me(i)) = vbString Then
        ToString = ToString + Chr$(34)
        ToString = ToString + CStr(Me(i))
        ToString = ToString + Chr$(34)
    ElseIf TypeOf Me(i) Is BeamElemList Then
        ToString = ToString + Me(i).ToString(delimiter)
    ElseIf (VarType(Me(i)) And vbArray) = vbArray Then
        ToString = ToString + "[Array]"
    ElseIf VarType(Me(i)) = vbObject Then
        ToString = ToString + "[Object]"
    Else
        ToString = ToString + CStr(Me(i))
    End If
    
    If i = mainArray.Count - 1 Then ToString = ToString + "}"
  Next i
End Function

'Union
' Combines both iArrays and removes duplicities
' @param iArray uArray | iArray to be unioned with current iArray
' @return iArray | Combined values without duplicities
Public Function Union(ByRef uArr As BeamElemList) As BeamElemList
  Set Union = Me.clone
  Union.PushArray uArr
  Union.RemoveDuplicates
End Function

'Unique
' Returns copy of iArray without duplicated values. Original array is not affected
' @return iArray | iArray with unique values
Public Function Unique() As BeamElemList
  Set Unique = New BeamElemList
  Dim el As Variant
  For Each el In mainArray
    If Not Unique.Contains(el) Then Unique.Push (el)
  Next el
End Function

'Unshift
' Add an element at the begining of the mainArray.
' @param Variant val | One element (String, number, ...) to add into iArray
' @return Long | Count of elements inside iArray
Public Function Unshift(ByVal val As Variant) As Long
  If mainArray.Count = 0 Then
    Unshift = Push(val)
  Else
    mainArray.Add val, before:=1
    Unshift = mainArray.Count
  End If
End Function

'UnshiftArray
' Add elements at the begining of the mainArray.
' @param Variant val | Array() or iArray of elements to add into iArray
' @return Long | Count of elements inside iArray
Public Function UnshiftArray(ByVal val As Variant) As Long
  If TypeOf val Is BeamElemList Then
    For i = val.Count - 1 To 0 Step -1
      Unshift val(i)
    Next i
  Else
    For i = UBound(val) To LBound(val) Step -1
      Unshift val(i)
    Next i
  End If
  UnshiftArray = mainArray.Count
End Function


' #####################
' # PRIVATE FUNCTIONS #
' #####################
Sub Inc(ByRef i)
   i = i + 1
End Sub

'Private Function rangeToArray(ByVal rng As Range) As Variant
'  rangeToArray = rng.Value
'End Function

Private Function randomFromTo(ByVal from As Long, ByVal upTo As Long) As Long
  Randomize
  randomFromTo = Int(from + Rnd() * (upTo - from + 1))
End Function

'比對 兩個陣列是否一樣
Private Function ArrayDifference(arr1 As Variant, arr2 As Variant) As Boolean

    Dim i As Integer
    If UBound(arr1) = UBound(arr2) Then
        For i = 0 To UBound(arr1)
            If arr1(i) = arr2(i) Then
                ArrayDifference = True
            Else
                ArrayDifference = False
                Exit Function
            End If
        Next
    Else
        ArrayDifference = False
    End If

End Function

'@Description("changes the contents of the array by removing or replacing existing elements and/or adding new elements in place.")
Public Function Splice( _
        ByVal StartIndex As Long, _
        ParamArray Args() As Variant _
    ) As Variant()
    'Dim LocalItems() As Variant
    Dim ActualStart As Long
    Dim ActualDeleteCount As Long
    Dim ArgsCount As Long
    Dim LocalLength As Long
    Dim LocalArgs() As Variant
    Dim result() As Variant
    Dim i As Long
    Dim TempArray() As Variant
    Dim ItemCount As Long
    Dim TempItems() As Variant
    
    LocalArgs = Args
    'LocalItems = mainArray
    LocalLength = Me.Count
    If StartIndex < LocalLength Then
        ActualStart = StartIndex
    Else
        ActualStart = min(StartIndex, LocalLength)
    End If
    
    ArgsCount = UBound(LocalArgs) + 1
    If ArgsCount = 0 Then
        ' only a start index has been supplied
        ' we're gonna delete everything
        ' 僅提供了起始索引
         '我們要刪除所有內容
        ItemCount = 0
        ActualDeleteCount = LocalLength - ActualStart
    Else
        ' first arg in args is delete count, second onwards are insertion items
        ' args 中的第一個參數是刪除計數，第二個之後是插入項
        ItemCount = ArgsCount - 1
        'deleteCount is first element in args.
        'deleteCount 是 args 中的第一個元素。
        ActualDeleteCount = min(max(Args(LBound(Args)), 0), LocalLength - ActualStart)
    End If
    

    ' get items to be deleted for return val
    ' 取得和刪除
    If ActualDeleteCount > 0 Then
        ReDim result(0 To ActualDeleteCount - 1)
        i = 0
        Do While i < ActualDeleteCount
            If IsObject(Me(ActualStart)) Then
                Set result(i) = Me(ActualStart)
                Me.Remove ActualStart
            Else
                result(i) = Me(ActualStart)
                Me.Remove ActualStart
            End If
            Inc i
        Loop
    Else
        ' return empty array if nothing to be deleted
        ReDim result(0)
    End If
    
    '取得要插入的陣列資料
    If ItemCount > 0 Then
        ReDim TempItems(0 To ItemCount - 1)
        For i = 0 To ItemCount - 1
            If IsObject(LocalArgs(i + 1)) Then
                Set TempItems(i) = LocalArgs(i + 1)
            Else
                TempItems(i) = LocalArgs(i + 1)
            End If
        Next
    Me.AddArrayBefore ActualStart, TempItems
    End If
    
    
    Splice = result
End Function

Attribute VB_Name = "BraceElem"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit


Public typs As String
Public header As String
Public startVoice As VoiceElement
Public endVoice As VoiceElement
Public lastContinuedVoice As VoiceElement
Public Sub init(voice As VoiceElement, typs As String)
        Me.startVoice = voice
        Me.typs = typs
End Sub

Public Sub setBottomStaff(voice As VoiceElement)
        Me.endVoice = voice
        '' If only the start brace has a name then the name belongs to the brace instead of the staff.
        If (Me.startVoice.header And Me.endVoice.header) Then
            Me.header = Me.startVoice.header
            Delete Me.startVoice.header
        End If
End Sub

Public Sub continuing(voice As VoiceElement)
        '' If the final staff isn"t present, then use the last one we saw.
        Me.lastContinuedVoice = voice
End Sub

Public Function getWidth() As Double

        getWidth = 10 '' TODO-PER as  right now the drawing function doesn"t vary the width at all. If it does in the future then this will change.
End Function

Public Function isStartVoice(voice As VoiceElement) As Boolean
        If (Not Me.startVoice Is Nothing And Not Me.startVoice.Staff Is Nothing) Then
            If (Me.startVoice.Staff.voices.Length > 0 And Me.startVoice.Staff.voices(0) Is voice) Then
                isStartVoice = True
            End If
        End If
        isStartVoice = False
    
End Function

Attribute VB_Name = "BraceElemList"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
'MIT License
'
'Copyright (c) 2019-2021 Petr Katerinak
'
'Permission is hereby granted, free of charge, to any person obtaining a copy
'of this software and associated documentation files (the "Software"), to deal
'in the Software without restriction, including without limitation the rights
'to use, copy, modify, merge, publish, distribute, sublicense, and/or sell
'copies of the Software, and to permit persons to whom the Software is
'furnished to do so, subject to the following conditions:
'
'The above copyright notice and this permission notice shall be included in all
'copies or substantial portions of the Software.
'
'THE SOFTWARE IS PROVIDED "AS IS", WITHOUT WARRANTY OF ANY KIND, EXPRESS OR
'IMPLIED, INCLUDING BUT NOT LIMITED TO THE WARRANTIES OF MERCHANTABILITY,
'FITNESS FOR A PARTICULAR PURPOSE AND NONINFRINGEMENT. IN NO EVENT SHALL THE
'AUTHORS OR COPYRIGHT HOLDERS BE LIABLE FOR ANY CLAIM, DAMAGES OR OTHER
'LIABILITY, WHETHER IN AN ACTION OF CONTRACT, TORT OR OTHERWISE, ARISING FROM,
'OUT OF OR IN CONNECTION WITH THE SOFTWARE OR THE USE OR OTHER DEALINGS IN THE
'SOFTWARE.
'
' Version of iArray: 1.0
''修正 元素從 0 開始

Private mainArray As New Collection
Private i As Long ' Counter

' #####################
' #    CONSTRUCTOR    #
' #####################
'Private Sub Class_Initialize()
'  Set mainArray = New Collection
'End Sub

' #####################
' #  Getter / Setter  #
' #####################
'Attribute Element.VB_UserMemId = 0 saved in both procedures

'@DefaultMember
Public Property Get element(ByVal index As Long) As BraceElem
Attribute element.VB_UserMemId = 0
    If index + 1 < 1 Or index + 1 > mainArray.Count Then
        Set element = Nothing
        Exit Property
    End If
    If IsObject(mainArray(index + 1)) = True Then
        Set element = mainArray(index + 1)
    Else
        element = mainArray(index + 1)
    End If

 
End Property

'@DefaultMember
Public Property Let element(ByVal index As Long, ByVal val As BraceElem)
Attribute element.VB_UserMemId = 0
  If index = 0 And mainArray.Count = 0 Then
    Me.Push val
    Exit Property
  End If
  If index + 1 > mainArray.Count Then
    Dim eMsg As String
    eMsg = IIf(mainArray.Count > 0, _
               "Index (" & index + 1 & ") out of iArray bounds (1-" & mainArray.Count & ")", _
               "iArray doesn't have any indexes")
    err.Raise Number:=9, Description:=eMsg
    Exit Property
  End If
  mainArray.Add val, after:=index + 1
  mainArray.Remove index + 1
End Property

' #############################
' # COMMON COLLECTION METHODS #
' #############################
Public Function Count() As Long
  Count = mainArray.Count
End Function
Public Sub Add(ByVal val As BraceElem, Optional ByVal bef As Variant = Empty, Optional ByVal aft As Variant = Empty)
  If IsEmpty(bef) And IsEmpty(aft) Then
    mainArray.Add val
  ElseIf IsEmpty(bef) Then
    mainArray.Add val, , , aft
  ElseIf IsEmpty(aft) Then
    mainArray.Add val, , bef
  Else
    mainArray.Add val, , bef, aft
  End If
End Sub
Public Sub Remove(index As Long)
  mainArray.Remove index + 1
End Sub

' ####################
' #  PUBLIC METHODS  #
' ####################

'AddAfter
' Adds element after given index.
' {1,2,3} -> index >= 3 -> Push val
' {1,2,3} -> index < 1 -> Unshift val
' {} -> index = any -> Push val
' @param Long index | Index after which will be added an element
' @param Variant val | One element (String, number, ...) to add into iArray
' @return Long | Count of elements inside iArray
Public Function AddAfter(ByVal index As Long, ByVal val As BraceElem) As Long
  If Me.Count < 1 Or index + 1 >= Me.Count Then
    Me.Push val
  ElseIf index + 1 < 1 Then
    Me.Unshift val
  Else
    Me.Add val, aft:=index + 1
  End If
  AddAfter = Me.Count
End Function

'AddArrayAfter
' Adds elements after given index.
' {1,2,3} -> index >= 3 -> PushArray val
' {1,2,3} -> index < 1 -> UnshiftArray val
' {} -> index = any -> PushArray val
' @param Long index | Index after which will be added an element
' @param Variant val | Array() or iArray of elements to add into iArray
' @return Long | Count of elements inside iArray
Public Function AddArrayAfter(ByVal index As Long, ByVal val As Variant) As Long
  If Me.Count < 1 Or index + 1 >= Me.Count Then
    Me.PushArray val
  ElseIf index + 1 < 1 Then
    Me.UnshiftArray val
  Else
    If TypeOf val Is BraceElemList Then
      For i = 0 To val.Count - 1
        Me.Add val(i), aft:=index + 1
        Inc index
      Next i
    Else
      For i = LBound(val) To UBound(val)
        Me.Add val(i), aft:=index + 1
        Inc index
      Next i
    End If
  End If
  AddArrayAfter = Me.Count
End Function

'AddArrayBefore
' Adds elements before given index.
' {1,2,3} -> index > 3 -> PushArray val
' {1,2,3} -> index <= 1 -> UnshiftArray val
' {} -> index = any -> PushArray val
' @param Long index | Index after which will be added an element
' @param Variant val | Array() or iArray of elements to add into iArray
' @return Long | Count of elements inside iArray
Public Function AddArrayBefore(ByVal index As Long, ByVal val As Variant) As Long
  If Me.Count < 1 Or index + 1 > Me.Count Then
    Me.PushArray val
  ElseIf index <= 0 Then
    Me.UnshiftArray val
  Else
    If TypeOf val Is BraceElemList Then
      For i = val.Count - 1 To 0 Step -1
        Me.Add val(i), bef:=index + 1
      Next i
    Else
      For i = UBound(val) To LBound(val) Step -1
        Me.Add val(i), bef:=index + 1
      Next i
    End If
  End If
  AddArrayBefore = Me.Count
End Function

'AddBefore
' Adds element before given index.
' {1,2,3} -> index > 3 -> Push val
' {1,2,3} -> index <= 1 -> Unshift val
' {} -> index = any -> Push val
' @param Long index | Index before which will be added an element
' @param Variant val | One element (String, number, ...) to add into iArray
' @return Long | Count of elements inside iArray
Public Function AddBefore(ByVal index As Long, ByVal val As BraceElem) As Long
  If Me.Count < 1 Or index + 1 > Me.Count Then
    Me.Push val
  ElseIf index + 1 <= 1 Then
    Me.Unshift val
  Else
    Me.Add val, bef:=index + 1
  End If
  AddBefore = Me.Count
End Function

'Avg
' Calculates the average of the numeric mainArray.
' @return Variant | Average value / "NaN" if iArray contains non-numeric value(s)
Public Function Avg() As Variant
  If Not Me.ContainsOnlyNumeric Then Avg = "NaN": Exit Function
  Avg = Me.sum / Me.Count
End Function

'Clear
' Empties iArray
Public Function Clear() As Boolean
  For i = mainArray.Count - 1 To 0 Step -1
    mainArray.Remove i + 1
  Next i
  Clear = IIf(mainArray.Count = 0, True, False)
End Function

'Clone
' Makes a hard copy of the mainArray
' @return mainArray | Return exact copy of itself
Public Function clone() As BraceElemList
  Set clone = New BraceElemList
  For i = 0 To Me.Count - 1
    clone.Push Me(i)
  Next i
End Function

'Contains
' Checks if given value is used inside mainArray.
' @param Variant val | One element (String, number, ...) to by checked if it exists in iArray
' $return Boolean | True = exists, False = doesn't exists
Public Function Contains(ByVal val As BraceElem) As Boolean
  Contains = False
  Dim el As Variant
  For Each el In mainArray
    If IsObject(val) = True Or VarType(val) And 8192 Then
        If (VarType(el) And 8192) And (VarType(val) And 8192) Then
            If ArrayDifference(el, val) Then
                Contains = True: Exit Function
            End If
        ElseIf IsObject(el) = True And IsObject(val) = True Then
            If el Is val Then
                Contains = True: Exit Function
            End If
        End If
    Else
        If IsObject(el) = False And (VarType(el) And 8192) <> 8192 Then
            If el = val Then
            Contains = True: Exit Function
            End If
        End If
    End If
  Next el
End Function

'ContainsAll
' Checks if all given values are used inside mainArray.
' @param Variant val | values to by checked if it exists in iArray
' $return Boolean | True = all exists, False = one ore more values doesn't exists
Public Function ContainsAll(ByVal val As BraceElemList) As Boolean
  ContainsAll = False
  Dim foundOccurrences As Integer: foundOccurrences = 0
  Dim values As New BraceElemList
  If Not TypeOf val Is BraceElemList Then
    If IsArray(val) Then
      values.PushArray (val)
    Else
      values.Push (val)
    End If
  Else
    Set values = val
  End If
  For i = 0 To values.Count - 1
    If Me.Contains(values(i)) Then Inc foundOccurrences
  Next i
  If foundOccurrences = values.Count Then ContainsAll = True
End Function

'CountOccurrences
' Checks how many times is given value used inside mainArray.
' @param Variant val | One element (String, number, ...) to by checked
' @return Long | Count of matched occurrences
Public Function CountOccurrences(val As Variant) As Long
  CountOccurrences = 0
  Dim el As Variant
  For Each el In mainArray
  
    If IsObject(val) = True Or VarType(val) And 8192 Then
        If VarType(el) And 8192 And VarType(val) And 8192 Then
            If ArrayDifference(el, val) Then
                Inc CountOccurrences
                Exit Function
            End If
        ElseIf IsObject(el) = True And IsObject(val) = True Then
            If el Is val Then
                Inc CountOccurrences
                Exit Function
            End If
        End If
    Else
        If IsObject(el) = False And Not (VarType(el) And 8192) Then
            If el = val Then
                Inc CountOccurrences
                Exit Function
            End If
        End If
    End If
  
     'If el = val Then Inc CountOccurrences
  Next el
End Function

'Dequeue
' Removes an element from the begining of the mainArray.
' @return Variant | Removed element or Empty, if iArray is empty
'刪除開頭一個元素。
Public Function Dequeue() As BraceElem
  Dequeue = Empty
  If mainArray.Count > 0 Then
    If VarType(Me(0)) = vbString Then
        Dequeue = Me(0)
    ElseIf TypeOf Me(0) Is BraceElemList Then
        Set Dequeue = Me(0)
    ElseIf VarType(Me(0)) = vbArray Then
        Set Dequeue = Me(0)
    ElseIf VarType(Me(0)) = vbObject Then
        Set Dequeue = Me(0)
    Else
        Dequeue = Me(0)
    End If
    
    mainArray.Remove 1
  End If
End Function

'Difference
' Checks for number of differences between two arrays, what was added/deleted or combination.
' @param iArray oldArray | Old iArray to be compared with current iArray
' @param String retType | �dd= deleted from old iArray, �aa= added in current iArray, �cc= combination of both (default)
' @return iArray | iArray with differences found
Public Function Difference(ByRef oldArray As BraceElemList, Optional ByVal retType As String = "c") As BraceElemList
  Set Difference = New BraceElemList
  Select Case LCase(retType)
    Case "d"
      For i = 0 To oldArray.Count - 1
        If Me.Contains(oldArray(i)) = False Then Difference.Push oldArray(i)
      Next i
    Case "a"
      For i = 0 To Count - 1
        If oldArray.Contains(Me(i)) = False Then Difference.Push Me(i)
      Next i
    Case "c"
      For i = 0 To oldArray.Count - 1
        If Me.Contains(oldArray(i)) = False Then Difference.Push oldArray(i)
      Next i
      For i = 0 To Count - 1
        If oldArray.Contains(Me(i)) = False Then Difference.Push Me(i)
      Next i
    Case Else
      err.Raise Number:=5, Description:="Unknown Difference return type attribute:" & vbCrLf & _
                                        "Allowed are 'A'dded/'D'eleted/'C'ombination of both"
  End Select
End Function

'DropLeft
' Remove n elements from the beginning of the mainArray. If n > count of iArray elements, all elements are removed.
' @param Long n | Number of elements to be removed
' @return iArray | Array of the removed elements
Public Function DropLeft(ByRef N As Long) As BraceElemList
  Set DropLeft = New BraceElemList
  If N > Me.Count Then N = Me.Count
  For i = 0 To N - 1
    DropLeft.Push Me(i)
  Next i
  For i = N - 1 To 0 Step -1
    Me.Remove (i)
  Next i
End Function

'DropRight
' Remove n elements from the end of the mainArray. If n > count of iArray elements, all elements are removed.
' @param Long n | Number of elements to be removed
' @return iArray | Array of the removed elements
Public Function DropRight(ByRef N As Long) As BraceElemList
  Set DropRight = New BraceElemList
  If N > Me.Count Then N = Me.Count
  For i = Me.Count - N To Me.Count - 1
    DropRight.Push Me(i)
  Next i
  For i = Me.Count - 1 To Me.Count - N Step -1
    Me.Remove (i)
  Next i
End Function

'Enqueue
' Adds an element at the end of the mainArray.
' @param Variant val | One element (String, number, ...) to add into iArray
' @return Long | Count of elements inside iArray
Public Function Enqueue(ByVal val As Variant) As Long
  Enqueue = Push(val)
End Function

'EnqueueArray
' Adds elements at the end of the iArray
' @param Variant val | Array() or iArray of elements to add into iArray
' @return Long | Count of elements inside array
Public Function EnqueueArray(ByVal val As Variant) As Long
  EnqueueArray = PushArray(val)
End Function

'First
' Returns value of the first element of the mainArray.
' @return Variant | Value of the first element or Empty if iArray is Empty
Public Function First() As BraceElem
  Set First = IIf(Me.Count > 0, Me(0), Empty)
End Function

'Head
' Returns all elements of iArray, except last one.
' @return iArray | Copy of original array, without last element
Public Function head() As BraceElemList
  Set head = Me.clone
  head.Pop
End Function

'Intersect
' Search for element that exists in both iArrays.
' @param iArray intArray | iArray to be intersected with current iArray
' @return iArray | Intersected values
Public Function Intersect(ByRef intersectedArr As BraceElemList) As BraceElemList
  Set Intersect = New BraceElemList
  Dim el As Variant
  For Each el In mainArray
    If intersectedArr.Contains(el) Then
      If Not Intersect.Contains(el) Then Intersect.Push (el)
    End If
  Next el
End Function

'ContainsOnlyNumeric
' Verify that all elements are numbers or convertable to numbers
' $return Boolean | True = contains only numeric values, False = contains inconvertible values
Public Function ContainsOnlyNumeric() As Boolean
  ContainsOnlyNumeric = True
  Dim el As Variant
  For Each el In mainArray
    If Not IsNumeric(el) Then ContainsOnlyNumeric = False: Exit Function
  Next el
End Function

'Join
' Joins two iArrays.
' @param iArray jArray | iArray to be joined with current iArray
' @return iArray | Joined iArray
Public Function Join(ByRef joinArr As BraceElemList) As BraceElemList
  Set Join = New BraceElemList
  Join.PushArray Me
  Join.PushArray joinArr
End Function

'Last
' Returns value of the last element of the mainArray.
' @return Variant | Value of the last element or Empty if iArray is Empty
Public Function Last() As BraceElem
  Set Last = IIf(Me.Count > 0, Me(Me.Count - 1), Empty)
End Function

'OccurrenceIndexes
' Returns all indexes of a value in mainArray.
' @return iArray | iArray containing indexes of occurrence
Public Function OccurenceIndexes(val As Variant) As BraceElemList
  Set OccurenceIndexes = New BraceElemList
  For i = 0 To Me.Count - 1
    If Me(i) = val Then
        OccurenceIndexes.Push (i)
    End If
  Next i
End Function

'Pop
' Removes an element from the end of the mainArray.
' @return Variant | Removed element or Empty, if iArray is empty
Public Function Pop() As BraceElem
  If mainArray.Count > 0 Then
    If VarType(Me(mainArray.Count - 1)) = vbObject Then
       Set Pop = Me(mainArray.Count - 1)
    Else
        Pop = Me(mainArray.Count - 1)
    End If
    mainArray.Remove mainArray.Count
  End If
End Function
  
  

'Push
' Adds an element at the end of the mainArray.
' @param Variant val | One element (String, number, ...) to add into iArray
' @return Long | Count of elements inside iArray
Public Function Push(ByVal val As BraceElem) As Long
  mainArray.Add val
  Push = mainArray.Count
End Function

'PushArray
' Adds elements at the end of the mainArray.
' @param Variant val | Array() or iArray of elements to add into iArray
' @return Long | Count of elements inside array
Public Function PushArray(ByVal val As Variant) As Long
  If TypeOf val Is BraceElemList Then
    For i = 0 To val.Count - 1
      Me.Push val(i)
    Next i
  Else
    For i = LBound(val) To UBound(val)
      Me.Push val(i)
    Next i
  End If
  PushArray = Me.Count
End Function

'RemoveDuplicates
' Keeps only the first occurrence of the value. Affects original array
' @return Long | Count of the removed elements
Public Function RemoveDuplicates() As Long
  RemoveDuplicates = 0
  For i = Me.Count - 1 To 0 Step -1
    If Me.CountOccurrences(Me(i)) > 1 Then
      Me.Remove i
      Inc RemoveDuplicates
    End If
  Next i
End Function

'Reverse
' Reverses the content of the iArray
' @return iArray | Reversed iArray
Public Function Reverse() As BraceElemList
  Set Reverse = New BraceElemList
  For i = 0 To Me.Count - 1
    Reverse.Unshift Me(i)
  Next i
End Function

'Shift
' Removes an element from the begining of the mainArray.
' @return Variant | Removed element or Empty, if iArray is empty
'轉移
' 從 iArray 的開頭刪除一個元素。
' @返回第一個元素 | 如果 iArray 為空，則刪除元素或為空
Public Function shift() As BraceElem
  shift = Empty
  If mainArray.Count > 0 Then
    If VarType(Me(0)) = vbString Then
        shift = Me(0)
    ElseIf TypeOf Me(0) Is BraceElemList Then
        Set shift = Me(0)
    ElseIf VarType(Me(0)) = vbArray Then
        Set shift = Me(0)
    ElseIf VarType(Me(0)) = vbObject Then
        Set shift = Me(0)
    Else
        shift = Me(0)
    End If
    
    mainArray.Remove 1
  End If
End Function

'Shuffle
' Randomly mixes content of the iArray
' @return iArray | Shuffled iArray
' 隨機播放
' 隨機混合 iArray 的內容
'@return iArray | 打亂iArray
Public Function Shuffle() As BraceElemList
  Set Shuffle = New BraceElemList
  Dim keys As New BraceElemList
  For i = 0 To Me.Count - 1
    keys.Push (i)
  Next i
  Dim rndNo As Long
  Do While keys.Count > 0
    rndNo = randomFromTo(0, keys.Count - 1)
    Shuffle.Push Me(keys(rndNo))
    keys.Remove (rndNo)
  Loop
End Function

'Sum
' Calculates the sum of the numeric mainArray.
' @return Variant | Sum value / "NaN" if iArray contains non-numeric value(s)
Public Function sum() As Variant
  If Not Me.ContainsOnlyNumeric Then sum = "NaN": Exit Function
  sum = 0
  Dim el As Variant
  For Each el In mainArray
    sum = sum + el
  Next el
End Function

'Tail
' Returns all elements of iArray, except first one.
' @return iArray | Copy of original array, without first element
'返回陣列中除了第一個元素的剩余元素陣列
Public Function Tail() As BraceElemList
  Set Tail = Me.clone
  Tail.Dequeue
End Function

Public Function ToList()
  If Me.Count = 0 Then ToList = Null: Exit Function
  Dim tarr()
  ReDim tarr(Me.Count - 1)
  For i = 0 To Me.Count - 1
    If VarType(Me(i)) = vbString Then
        tarr(i) = Me(i)
    ElseIf TypeOf Me(i) Is BraceElemList Then
        Set tarr(i) = Me(i)
    ElseIf VarType(Me(i)) = vbObject Then
        Set tarr(i) = Me(i)
    Else
        tarr(i) = Me(i)
    End If
  Next i
  ToList = tarr
End Function

'ToString
' Creates string representation of the mainArray.
' @param String delimiter | Optional character to separate the iArray's elements (default = " ")
' @return String | Formated representation of tha iArray
Public Function ToString(Optional ByVal delimiter As String = " ") As String
  If Me.Count = 0 Then ToString = "{}": Exit Function
  ToString = vbNullString
  For i = 0 To Me.Count - 1
    If i = 0 Then ToString = ToString + "{"
    If i > 0 Then ToString = ToString + delimiter
    If VarType(Me(i)) = vbString Then
        ToString = ToString + Chr$(34)
        ToString = ToString + CStr(Me(i))
        ToString = ToString + Chr$(34)
    ElseIf TypeOf Me(i) Is BraceElemList Then
        ToString = ToString + Me(i).ToString(delimiter)
    ElseIf (VarType(Me(i)) And vbArray) = vbArray Then
        ToString = ToString + "[Array]"
    ElseIf VarType(Me(i)) = vbObject Then
        ToString = ToString + "[Object]"
    Else
        ToString = ToString + CStr(Me(i))
    End If
    
    If i = mainArray.Count - 1 Then ToString = ToString + "}"
  Next i
End Function

'Union
' Combines both iArrays and removes duplicities
' @param iArray uArray | iArray to be unioned with current iArray
' @return iArray | Combined values without duplicities
Public Function Union(ByRef uArr As BraceElemList) As BraceElemList
  Set Union = Me.clone
  Union.PushArray uArr
  Union.RemoveDuplicates
End Function

'Unique
' Returns copy of iArray without duplicated values. Original array is not affected
' @return iArray | iArray with unique values
Public Function Unique() As BraceElemList
  Set Unique = New BraceElemList
  Dim el As Variant
  For Each el In mainArray
    If Not Unique.Contains(el) Then Unique.Push (el)
  Next el
End Function

'Unshift
' Add an element at the begining of the mainArray.
' @param Variant val | One element (String, number, ...) to add into iArray
' @return Long | Count of elements inside iArray
Public Function Unshift(ByVal val As Variant) As Long
  If mainArray.Count = 0 Then
    Unshift = Push(val)
  Else
    mainArray.Add val, before:=1
    Unshift = mainArray.Count
  End If
End Function

'UnshiftArray
' Add elements at the begining of the mainArray.
' @param Variant val | Array() or iArray of elements to add into iArray
' @return Long | Count of elements inside iArray
Public Function UnshiftArray(ByVal val As Variant) As Long
  If TypeOf val Is BraceElemList Then
    For i = val.Count - 1 To 0 Step -1
      Unshift val(i)
    Next i
  Else
    For i = UBound(val) To LBound(val) Step -1
      Unshift val(i)
    Next i
  End If
  UnshiftArray = mainArray.Count
End Function


' #####################
' # PRIVATE FUNCTIONS #
' #####################
Sub Inc(ByRef i)
   i = i + 1
End Sub

'Private Function rangeToArray(ByVal rng As Range) As Variant
'  rangeToArray = rng.Value
'End Function

Private Function randomFromTo(ByVal from As Long, ByVal upTo As Long) As Long
  Randomize
  randomFromTo = Int(from + Rnd() * (upTo - from + 1))
End Function

'比對 兩個陣列是否一樣
Private Function ArrayDifference(arr1 As Variant, arr2 As Variant) As Boolean

    Dim i As Integer
    If UBound(arr1) = UBound(arr2) Then
        For i = 0 To UBound(arr1)
            If arr1(i) = arr2(i) Then
                ArrayDifference = True
            Else
                ArrayDifference = False
                Exit Function
            End If
        Next
    Else
        ArrayDifference = False
    End If

End Function

'@Description("changes the contents of the array by removing or replacing existing elements and/or adding new elements in place.")
Public Function Splice( _
        ByVal StartIndex As Long, _
        ParamArray Args() As Variant _
    ) As Variant()
    'Dim LocalItems() As Variant
    Dim ActualStart As Long
    Dim ActualDeleteCount As Long
    Dim ArgsCount As Long
    Dim LocalLength As Long
    Dim LocalArgs() As Variant
    Dim result() As Variant
    Dim i As Long
    Dim TempArray() As Variant
    Dim ItemCount As Long
    Dim TempItems() As Variant
    
    LocalArgs = Args
    'LocalItems = mainArray
    LocalLength = Me.Count
    If StartIndex < LocalLength Then
        ActualStart = StartIndex
    Else
        ActualStart = min(StartIndex, LocalLength)
    End If
    
    ArgsCount = UBound(LocalArgs) + 1
    If ArgsCount = 0 Then
        ' only a start index has been supplied
        ' we're gonna delete everything
        ' 僅提供了起始索引
         '我們要刪除所有內容
        ItemCount = 0
        ActualDeleteCount = LocalLength - ActualStart
    Else
        ' first arg in args is delete count, second onwards are insertion items
        ' args 中的第一個參數是刪除計數，第二個之後是插入項
        ItemCount = ArgsCount - 1
        'deleteCount is first element in args.
        'deleteCount 是 args 中的第一個元素。
        ActualDeleteCount = min(max(Args(LBound(Args)), 0), LocalLength - ActualStart)
    End If
    

    ' get items to be deleted for return val
    ' 取得和刪除
    If ActualDeleteCount > 0 Then
        ReDim result(0 To ActualDeleteCount - 1)
        i = 0
        Do While i < ActualDeleteCount
            If IsObject(Me(ActualStart)) Then
                Set result(i) = Me(ActualStart)
                Me.Remove ActualStart
            Else
                result(i) = Me(ActualStart)
                Me.Remove ActualStart
            End If
            Inc i
        Loop
    Else
        ' return empty array if nothing to be deleted
        ReDim result(0)
    End If
    
    '取得要插入的陣列資料
    If ItemCount > 0 Then
        ReDim TempItems(0 To ItemCount - 1)
        For i = 0 To ItemCount - 1
            If IsObject(LocalArgs(i + 1)) Then
                Set TempItems(i) = LocalArgs(i + 1)
            Else
                TempItems(i) = LocalArgs(i + 1)
            End If
        Next
    Me.AddArrayBefore ActualStart, TempItems
    End If
    
    
    Splice = result
End Function

Attribute VB_Name = "Class1"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public barNumber      As Double
Public brace As BracePosition
Public bracket As BracePosition
Public clef As ClefProperties
Public connectBarLines As BracePosition
Public annotationfont    As vFont
Public gchordfont     As vFont
Public tripletfont    As vFont
Public vocalfont    As vFont
Public key As KeySignature
Public meter As meter
Public spacingAbove    As Double
Public spacingBelow   As Double
Public stafflines   As Double
Public isJianpu As Boolean
Public staffscale    As Double
Public title As iArray
Public voices As VoiceABC    'Array<Array<VoiceItem>>

Attribute VB_Name = "Class2"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public formatting As vFormatting
Public engraver As EngraverController
Public lines As TuneLine
Public media As media
Public metaText As metaText
Public metaTextInfo As metaTextInfo
Public version As String

Attribute VB_Name = "CommonFileDialog"


'CommonFileDialog 模組內容
'Description:
'
'The FileDialog class allows you to use the common dialogs "Open" and "Save" from VBA. Properties for the class include
'Multiselect, title, filter, initial directory, and hide read only.
'Also included is simple methods for finding the window to make the parent of the dialog (the one that it will center on).
'Snippet Code: - Common File Dialog Class

Option Explicit
#If VBA7 Then
'''The Win32 API Functions''/
Private Declare PtrSafe Function GetSaveFileName Lib "comdlg32.dll" Alias "GetSaveFileNameA" (pOpenfilename As OPENFILENAME) As Long
Private Declare PtrSafe Function GetOpenFileName Lib "comdlg32.dll" Alias "GetOpenFileNameA" (pOpenfilename As OPENFILENAME) As Long
Private Declare PtrSafe Function FindWindow Lib "user32" Alias "FindWindowA" (ByVal lpClassName As String, ByVal lpWindowName As String) As Long
#Else
Private Declare Function GetSaveFileName Lib "comdlg32.dll" Alias "GetSaveFileNameA" (pOpenfilename As OPENFILENAME) As Long
Private Declare Function GetOpenFileName Lib "comdlg32.dll" Alias "GetOpenFileNameA" (pOpenfilename As OPENFILENAME) As Long
Private Declare Function FindWindow Lib "user32" Alias "FindWindowA" (ByVal lpClassName As String, ByVal lpWindowName As String) As Long
#End If


'''A few of the available Flags''/
Private Const OFN_FILEMUSTEXIST = &H1000
Private Const OFN_ALLOWMULTISELECT = &H200
Public Const OFN_PATHMUSTEXIST = &H800
Public Const OFN_HIDEREADONLY = &H4 '隱蔽只讀複選框



'This one keeps your dialog from turning into
'A browse by folder dialog if multiselect is true!
'Not sure what I mean? Remove it from the flags
'In the "Show Open" & "Show Save" methods.
Private Const OFN_EXPLORER As Long = &H80000
'''The Structure
Private Type OPENFILENAME
    lStructSize As Long
    hwndOwner As Long '擁有對話框的窗口
    hInstance As Long
    lpstrFilter As String '裝載文件過濾器的緩衝區
    lpstrCustomFilter As String
    nMaxCustFilter As Long
    nFilterIndex As Long
    lpstrFile As String
    nMaxFile As Long
    lpstrFileTitle As String
    nMaxFileTitle As Long
    lpstrInitialDir As String
    lpstrTitle As String    '對話框的標題
    flags As Long
    nFileOffset As Integer
    nFileExtension As Integer
    lpstrDefExt As String
    lCustData As Long
    lpfnHook As Long
    lpTemplateName As String
End Type
Private lngHwnd As Long
Private strFilter As String
Private strTitle As String
Private strDir As String
Private blnHideReadOnly As Boolean
Private blnAllowMulti As Boolean
Private blnMustExist As Boolean
Private Sub Class_Initialize()
    'Set default values when
    'class is first created
    strDir = CurDir
    strTitle = "Llamas Rule"
    strFilter = "All Files" _
    & Chr$(0) & "*.*" & Chr$(0)
    lngHwnd = FindWindow(vbNullString, Application.Caption)
    'None of the flags are set here!
End Sub
Public Function FindUserForm(objForm As UserForm) As Long
    Dim lngTemp As Long
    Dim strCaption As String
    strCaption = objForm.Caption
    lngTemp = FindWindow(vbNullString, strCaption)
    If lngTemp <> 0 Then
        FindUserForm = lngTemp
    End If
End Function
Public Property Let OwnerHwnd(WindowHandle As Long)
    '''FOR YOU TODO''
    'Use the API to validate this handle
    lngHwnd = WindowHandle
    'This value is set at startup to the handle of the
    'AutoCAD Application window, if you want the owner
    'to be a user form you will need to obtain its
    'Handle by using the "FindUserForm" function in
    'This class.
End Property
Public Property Get OwnerHwnd() As Long
    OwnerHwnd = lngHwnd
End Property
Public Property Let title(Caption As String)
    'don't allow null strings
    If Not Caption = vbNullString Then
        strTitle = Caption
    End If
End Property
Public Property Get title() As String
    title = strTitle
End Property
Public Property Let Filter(ByVal FilterString As String)
    'Filters change the type of files that are
    'displayed in the dialog. I have designed this
    'validation to use the same filter format the
    'Common dialog OCX uses:
    '"All Files (*.*)|*.*"
    Dim intPos As Integer
    Do While InStr(FilterString, "|") > 0
    intPos = InStr(FilterString, "|")
    If intPos > 0 Then
        FilterString = left$(FilterString, intPos - 1) _
        & Chr$(0) & right$(FilterString, _
        Len(FilterString) - intPos)
    End If
    Loop
    If right$(FilterString, 2) <> Chr$(0) & Chr$(0) Then
        FilterString = FilterString & Chr$(0)
    End If
    strFilter = FilterString
End Property
Public Property Get Filter() As String
    'Here we reverse the process and return
    'the Filter in the same format the it was
    'entered
    Dim intPos As Integer
    Dim strTemp As String
    strTemp = strFilter
    Do While InStr(strTemp, Chr$(0)) > 0
    intPos = InStr(strTemp, Chr$(0))
    If intPos > 0 Then
        strTemp = left$(strTemp, intPos - 1) _
        & "|" & right$(strTemp, _
        Len(strTemp) - intPos)
    End If
    Loop
    If right$(strTemp, 1) = "|" Then
        strTemp = left$(strTemp, Len(strTemp) - 1)
    End If
    Filter = strTemp
End Property
Public Property Let InitialDir(strFolder As String)
    'Sets the directory the dialog displays when called
    If Len(dir(strFolder)) > 0 Then
        strDir = strFolder
        Else
        err.Raise 514, "FileDialog", "Invalid Initial Directory"
    End If
End Property
Public Property Let HideReadOnly(blnVal As Boolean)
    blnHideReadOnly = blnVal
End Property
Public Property Let MultiSelect(blnVal As Boolean)
    'allow users to select more than one file using
    'The Shift or CTRL keys during selection
    blnAllowMulti = blnVal
End Property
Public Property Let FileMustExist(blnVal As Boolean)
    blnMustExist = blnVal
End Property
'@~~~~~~~~~~~~~~~~~~~~~~~~~~~~~~~~~~~~~~~~~~~~~~~~@
' Display and use the File open dialog
'@~~~~~~~~~~~~~~~~~~~~~~~~~~~~~~~~~~~~~~~~~~~~~~~~@
Public Function ShowOpen() As String
    Dim strTemp As String
    Dim udtStruct As OPENFILENAME
    udtStruct.lStructSize = Len(udtStruct)
    'Use our private variable
    udtStruct.hwndOwner = lngHwnd
    'Use our private variable
    udtStruct.lpstrFilter = strFilter
    udtStruct.lpstrFile = space$(254)
    udtStruct.nMaxFile = 255
    udtStruct.lpstrFileTitle = space$(254)
    udtStruct.nMaxFileTitle = 255
    'Use our private variable
    udtStruct.lpstrInitialDir = strDir
    'Use our private variable
    udtStruct.lpstrTitle = strTitle
    'Ok, here we test our booleans to
    'set the flag
    If blnHideReadOnly And blnAllowMulti And blnMustExist Then
        udtStruct.flags = OFN_HIDEREADONLY Or _
        OFN_ALLOWMULTISELECT Or OFN_EXPLORER Or OFN_FILEMUSTEXIST
        ElseIf blnHideReadOnly And blnAllowMulti Then
        udtStruct.flags = OFN_ALLOWMULTISELECT _
        Or OFN_EXPLORER Or OFN_HIDEREADONLY
        ElseIf blnHideReadOnly And blnMustExist Then
        udtStruct.flags = OFN_HIDEREADONLY Or OFN_FILEMUSTEXIST
        ElseIf blnAllowMulti And blnMustExist Then
        udtStruct.flags = OFN_ALLOWMULTISELECT Or _
        OFN_EXPLORER Or OFN_FILEMUSTEXIST
        ElseIf blnHideReadOnly Then
        udtStruct.flags = OFN_HIDEREADONLY
        ElseIf blnAllowMulti Then
        udtStruct.flags = OFN_ALLOWMULTISELECT _
        Or OFN_EXPLORER
        ElseIf blnMustExist Then
        udtStruct.flags = OFN_FILEMUSTEXIST
    End If
    If GetOpenFileName(udtStruct) Then
        strTemp = (Trim(udtStruct.lpstrFile))
        ShowOpen = Mid(strTemp, 1, Len(strTemp) - 1)
    End If
End Function
'@~~~~~~~~~~~~~~~~~~~~~~~~~~~~~~~~~~~~~~~~~~~~~~~~@
' Display and use the File Save dialog
'@~~~~~~~~~~~~~~~~~~~~~~~~~~~~~~~~~~~~~~~~~~~~~~~~@
Public Function ShowSave() As String
    Dim strTemp As String
    Dim udtStruct As OPENFILENAME
    udtStruct.lStructSize = Len(udtStruct)
    'Use our private variable
    udtStruct.hwndOwner = lngHwnd
    'Use our private variable
    udtStruct.lpstrFilter = strFilter
    udtStruct.lpstrFile = space$(254)
    udtStruct.nMaxFile = 255
    udtStruct.lpstrFileTitle = space$(254)
    udtStruct.nMaxFileTitle = 255
    'Use our private variable
    udtStruct.lpstrInitialDir = strDir
    'Use our private variable
    udtStruct.lpstrTitle = strTitle
    If blnMustExist Then
        udtStruct.flags = OFN_FILEMUSTEXIST
    End If
    If GetSaveFileName(udtStruct) Then
        strTemp = (Trim(udtStruct.lpstrFile))
        ShowSave = Mid(strTemp, 1, Len(strTemp) - 1)
    End If
End Function


Function GetFile(strTitle As String, strFilter As String, Optional strIniDir As String) As String
 
    On Error Resume Next
    Dim lntFile As Integer
    Dim fileName As String
    Dim OFileBox As OPENFILENAME
    With OFileBox
        .lpstrTitle = strTitle '對話框標題
        .lpstrInitialDir = strIniDir '初始目錄
        .lStructSize = Len(OFileBox)
        .hwndOwner = ThisDrawing.hWnd
        .flags = OFN_PATHMUSTEXIST Or OFN_FILEMUSTEXIST Or OFN_HIDEREADONLY
        .lpstrFile = String$(255, 0)
        .nMaxFile = 255
        .lpstrFileTitle = String$(255, 0)
        .nMaxFileTitle = 255
        .lpstrFilter = strFilter  '過濾器
        .nFilterIndex = 1
    End With
     
    lntFile = GetOpenFileName(OFileBox) '執行打開對話框
    If lntFile <> 0 Then
        fileName = left(OFileBox.lpstrFile, InStr(OFileBox.lpstrFile, vbNullChar) - 1)
        GetFile = fileName
    Else
        GetFile = ""
    End If
 
End Function
Function saveFile(strTitle As String, strFilter As String, Optional strIniDir As String) As String
 
    On Error Resume Next
    Dim lntFile As Integer
    Dim fileName As String
    Dim OFileBox As OPENFILENAME
    With OFileBox
        .lpstrTitle = strTitle '對話框標題
        .lpstrInitialDir = strIniDir '初始目錄
        .lStructSize = Len(OFileBox)
        .hwndOwner = ThisDrawing.hWnd
        .flags = OFN_PATHMUSTEXIST Or OFN_FILEMUSTEXIST Or OFN_HIDEREADONLY
        .lpstrFile = String$(255, 0)
        .nMaxFile = 255
        .lpstrFileTitle = String$(255, 0)
        .nMaxFileTitle = 255
        .lpstrFilter = strFilter  '過濾器
        .nFilterIndex = 1
    End With
     
    lntFile = GetSaveFileName(OFileBox) '執行打開對話框
    If lntFile <> 0 Then
        fileName = left(OFileBox.lpstrFile, InStr(OFileBox.lpstrFile, vbNullChar) - 1)
        saveFile = fileName
    Else
        saveFile = ""
    End If
 
End Function

Attribute VB_Name = "DISC"
Attribute VB_Base = "0{6B33FA79-9C0F-4764-A15F-56DAB5391D34}{242AC99D-2F94-4542-842F-4731D9549DAA}"
Attribute VB_GlobalNameSpace = False
Attribute VB_Creatable = False
Attribute VB_PredeclaredId = True
Attribute VB_Exposed = False
Attribute VB_TemplateDerived = False
Attribute VB_Customizable = False

Private Sub cbLoad_Click()
  
    Dim TrackingDictionary As AcadDictionary, TrackingXRecord As AcadXRecord
    Dim XRecordDataType As Variant, XRecordData As Variant
    Dim ArraySize As Long, iCount As Long
    Dim DataType As Integer, data As String, msg As String
    
        ' Unique identifiers to distinguish our XRecordData from other XRecordData
    Const TYPE_STRING = 1
    Const TAG_DICTIONARY_NAME = "ObjectTrackerDictionary"
    Const TAG_XRECORD_NAME = "ObjectTrackerXRecord"

    ' Connect to the dictionary we store the XRecord in
    On Error GoTo create
    Set TrackingDictionary = ThisDrawing.Dictionaries(TAG_DICTIONARY_NAME)
    Set TrackingXRecord = TrackingDictionary.GetObject(TAG_XRECORD_NAME)
    On Error GoTo 0
    
 
    ' Read back all XRecordData entries
    TrackingXRecord.GetXRecordData XRecordDataType, XRecordData
    ArraySize = UBound(XRecordDataType)
    
    ' Retrieve and display stored XRecordData
    For iCount = 0 To ArraySize
        ' Get information for this element
        DataType = XRecordDataType(iCount)
        data = XRecordData(iCount)
        
        If DataType = TYPE_STRING Then
            msg = msg & data & vbCrLf
        End If
    Next
    Me.TextBox1 = msg
    ''MsgBox "The data in the XRecord is: " & vbCrLf & vbCrLf & msg, vbInformation
    
    Exit Sub

create:
    ' Create the entities that hold our XRecordData
    If TrackingDictionary Is Nothing Then  ' Make sure we have our tracking object
        Set TrackingDictionary = ThisDrawing.Dictionaries.Add(TAG_DICTIONARY_NAME)
        Set TrackingXRecord = TrackingDictionary.AddXRecord(TAG_XRECORD_NAME)
    End If
    
    Resume
End Sub

Private Sub CommandButton1_Click()

    ' This example creates a new XRecord if one doesn't exist,
    ' appends data to the XRecord and reads it back.  To see data being added
    ' run the example more than once.
    
    Dim TrackingDictionary As AcadDictionary, TrackingXRecord As AcadXRecord
    Dim XRecordDataType As Variant, XRecordData As Variant
    Dim ArraySize As Long, iCount As Long
    Dim DataType As Integer, data As String, msg As String
    
    ' Unique identifiers to distinguish our XRecordData from other XRecordData
    Const TYPE_STRING = 1
    Const TAG_DICTIONARY_NAME = "ObjectTrackerDictionary"
    Const TAG_XRECORD_NAME = "ObjectTrackerXRecord"

    ' Connect to the dictionary we store the XRecord in
    On Error GoTo create
    Set TrackingDictionary = ThisDrawing.Dictionaries(TAG_DICTIONARY_NAME)
    Set TrackingXRecord = TrackingDictionary.GetObject(TAG_XRECORD_NAME)
    On Error GoTo 0
    
    ' Get current XRecordData
    TrackingXRecord.GetXRecordData XRecordDataType, XRecordData
    
    ' If we don't have an array already then create one
    If VarType(XRecordDataType) And vbArray = vbArray Then
        ArraySize = UBound(XRecordDataType) + 1       ' Get the size of the data elements returned
        ArraySize = ArraySize + 1                        ' Increase to hold new data
    
        ReDim Preserve XRecordDataType(0 To ArraySize)
        ReDim Preserve XRecordData(0 To ArraySize)
    Else
        ArraySize = 0
        ReDim XRecordDataType(0 To ArraySize) As Integer
        ReDim XRecordData(0 To ArraySize) As Variant
    End If
    
    ' Append new XRecord Data
    '
    ' For this sample we only append the current time to the XRecord
    XRecordDataType(ArraySize) = TYPE_STRING: XRecordData(ArraySize) = CStr(Now)
    TrackingXRecord.SetXRecordData XRecordDataType, XRecordData
    
    ' Read back all XRecordData entries
    TrackingXRecord.GetXRecordData XRecordDataType, XRecordData
    ArraySize = UBound(XRecordDataType)
    
    ' Retrieve and display stored XRecordData
    For iCount = 0 To ArraySize
        ' Get information for this element
        DataType = XRecordDataType(iCount)
        data = XRecordData(iCount)
        
        If DataType = TYPE_STRING Then
            msg = msg & data & vbCrLf
        End If
    Next
    
    MsgBox "The data in the XRecord is: " & vbCrLf & vbCrLf & msg, vbInformation
    
    Exit Sub

create:
    ' Create the entities that hold our XRecordData
    If TrackingDictionary Is Nothing Then  ' Make sure we have our tracking object
        Set TrackingDictionary = ThisDrawing.Dictionaries.Add(TAG_DICTIONARY_NAME)
        Set TrackingXRecord = TrackingDictionary.AddXRecord(TAG_XRECORD_NAME)
    End If
    
    Resume
End Sub

Private Sub CommandButton2_Click()
    
    Dim TrackingDictionary As AcadDictionary, TrackingXRecord As AcadXRecord
    Dim XRecordDataType As Variant, XRecordData As Variant
    Dim ArraySize As Long, iCount As Long
    Dim DataType As Integer, data As String, msg As String
    
    ' Unique identifiers to distinguish our XRecordData from other XRecordData
    Const TYPE_STRING = 1
    Const TAG_DICTIONARY_NAME = "ObjectTrackerDictionary"
    Const TAG_XRECORD_NAME = "ObjectTrackerXRecord"

    ' Connect to the dictionary we store the XRecord in
    On Error GoTo create
    Set TrackingDictionary = ThisDrawing.Dictionaries(TAG_DICTIONARY_NAME)
    Set TrackingXRecord = TrackingDictionary.GetObject(TAG_XRECORD_NAME)
End Sub
Option Explicit

'使用擴展字典
'AutoCAD有兩種字典
'第一種：擴展字典——一種與具體的對象關聯的字典，每個對象僅能擁有一個擴展字典，
'                    其中可以保存與該對象有關的信息。
'第二種：命名對象字典(Named Object Dictionary)——用來保存與實體無關的數據，
'                    AutoCAD本身就使用對象命名字典來保存一些信息，例如組字典（保存編組的信息）
'                    多線樣式字典等。

'A 使用擴展字典的一般步驟：
'  保存信息的基本步驟：
'  1、使用GetExtensionDictionary方法創建一個對象的擴展字典
'  2、使用AddXData方法向擴展字典添加一條擴展記錄
'  3、使用SetXRecordData將數據保存在擴展記錄中。
'  讀取擴展字典的基本步驟：
'  1、使用GetExtensionDictionary獲取對象的擴展字典
'  2、使用GetObject方法獲得指定的擴展記錄
'  3、使用GetXRecordData讀取保存在擴展記錄中的數據。

'B 使用命名對象字典的一般步驟：
'  保存命名字典信息的基本步驟
'  1、使用Dictionaries.add添加一個命名對象字典
'  2、同A
'  3、同A
'  讀取命名對象字典的基本步驟：
'  1、使用對象的基本操作獲得Dictionaries集合中制定的字典
'  2、同A
'  3、同A

Public Function HasXRecord(ByVal ent As AcadEntity, ByVal key As String) As Boolean
  '判斷對象是否已經擁有擴展字典
  Dim objDict As AcadDictionary
  Dim objXRecord As AcadXRecord
 
  If ent.HasExtensionDictionary Then
    '獲得擴展字典
    Set objDict = ent.GetExtensionDictionary
   
    On Error Resume Next
    Set objXRecord = objDict.GetObject(key)
    Set objDict = Nothing
   
    If err Then
      err.Clear
      HasXRecord = False
    Else
      HasXRecord = True
    End If
  Else
    HasXRecord = False
  End If
   
End Function

Public Sub CreateXRecord(ByRef xDataType As Variant, ByRef xData As Variant, ParamArray Filter())
  '創建擴展記錄的數據集
  Debug.Assert (UBound(Filter) Mod 2 = 1)
 
  Dim Count As Integer
  Count = (UBound(Filter) + 1) / 2
  Dim DataType() As Integer, data() As Variant
  ReDim DataType(Count - 1)
  ReDim data(Count - 1)
 
  Dim i As Integer
  For i = 0 To Count - 1
    DataType(i) = Filter(2 * i)
    data(i) = Filter(2 * i + 1)
  Next i
    xDataType = DataType
    xData = data
End Sub

Public Sub AddXRecord(ByVal ent As AcadEntity, ByVal key As String, ByVal xDataType As Variant, ByVal xData As Variant)
  '向指定的實體添加擴展字典
  Dim objDict As AcadDictionary
  Dim objXRecord As AcadXRecord
 
  Set objDict = ent.GetExtensionDictionary()
  Set objXRecord = objDict.AddXRecord(key)
  objXRecord.SetXRecordData xDataType, xData
End Sub
  
Public Sub GetXRecord(ByVal ent As AcadEntity, ByVal key As String, ByRef xDataType As Variant, ByRef xData As Variant)
  '獲取擴展字典
  Dim objDict As AcadDictionary
  Dim objXRecord As AcadXRecord
 
  Set objDict = ent.GetExtensionDictionary
  Set objXRecord = objDict.GetObject(key)
  objXRecord.GetXRecordData xDataType, xData
End Sub

Public Function HasNamedDictionary(ByVal DictName As String, ByVal key As String) As Boolean
  '判斷是否已經存在鍵位dictName的字典
  On Error Resume Next
 
  Dim objDict As AcadDictionary
  Dim objXRecord As AcadXRecord
 
  Set objDict = ThisDrawing.Dictionaries(DictName)
  If err Then
    err.Clear
    HasNamedDictionary = False
  Else
    Set objXRecord = objDict.GetObject(key)
    If err Then
      err.Clear
      HasNamedDictionary = False
    Else
      HasNamedDictionary = True
    End If
  End If
End Function

Public Sub AddNamedDictionary(ByVal DictName As String, ByVal key As String, ByVal xDataType As Variant, ByVal xData As Variant)
  '用於向當前圖形添加指定的命名對象字典
  Dim objDict As AcadDictionary
  Dim objXRecord As AcadXRecord
 
  Set objDict = ThisDrawing.Dictionaries.Add(DictName)
  Set objXRecord = objDict.AddXRecord(key)
  objXRecord.SetXRecordData xDataType, xData
End Sub

Public Sub GetNamedDictionary(ByVal DictName As String, ByVal key As String, ByRef xDataType As Variant, ByRef xData As Variant)
  '從當前圖形中獲得指定的命名對象字典
  Dim objDict As AcadDictionary
  Dim objXRecord As AcadXRecord
 
  Set objDict = ThisDrawing.Dictionaries(DictName)
  Set objXRecord = objDict.GetObject(key)
  objXRecord.GetXRecordData xDataType, xData
End Sub

 

調用類:

Option Explicit

Public Sub AddEntXRecord()
  Dim ent As AcadEntity
  Dim PickPoint As Variant
 
  ThisDrawing.Utility.GetEntity ent, PickPoint, vbCr & "請選擇對象："
 
  Dim point(0 To 2) As Double
  SetPoint3d point, 100, 100, 0
 
  Dim xRecord As New clsXRecord
  Dim DataType As Variant, data As Variant
 
  xRecord.GetXRecord ent, "EX02", DataType, data
 
  Dim s As String
  s = data(1)
 
  xRecord.CreateXRecord DataType, data, _
      1, "道路", _
      8, ent.Layer, _
      40, PickPoint(0), _
      10, point
 
  If xRecord.HasXRecord(ent, "EX02") Then
    ThisDrawing.Utility.Prompt vbNewLine & "實體已經包含指定名稱的擴展記錄 "
  Else
    xRecord.AddXRecord ent, "EX02", DataType, data
    ThisDrawing.Utility.Prompt vbNewLine & "成功為實體添加擴展記錄 "
  End If
 
 
 
End Sub


Public Sub SetPoint3d(ByVal pt As Variant, ByRef x As Double, ByRef y As Double, ByRef Z As Double)
  ReDim pt(0 To 2) As Double
  pt(0) = x
  pt(1) = y
  pt(2) = Z
 
End Sub

Private Sub CommandButton3_Click()
    '把 textbox1 內的多文字，轉換成多個 AcadText
    Dim returnPnt As Variant
    
    Me.Hide
    returnPnt = ThisDrawing.Utility.GetPoint(, "選擇插入點： ")
    
    
    Dim textObj As AcadMText
    Dim textString As String
    Dim insertionPoint(0 To 2) As Double
    Dim height As Double
    Dim i As Integer
    
    For i = 1 To Len(Me.TextBox1.text)
        
        textString = MidB(Me.TextBox1.text, i, 1)
        insertionPoint(0) = returnPnt(0) + i * 10
        insertionPoint(1) = returnPnt(1)
        insertionPoint(2) = 0
        height = 3
    
        ' Create the text object in model space
        Set textObj = ThisDrawing.ModelSpace.AddMText(insertionPoint, 3, textString)
    Next
 
End Sub

Private Sub CommandButton4_Click()
    Dim returnObj As AcadObject
    Dim basePnt As Variant
    Dim arrStr As Variant
    On Error Resume Next
    
    ' The following example waits for a selection from the user
    Me.Hide
    ThisDrawing.Utility.GetEntity returnObj, basePnt, "Select an object"
    arrStr = Split(returnObj.textString, "\P")
    
    Dim textObj As AcadMText
    Dim textString As String
    Dim insertionPoint(0 To 2) As Double
    Dim height As Double
    Dim i As Integer
    
    For i = 0 To UBound(arrStr)
        
        textString = arrStr(i)
        insertionPoint(0) = basePnt(0) + 30
        insertionPoint(1) = basePnt(1) - (i * 5)
        insertionPoint(2) = 0
        height = 3
    
        ' Create the text object in model space
        Set textObj = ThisDrawing.ModelSpace.AddMText(insertionPoint, 5, textString)
        textObj.height = 5
    Next
    
End Sub

Private Sub UserForm_Click()

End Sub

Private Sub UserForm_Deactivate()

End Sub

Private Sub UserForm_ QueryClose(Cancel As Integer, CloseMode As Integer)

End Sub

Attribute VB_Name = "DataBuffer"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False

Option Explicit

'2013.03.17  V3 正要修改 二胡的版本，因程式之前是用古箏的指法圖，現在改成二胡的指法圖

Const mChar As String = "*|||||||"    ' 資料格式 '資料的前面字元有那些
Const TRACK_MAX As Integer = 5      '最大的音軌數

Dim mCharI() As Integer
Dim mMete As Integer        '每小節有幾拍
Dim mFontSize As Integer
Dim mTextnote() As String       '把每行資料放進來 這是有陣列的
Dim mmsa(0 To 1) As String
Dim mOpenATable_ As Boolean

Dim currentTextNotePos As Integer
Private Type t
    ln As Integer   '要記錄讀進來的資料是在文件裡的第幾 "行"
    WD As Integer   '要記錄貢進來的資料是在文件要的第幾 "字"
End Type




Private Type KeyFormat
    typs As Cg
    mtone As String       '星指法
    mfingering As String  '指法
    mnote As String           '高低音
    mscale As String          '音階
    mtempo As String         '拍子
    duration As Integer            '拍子的延遲長度
    mtow_fingering As String  '指法 第二個
    mslur As String           '連音符
    mand As String               '記錄合音 true為跟後面一音合音 ,false為沒有
    what As Integer             '記錄一些不一樣的指法
    
'    textdata As String
    
'    mfPosition As Double    '這是看這字上下移多少
'    mnPosition As Double    '這是看這字上下移多少
'    msPosition As Double     '這是看這字上下移多少
'    mtPosition As Double    '這是看這字上下移多少
'    mtow_fPosition As Double   '這是看 指法 第二個 這字上下移多少
'    mslPosition As Double    '連音符 字上下移多少
    
    ln As Integer   '要記錄讀進來的資料是在文件裡的第幾 "行"
    WD As Integer   '要記錄貢進來的資料是在文件要的第幾 "字"
End Type


Dim mMusic() As MusicItemList  'voiceFormat                '了解嗎
'Dim mSize() As Long '現在的 mMusic() as KeyFormat 的物件數量
Dim pos(10) As Long '記錄現在到那個元素
Dim lastDuration As Double ''記錄上一次的長度
'Dim mLogSize() As Long '現在的 mMusic() 的空白陣列 的數量
Dim author As String    '作者
Dim title As String     '標題

Dim GroupABCLists(8)  As VoiceABCList

Property Get getTITLE() As String
    getTITLE = title
End Property

Public Sub init()
    Dim i As Integer
    For i = 0 To 10
        pos(i) = 0
    Next
End Sub


Private Sub Class_Initialize()
    'ReDim mMusic(TRACK_MAX)
    'ReDim mMusic(TRACK_MAX, 100)
    ReDim mSize(TRACK_MAX)
    ReDim mLogSize(TRACK_MAX)
    Dim i As Integer
    ReDim mMusic(0)
    
    Set mMusic(0) = New MusicItemList
    
    
    ReDim mTextnote(amt.mHowData)
    ReDim mCharI(amt.mHowData)
End Sub
Sub Clear()
    Class_Initialize
End Sub
Private Sub initMusicMain(nTrack As Integer)
    If UBound(mMusic) < nTrack Then
        ReDim Preserve mMusic(nTrack)
        
        Set mMusic(nTrack) = New MusicItemList
    
    End If
End Sub
Private Function joinFormation(mTextnote() As String) As MusicNoteItemList
    Dim moeList As New MusicNoteItemList
    Dim moe As MusicNoteItem
    Dim c() As String
    ReDim c(UBound(mTextnote))
    Dim j As Integer
    Dim pos As Integer
    '取得資料
    For pos = 1 To Len(mTextnote(amt.iNote))
        For j = amt.iTONE To Len(mChar)
            c(j) = Mid(mTextnote(j), pos, 1)
            If c(j) = "" Then c(j) = " "
        Next

        If c(amt.iNote) <> "" Then
            Set moe = New MusicNoteItem
            moe.typs = Cg.note
            moe.mtone = c(amt.iTONE)             ' * 行
            moe.mnote = c(amt.iNote)                  '這為主行       1234567.|l
            moe.mfingering = c(amt.iFinge)       '這是指法行     _+)(*&
            moe.mtow_fingering = c(amt.iTowFinge) '這是指法行第二行  _+)(*&
            moe.mtempo = c(amt.iTempo)            '這是拍子       -=368acefz
            moe.mscale = c(amt.iScale)            '這是高低音行   .,:
            moe.mslur = c(amt.iSlur)
            moe.mand = c(amt.iAdd)
            
            moeList.Push moe
        End If
        
    Next
    Set joinFormation = moeList

End Function

Private Sub SetMusicNoteFormation(moeList() As MusicNoteItemList)
'nTrack as integer '要轉換到第幾個音軌資料
'ln As Integer   '要記錄讀進來的資料是在文件裡的第幾 "行"
'wd As Integer   '要記錄貢進來的資料是在文件要的第幾 "字"
    Dim nTrack As Integer
    Dim pos As Integer
    Dim j As Integer
    Dim lsup As Integer
    Dim count_tuplet As Integer
    Dim flueTuplet As Boolean

    Dim objMusic As MusicItem
    Dim c As MusicNoteItem
    Dim sc As MusicNoteItem
    Dim isAdd As Boolean
    Dim isDots As Boolean
    Dim isRest As Boolean
    
    
    Dim extraList As MusicNoteItemList
    Dim isExtra As Boolean
    
    count_tuplet = 0
    flueTuplet = False
    For nTrack = 0 To UBound(moeList)
        initMusicMain nTrack
        
        For pos = 0 To moeList(nTrack).Count - 1
'            Debug.Print "sMNFOR  ", , nTrack, "  ", pos
'            If pos = 1503 Then
'                pos = pos
'            End If
            '取得資料
            Set c = moeList(nTrack)(pos)
            isDots = False

            If c.typs = Cg.Config Then
                noteConfigSet nTrack, c
                GoTo nogood
            End If
            Select Case c.mnote  '這是音階
                Case "."
                    isDots = True
                Case "Z"
                    '合併小節 Z
                    restConfigSet nTrack, c
                    GoTo nogood
                Case "|"
                        GoTo nogood
                Case " ", ""
                        GoTo nogood
            End Select
            
            If c.mand = "]" Then
                isAdd = False
                If isDots Then
                    objMusic.dots = 1
                Else
                    objMusic.typs = Cg.note
                    objMusic.notes.Push c
                End If
                
                Set objMusic = calDuration2(objMusic, lastDuration)
                mMusic(nTrack).Push objMusic
                
            ElseIf c.mand = "[" Or isAdd = True Then
                If c.mand = "[" Then
                    Set objMusic = New MusicItem
                    Set objMusic.notes = New MusicNoteItemList
                End If
                If isDots Then
                    objMusic.dots = 1
                Else
                    objMusic.typs = Cg.note
                    objMusic.notes.Push c
                End If
                
                isAdd = True
                Set objMusic = calDuration2(objMusic, lastDuration)
            ElseIf c.mtow_fingering = ">" Then
            '前墜字
                If isExtra = False Then
                    Set objMusic = Nothing
                    Set extraList = New MusicNoteItemList
                    isExtra = True
                End If
                extraList.Push c
                
            ElseIf c.mtow_fingering = "<" Then
            '後墜字
                    Set objMusic = mMusic(nTrack).Last
                    If objMusic.rightObjs Is Nothing Then
                        Set objMusic.rightObjs = New MusicNoteItemList
                    End If
                    objMusic.rightObjs.Push c
            Else
                If isDots Then
                    Set objMusic = mMusic(nTrack).Last
                    objMusic.dots = 1
                Set objMusic = calDuration2(objMusic, lastDuration)
                Else
                    
                    Set objMusic = New MusicItem
                    Set objMusic.notes = New MusicNoteItemList
                    
                    objMusic.typs = Cg.note
                    objMusic.notes.Push c
                    Set objMusic = calDuration2(objMusic, lastDuration)
                    mMusic(nTrack).Push objMusic
                End If
            End If
            
            If Not objMusic Is Nothing And isExtra = True Then
                '這是看如有前墜字物件後，有產生 MusicItem
                '就加入前墜字 給 MusicItem
                Set objMusic.extraObjs = extraList
                Set extraList = Nothing
                isExtra = False
                
            End If
            'calExtraw objMusic
        
            If c.mslur = "[" Or c.mslur = "(" Then
                objMusic.slurStart = True       '二胡連音線，(古箏是合音)
            ElseIf c.mslur = "]" Or c.mslur = ")" Then
                objMusic.slurEnd = True
            End If
            
            
            If c.mslur = "{" Then
                objMusic.tupletStart = True        '多連音線
                flueTuplet = True
                count_tuplet = 1
            ElseIf c.mslur = "}" Then
                objMusic.tupletEnd = True
                count_tuplet = count_tuplet + 1
                objMusic.tupletCount = count_tuplet
                count_tuplet = 0
                flueTuplet = False
            ElseIf flueTuplet = True Then
                count_tuplet = count_tuplet + 1
            End If
            
            
            'objMusic.ln = ln  '寫入第幾行
            'objMusic.WD = i   '寫入第幾字
            
nogood:
        Next pos
    Next nTrack
End Sub

Private Sub noteConfigSet(nTrack As Integer, c As MusicNoteItem)
    
    Dim kk As String
    Dim regEx As New RegExp
    regEx.Global = True
    
    If c.configText <> "" Or c.configText <> " " Then
        kk = Mid(c.configText, 1, 1)
        If kk = "M" Then
            '記錄拍號

            Dim meteMatches
            Dim musicIt As MusicItem
            Set musicIt = New MusicItem
            regEx.Pattern = "(\d+)/(\d+)"
            Set meteMatches = regEx.Execute(c.configText)

            If meteMatches.Count >= 1 Then
                musicIt.typs = Cg.meter
                musicIt.mete = meteMatches(0).SubMatches(0)
                musicIt.mete2 = meteMatches(0).SubMatches(1)
            End If
            mMusic(nTrack).Push musicIt
        ElseIf kk = "I" Then
            '設定每行幾小節
            
            Dim regMatches
            Dim rMusicItem As MusicItem
            Set rMusicItem = New MusicItem
            
            regEx.Pattern = ":setbar[\s]+(\d+)\s*?/\s*?(\d+)"
            Set regMatches = regEx.Execute(c.configText)
            If regMatches.Count = 1 Then
                rMusicItem.typs = Cg.Config
                '設定第x節開始，設定每行幾小節
                If regMatches(0).SubMatches.Count = 2 Then
                    rMusicItem.setbarstaffid = regMatches(0).SubMatches(0)
                    rMusicItem.setbarstaff = regMatches(0).SubMatches(1)
                End If
            End If
        
            regEx.Pattern = ":bar[\s]+(\d+)"
            Set regMatches = regEx.Execute(c.configText)
            If regMatches.Count = 1 Then
                rMusicItem.typs = Cg.Config
                rMusicItem.barsperstaff = regMatches(0).SubMatches(0) '設定每行幾小節
            End If
            
            '設定第 x 小節強制換行
            regEx.Pattern = ":linebreak[\s]+(\d+)"
            Set regMatches = regEx.Execute(c.configText)
            If regMatches.Count = 1 Then
                rMusicItem.typs = Cg.Config
                rMusicItem.barlinebreak = regMatches(0).SubMatches(0)
            End If
            
            '設定第 x 小節強制換頁，小節數重 1 開始
            regEx.Pattern = ":pagebreak[\s]+(\d+)"
            Set regMatches = regEx.Execute(c.configText)
            If regMatches.Count = 1 Then
                rMusicItem.typs = Cg.Config
                rMusicItem.barpagebreak = regMatches(0).SubMatches(0)
            End If
            
            
            
            
            mMusic(nTrack).Push rMusicItem
            
            

        End If
    End If


End Sub
Private Sub restConfigSet(nTrack As Integer, c As MusicNoteItem)
'休子符,小節合併
    Dim rMusicItem As MusicItem
    Set rMusicItem = New MusicItem
    
    
    If c.mnote = "Z" Then
        rMusicItem.typs = Cg.rest
        Set rMusicItem.rest = New aRestItem
        rMusicItem.rest.typs = "multimeasure"
        rMusicItem.rest.text = CharToValue(c.mtempo)
        rMusicItem.rest.barNumber = CharToValue(c.mtempo)
    End If
    
    mMusic(nTrack).Push rMusicItem
            
End Sub



Private Function getChars(mTextnote() As String, pos As Integer) As String()
    Dim c() As String
    ReDim c(UBound(mTextnote))
    Dim j As Integer
            '取得資料
        For j = amt.iTONE To Len(mChar)
            
            c(j) = Mid(mTextnote(j), pos, 1)
            If c(j) = "" Then c(j) = " "
        Next j
        getChars = c
End Function
Private Sub SetMusicItem(nTrack As Integer, ln As Integer, WD As Integer)
'nTrack as integer '要轉換到第幾個音軌資料
'ln As Integer   '要記錄讀進來的資料是在文件裡的第幾 "行"
'wd As Integer   '要記錄貢進來的資料是在文件要的第幾 "字"
    Dim c() As String
    ReDim c(amt.mHowData)
    Dim i As Integer
    Dim j As Integer
    Dim lsup As Integer
    

    
    '迴圈每個字
    Dim a As String
    
    'Dim spaceMusic As voiceFormat   '空白
    'Dim spaceNote(0) As noteFormat     '空白
    'ReDim Preserve spaceMusic.notes(0)
    Dim objMusic As MusicItem
    Dim objNote As MusicNoteItem
    
    Dim c_TONE As String
    Dim c_Note As String
    Dim c_Finge As String
    Dim c_TowFinge As String
    Dim c_Tempo As String
    Dim c_Scale As String
    Dim c_Slur As String
    Dim c_Add As String
    Dim isAdd As Boolean
    remMusic nTrack
    For i = 1 To Len(mTextnote(amt.iNote))
        '取得資料
        c = getChars(mTextnote, i)
        Debug.Print "mTextnote(amt.iNote) i: " & i
        If i = 3 Then
            i = i
        End If
        
'        c_TONE = c(AMT.iTONE)      ' * 行
'        c_Note = c(AMT.iNote)      '這為主行       1234567.|l
'        c_Finge = c(AMT.iFinge)    '這是指法行     _+)(*&
'        c_TowFinge = c(AMT.iTowFinge) '這是指法行第二行  _+)(*&
'        c_Tempo = c(AMT.iTempo)    '這是拍子       -=368acefz
'        c_Scale = c(AMT.iScale)    '這是高低音行   .,:
'        c_Slur = c(AMT.iSlur)      '二胡連音線，(古箏是合音)
'
        
        Select Case c(amt.iNote)     '這是音階
            Case "0", "1", "2", "3", "4", "5", "6", "7"
                c_Note = c(amt.iNote)
            Case "."
                'c_Note = c(amt.iNote)
                Dim uu As Integer
                For uu = mMusic(nTrack).Count - 1 To 0 Step -1
                    If mMusic(nTrack)(uu).duration > 0 Then
                        Set objMusic = mMusic(nTrack)(uu)
                        objMusic.identify_Duration objMusic.duration * 1.5
                        'objMusic.calMeWidth
                        GoTo nogood
                    End If
                Next

            Case "-"
                c_Note = c(amt.iNote)
            Case "|"
                If i = 1 Then
'lin'               mSize(ntrack) = mSize(ntrack) - 1
                    GoTo nogood
                End If
                c_Note = c(amt.iNote)
            Case " ", ""
'lin'               mSize(ntrack) = mSize(ntrack) - 1
                    GoTo nogood
            Case Else
                c_Note = c(amt.iNote)
        End Select
        
        
        Select Case c(amt.iFinge)     '這是指法
            Case " "
            Case "("
            Case "|"
            
            Case "a" To "z", "A" To "Z", "-", "="
            Case Chr(21) To Chr(125)
                c_Finge = c(amt.iFinge)
            Case Else
                c_Finge = c(amt.iFinge)
        End Select
            
        Select Case c(amt.iTowFinge)     '這是指法2 第二行
            Case "a" To "z", "A" To "Z", "-", "="
                c_TowFinge = c(amt.iTowFinge)
            Case "1" To "7"
                c_TowFinge = c(amt.iTowFinge)
            Case " ", "(", "|"
                c_TowFinge = c(amt.iTowFinge)
            Case Else
                c_TowFinge = c(amt.iTowFinge)
        End Select
        

        Select Case c(amt.iTempo)     '這是拍子
            Case " "
                c_Tempo = c(amt.iTempo)
            Case "-", "2"
                c_Tempo = c(amt.iTempo)
            Case "=", "4", "3"
                c_Tempo = c(amt.iTempo)
            Case "6", "8", "A"
                c_Tempo = c(amt.iTempo)
            Case "|"
                c_Tempo = c(amt.iTempo)
            Case Else
                IsEmpty c(amt.iTempo)
                c_Tempo = c(amt.iTempo)
        End Select
        
        
        c_TONE = c(amt.iTONE)
        c_Scale = c(amt.iScale)
        c_Slur = c(amt.iSlur)   '滑音行
        c_Finge = c(amt.iFinge)
        c_Add = c(amt.iAdd)     '合音行
        
        Set objNote = New MusicNoteItem
        
        objNote.mtone = c_TONE     ' * 行
        objNote.mnote = c_Note      '這為主行       1234567.|l
        objNote.mfingering = c_Finge    '這是指法行     _+)(*&
        objNote.mtow_fingering = c_TowFinge  '這是指法行第二行  _+)(*&
        objNote.mtempo = c_Tempo   '這是拍子       -=368acefz
        objNote.mscale = c_Scale   '這是高低音行   .,:
        


        
        If c_Add = "]" Then
            isAdd = False
            objMusic.typs = Cg.note
            objMusic.notes.Push objNote
            objMusic.mtempo = c_Tempo   '這是拍子       -=368acefz
            lastDuration = calDuration(objMusic, lastDuration)
            objMusic.identify_Duration lastDuration
            mMusic(nTrack).Push objMusic
        ElseIf c_Add = "[" Or isAdd = True Then
            If c_Add = "[" Then
                Set objMusic = New MusicItem
                Set objMusic.notes = New MusicNoteItemList
            End If
            isAdd = True
            objMusic.typs = Cg.note
            objMusic.notes.Push objNote
            objMusic.mtempo = c_Tempo   '這是拍子       -=368acefz
            lastDuration = calDuration(objMusic, lastDuration)
            objMusic.identify_Duration lastDuration
        Else
            Set objMusic = New MusicItem
            Set objMusic.notes = New MusicNoteItemList
            
            objMusic.typs = Cg.note
            objMusic.notes.Push objNote
            objMusic.mtempo = c_Tempo   '這是拍子       -=368acefz
            lastDuration = calDuration(objMusic, lastDuration)
            objMusic.identify_Duration lastDuration
            mMusic(nTrack).Push objMusic
        End If
        ''calExtraw objMusic
    
        If c_Slur = "[" Or c_Slur = "(" Then
            objMusic.slurStart = True       '二胡連音線，(古箏是合音)
        ElseIf c_Slur = "]" Or c_Slur = ")" Then
            objMusic.slurEnd = True
        End If
        
        
        objMusic.ln = ln  '寫入第幾行
        objMusic.WD = i   '寫入第幾字
        
nogood:
    Next i
End Sub
Private Sub clearTextNote(mTextnote() As String)
    Dim i As Integer
    For i = 0 To UBound(mTextnote) - 1
        mTextnote(i) = ""
    Next
End Sub
 Public Sub LoadDataToBuf(the_data As String)
' 從檔案中讀取一列字串放到特定位置,讀到'*'離開
    Dim nTrack As Integer
    Dim tmp_ntrack As Integer
    
    
    Dim cc As String
    Dim mcc As String
    '一行一行的分開，放入 tmp_str
    Dim valText As Variant
    
    Dim ln As Integer
    
    
    Dim pos As Integer
    Dim ko As Integer
    Dim findSt As Integer
    Dim findEnd As Integer
    Dim regEx As New RegExp
    regEx.Global = True
    Dim MusicNoteFormation() As New MusicNoteItemList
    Dim moe As MusicNoteItem
    
    
    
    If the_data = "" Then
        MsgBox ("沒有資料")
        Exit Sub
    End If
    
    valText = Split(the_data, vbCrLf)
    nTrack = -1
    tmp_ntrack = -1
    
    For ln = 0 To UBound(valText)
        cc = VBA.Mid(valText(ln), 1, 1)
        mcc = valText(ln)
        If cc = "<" Then
            If nTrack >= 0 Then
                MusicNoteFormation(nTrack).PushArray joinFormation(mTextnote)
            End If
            If nTrack = -1 Then
                findSt = InStr(1, mcc, "<")
                findEnd = InStr(1, mcc, ">")
                title = Mid(mcc, findSt + 1, findEnd - findSt - 1)
                
            End If
            
            clearTextNote mTextnote
            nTrack = nTrack + 1
            ReDim Preserve MusicNoteFormation(nTrack)
            Set MusicNoteFormation(nTrack) = New MusicNoteItemList
        ElseIf cc = "*" Then
            MusicNoteFormation(nTrack).PushArray joinFormation(mTextnote)
            clearTextNote mTextnote
            
            pos = amt.iTONE
            mTextnote(pos) = mcc
        ElseIf cc = "|" Then
            pos = pos + 1
            mTextnote(pos) = mcc
                        
        ElseIf cc = "M" Or cc = "I" Then
            MusicNoteFormation(nTrack).PushArray joinFormation(mTextnote)
            clearTextNote mTextnote
            
            Set moe = New MusicNoteItem
            moe.typs = Cg.Config
            moe.configText = mcc
            '記錄拍號
            MusicNoteFormation(nTrack).Push moe
            
        End If
    Next
    MusicNoteFormation(nTrack).PushArray joinFormation(mTextnote)
    clearTextNote mTextnote
    SetMusicNoteFormation MusicNoteFormation
    'Call SetMusicItem(nTrack, ln, 1) '轉換成物件資料
    'Call SetMusicItemToABC(ntrack, i, 1)
    
    
    
    
End Sub
'
' Public Sub LoadDataToBuf(the_data As String)
'' 從檔案中讀取一列字串放到特定位置,讀到'*'離開
'    Dim ntrack As Integer
'    Dim tmp_ntrack As Integer
'    Dim buf_i(2000) As String
'    Dim tab_m As Integer, vol As Integer
'    Dim name(256) As String
'    Dim p As String
'
'
'    Dim cc As String
'    Dim mcc As String
'    '一行一行的分開，放入 tmp_str
'    Dim valText As Variant
'    Dim numPC As Integer
'    Dim ln As Integer
'    If the_data = "" Then
'        MsgBox ("沒有資料")
'        Exit Sub
'    End If
'
'    valText = Split(the_data, vbCrLf)
'    ntrack = -1
'    tmp_ntrack = -1
'    numPC = UBound(valText)
'    Dim pos As Integer
'    Dim ko As Integer
'    Dim findSt As Integer
'    Dim findEnd As Integer
'    Dim regEx As New RegExp
'    regEx.Global = True
'    Dim MusicNoteFormation As New MusicNoteItemList
'
'
'
'
'    For ln = 0 To numPC
'        cc = VBA.Mid(valText(ln), 1, 1)
'        mcc = valText(ln)
'        Debug.Print "ln: " & ln
'
'        If cc = "<" Then
'            If ntrack >= 0 Then
'                MusicNoteFormation.PushArray joinFormation(mTextnote)
'                'Call SetMusicItem(ntrack, ln, 1) '轉換成物件資料
'                'Call SetMusicItemToABC(ntrack, i, 1)
'            End If
'            If ntrack = -1 Then
'                findSt = InStr(1, mcc, "<")
'                findEnd = InStr(1, mcc, ">")
'                title = Mid(mcc, findSt + 1, findEnd - findSt - 1)
'            End If
'
'            clearTextNote mTextnote
'            ntrack = ntrack + 1
'        ElseIf cc = "*" Then
'            MusicNoteFormation.PushArray joinFormation(mTextnote)
'            'Call SetMusicItem(ntrack, ln, 1) '轉換成物件資料
'            'Call SetMusicItemToABC(ntrack, i, 1)
'            clearTextNote mTextnote
'
'            pos = amt.iTONE
'            mTextnote(pos) = mcc
'        ElseIf cc = "|" Then
'            pos = pos + 1
'            mTextnote(pos) = mcc
'
'        ElseIf cc = "M" Then
'            '記錄拍號
'            MusicNoteFormation.PushArray joinFormation(mTextnote)
'            'Call SetMusicItem(ntrack, ln, 1) '轉換成物件資料
'            'Call SetMusicItemToABC(ntrack, i, 1)
'            clearTextNote mTextnote
'
'            Dim meteMatches
'            Dim musicIt As MusicItem
'            Set musicIt = New MusicItem
'            regEx.Pattern = "(\d+)/(\d+)"
'            Set meteMatches = regEx.Execute(valText(ln))
'
'            If meteMatches.Count >= 1 Then
'                musicIt.typs = Cg.meter
'                musicIt.mete = meteMatches(0).SubMatches(0)
'                musicIt.mete2 = meteMatches(0).SubMatches(1)
'            End If
'            mMusic(ntrack).Push musicIt
'        ElseIf cc = "I" Then
'            '設定每行幾小節
'            MusicNoteFormation.PushArray joinFormation(mTextnote)
'            'Call SetMusicItem(ntrack, ln, 1) '轉換成物件資料
'            clearTextNote mTextnote
'            Dim regMatches
'            Dim rMusicItem As MusicItem
'            Set rMusicItem = New MusicItem
'            regEx.Pattern = "bar[\s]+(\d+)"
'            Set regMatches = regEx.Execute(valText(ln))
'
'            If regMatches.Count >= 1 Then
'                rMusicItem.typs = Cg.Config
'                rMusicItem.barsperstaff = regMatches(0).SubMatches(0) '設定每行幾小節
'
'            End If
'            mMusic(ntrack).Push rMusicItem
'        End If
'    Next
'
'    Call SetMusicItem(ntrack, ln, 1) '轉換成物件資料
'    'Call SetMusicItemToABC(ntrack, i, 1)
'
'
'
'
'End Sub


Function GetTrackSize() As Integer
'取得有多少軌
'    Dim i As Integer
'    For i = 0 To TRACK_MAX
'        If mSize(i) < 3 Then
'            GetTrackSize = i
'            Exit Function
'        End If
'    Next
'    GetTrackSize = TRACK_MAX
    GetTrackSize = UBound(mMusic) + 1
End Function

Public Function GetTrackBufferSize(the_track As Integer) As Long
'取得每軌有多少音符
    GetTrackBufferSize = mMusic(the_track).Count
End Function
Function GetData(the_track As Integer, the_item As Long) As MusicItem
    'the_track 第幾部
    'the_item 第幾個
    Dim tmp_s As String
    Dim i As Integer
    Dim musList As MusicItemList
    If UBound(mMusic) >= the_track Then
        'Set musList = mMusic(the_track)
        If mMusic(the_track).Count >= the_item Then
            Set GetData = mMusic(the_track)(the_item)
            Exit Function
        End If
    End If
    
    Set GetData = Nothing

End Function
Function GetDataPos(the_track As Integer) As MusicItem
    'the_track 第幾部
    'the_item 第幾個
    Dim tmp_s As String
    Dim i As Integer
    Dim musItem As MusicItemList
    If (mSize(the_track) > 1 And mSize(the_track) > pos(the_track)) Then
        Set musItem = mMusic(the_track)
        Set GetDataPos = musItem(pos(the_track))
        pos(the_track) = pos(the_track) + 1
    End If
End Function

Private Function ConverRegexList(arrCode As iArray, comparValue As String) As String
    Dim sarr() As String
    Dim i As Integer
    Dim rstr As String

        For i = 0 To arrCode.Count - 1
'            sarr = Split(arrCode(i), " ")
'            If iLe = sarr(0) Then
'                rstr = sarr(1)
'                Exit For
'            Else
'                rstr = cc
'            End If
        Next
    ConverRegexList = rstr
End Function
Private Function initTextNoteData() As Boolean
    currentTextNotePos = 1
End Function
Private Function getTextNoteNextKF() As KeyFormat
    Dim j As Integer
    Dim c() As String
    ReDim c(amt.mHowData)
        For j = amt.iTONE To Len(mChar)
            c(j) = Mid(mTextnote(j), currentTextNotePos, 1)
            If c(j) = "" Then c(j) = " "
        Next j
        Dim kg As KeyFormat
        kg.mtone = c(amt.iTONE)
        kg.mnote = c(amt.iNote)
        kg.mfingering = c(amt.iFinge)
        kg.mtow_fingering = c(amt.iTowFinge)
        kg.mscale = c(amt.iScale)
        kg.mtempo = c(amt.iTempo)
        kg.mand = c(amt.iAdd)
        kg.mslur = c(amt.iSlur)
        getTextNoteNextKF = kg
End Function
Private Function updateTextNoteData() As Boolean
        If currentTextNotePos <= Len(mTextnote(amt.iNote)) Then
            currentTextNotePos = currentTextNotePos + 1
            updateTextNoteData = True
        Else
            updateTextNoteData = False
        End If
End Function
Private Function getTempoConverDuration(str As String) As Double
    '拍子的 字元 轉 成  duration
    
    Dim tempo_hj As String
    Dim tempo_val As Variant
    Dim tempo_ll As Variant
    
    tempo_hj = " -2=45368aAcCfFgGzZ"
    tempo_ll = Array(1, 2, 2, 4, 4, 5, 3, 6, 8, 10, 10, 12, 12, 15, 15, 16, 32, 32)
    tempo_val = Array(0, 1, 1, 2, 2, 2, 2, 2, 3, 3, 3, 4, 4, 4, 4, 4, 4, 4, 4)
    

    Dim ii As Integer
    Dim cn As String
    Dim val As Integer
    
    For ii = 0 To Len(tempo_hj) - 1
        cn = Mid(tempo_hj, ii + 1, 1)
        If cn = str Then
            val = tempo_ll(ii)
            getTempoConverDuration = 1 / (val * 4)
            Exit Function
        End If
    Next ii
    
End Function
Private Function getNoteConverPitch(str As String) As Double
    '高低音 的 字元 轉 成
    
    Dim tempo_hj As String
    Dim tempo_val As Variant
    Dim tempo_ll As Variant
    
    tempo_hj = "?;, .:!"
    tempo_ll = Array(-3, -2, -1, 0, 1, 2, 3)
    Dim ii As Integer
    Dim cn As String
    Dim val As Integer
        
    For ii = 0 To Len(tempo_hj) - 1
        cn = Mid(tempo_hj, ii + 1, 1)
        If cn = str Then
            val = tempo_ll(ii)
            getNoteConverPitch = 7 * val
            Exit Function
        End If
    Next ii
End Function
Private Function converMITABC(GroupABCs As VoiceABCList, vABC As VoiceABC, kf As KeyFormat) As VoiceABC
        Select Case kf.mnote     '這是音階
            Case "0"
                If (vABC.rest Is Nothing) Then
                    Set vABC.rest = New vrestNote
                End If
                vABC.el_typs = "note"
                vABC.rest.typs = "rest"
                vABC.duration = getTempoConverDuration(kf.mtempo)
                
            Case "1", "2", "3", "4", "5", "6", "7"
                Dim pitEle As vpitchesNote
                
                If (vABC.pitches Is Nothing) Then
                    Set vABC.pitches = New vpitchesNoteList
                End If
                Set pitEle = New vpitchesNote
                pitEle.Name = kf.mnote
                pitEle.pitch = CInt(kf.mnote) - 1 + getNoteConverPitch(kf.mscale)
                pitEle.verticalPos = pitEle.pitch
                pitEle.highestVert = pitEle.pitch + 6
                
                vABC.el_typs = "note"
                vABC.duration = getTempoConverDuration(kf.mtempo)
                vABC.pitches.Push pitEle
            Case "-"
                Set vABC = GroupABCs.Last
                vABC.duration = (1 / 4)
                vABC.pitches(0).Name = "-"
            Case "."
                Set vABC = GroupABCs.Last
                If (vABC.dots > 0) Then
                    Dim m As Integer
                    Dim d, f As Double
                        d = 1: f = 1
                    For m = 0 To vABC.dots - 1
                        f = f + d / 2
                        d = d / 2
                    Next
                    d = vABC.duration / f
                    vABC.dots = vABC.dots + 1
                    f = d
                    For m = 0 To vABC.dots
                        f = f + d / 2
                        d = d / 2
                    Next
                    vABC.duration = f
                Else
                    vABC.dots = 1
                    vABC.duration = vABC.duration + vABC.duration / 2
                End If
                Set vABC = Nothing

            Case "|", ":", "[", "]"
                Dim lastABC As VoiceABC
                Dim regEx As New RegExp
                
                ' 設定匹配規則
                regEx.Pattern = "[\[\]\|:]"
                Set lastABC = GroupABCs.Last
                If regEx.Test(lastABC.Name) Then
                    Set vABC = lastABC
                End If
                vABC.el_typs = "bar"
                vABC.Name = vABC.Name + kf.mnote
                
                Select Case vABC.Name
                    Case "|": vABC.typs = "bar_thin"
                    Case "||": vABC.typs = "bar_thin_thin"
                    Case ":|": vABC.typs = "bar_right_repeat"
                    Case "|:": vABC.typs = "bar_left_repeat"
                    Case ":|:": vABC.typs = "fasfasdfasf"
                    Case "[|": vABC.typs = "bar_thin_thick"
                    Case "|]": vABC.typs = "bar_thin_thick"
                    Case Else: vABC.typs = "bar_thin"
                End Select
                
            Case " ", ""
                Set vABC = Nothing
            Case Else
                Set vABC = Nothing
        End Select

        Set converMITABC = vABC
End Function
Private Function SetMusicItemToABC(nTrack As Integer, ln As Integer, WD As Integer) As VoiceABCList
'nTrack as integer '要轉換到第幾個音軌資料
'ln As Integer   '要記錄讀進來的資料是在文件裡的第幾 "行"
'wd As Integer   '要記錄貢進來的資料是在文件要的第幾 "字"
    Dim c() As String
    ReDim c(amt.mHowData)
    Dim i As Integer, j As Integer, k As Integer
    Dim lsup As Integer
    Dim ilo As Integer
    
    '看陣列夠不夠
'    If mSize(ntrack) + Len(mTextNote(amt.iNote)) > UBound(mMusic, 2) Then
'        ReDim Preserve mMusic(TRACK_MAX, UBound(mMusic, 2) * 2)
'    End If
    
    '迴圈每個字
    Dim a As String
    
    'Dim spaceMusic As voiceFormat   '空白
    'Dim spaceNote(0) As noteFormat     '空白
    'ReDim Preserve spaceMusic.notes(0)
    Dim objMusic As MusicItem
    Dim objNote As MusicNoteItem
    
    Dim c_TONE As String
    Dim c_Note As String
    Dim c_Finge As String
    Dim c_TowFinge As String
    Dim c_Tempo As String
    Dim c_Scale As String
    Dim c_Slur As String
    Dim c_Add As String
    Dim isAdd As Boolean

    Dim pit As New vpitchesNote
    Dim lastABC As VoiceABC       '記錄上一個音符元件
        
    
    Dim kf As KeyFormat
    Dim vABC As VoiceABC
    Dim pitEle As vpitchesNote
    Dim lastPitchs As vpitchesNoteList '記錄上一個音符元件
    Dim lastPitch As vpitchesNote
    Dim curABCList As VoiceABCList
    
    If GroupABCLists(nTrack) Is Nothing Then
        Set GroupABCLists(nTrack) = New VoiceABCList
    End If
    
        Set curABCList = GroupABCLists(nTrack)
    
    initTextNoteData
    Do
        kf = getTextNoteNextKF
        If curABCList.Count = 84 Then
             a = a
        End If
        
        Select Case kf.mand
            Case "["
                isAdd = True
                Set vABC = New VoiceABC
                Set vABC = converMITABC(curABCList, vABC, kf)
                If Not (vABC Is Nothing) Then
                    curABCList.Push vABC
                End If
                
            Case "]"
                isAdd = False
                Set vABC = curABCList.Last
                Set vABC = converMITABC(curABCList, vABC, kf)
            Case " "
                If isAdd = True Then
                    Set vABC = curABCList.Last
                    Set vABC = converMITABC(curABCList, vABC, kf)
                Else
                    Set vABC = New VoiceABC
                    Set vABC = converMITABC(curABCList, vABC, kf)
                    If Not (vABC Is Nothing) Then
                        curABCList.Push vABC
                    End If
                End If
            Case Else
        End Select
    
    Loop Until updateTextNoteData = False
    Set SetMusicItemToABC = curABCList
    i = 8
'
'    For i = 1 To Len(mTextNote(amt.iNote))
'
'        '取得資料
'        For j = amt.iTONE To Len(mChar)
'            C(j) = Mid(mTextNote(j), i, 1)
'            If C(j) = "" Then C(j) = " "
'        Next j
'
'
''        c_TONE = c(AMT.iTONE)      ' * 行
''        c_Note = c(AMT.iNote)      '這為主行       1234567.|l
''        c_Finge = c(AMT.iFinge)    '這是指法行     _+)(*&
''        c_TowFinge = c(AMT.iTowFinge) '這是指法行第二行  _+)(*&
''        c_Tempo = c(AMT.iTempo)    '這是拍子       -=368acefz
''        c_Scale = c(AMT.iScale)    '這是高低音行   .,:
''        c_Slur = c(AMT.iSlur)      '二胡連音線，(古箏是合音)
''
'        Dim vABC As New VoiceABC
'        Dim pit As New vpitchesNote
'        Dim lastABC As VoiceABC       '記錄上一個音符元件
'        Dim lastPitchs As vpitchesNoteList '記錄上一個音符元件
'
'        If Not (lastABC Is Nothing) Then Set lastPitch = lastABC.pitches
'
'        Select Case C(amt.iAdd)
'            Case "["
'                isAdd = True
'                For k = i To Len(mTextNote(amt.iNote))
'                    '取得資料
'                    For j = amt.iTONE To Len(mChar)
'                        C(j) = Mid(mTextNote(j), i, 1)
'                        If C(j) = "" Then C(j) = " "
'                    Next j
'                Next
'            Case "]"
'            Case " "
'            Case Else
'        End Select
'        ilo = mSize(ntrack)
'        Select Case C(amt.iNote)     '這是音階
'            Case "0"
'            Case "1", "2", "3", "4", "5", "6", "7"
'                pit.pitch = CInt(C(amt.iNote))
'            Case "."
'                lastPitch.duration = lastPitch.duration + lastPitch.duration / 2
'            Case "-"
'                lastPitch.duration = lastPitch.duration + 0.25
'            Case "|"
'                If i = 1 Then
''lin'               mSize(ntrack) = mSize(ntrack) - 1
'                    GoTo nogood
'                End If
'                c_Note = C(amt.iNote)
'            Case " ", ""
''lin'               mSize(ntrack) = mSize(ntrack) - 1
'                    GoTo nogood
'            Case Else
'                c_Note = C(amt.iNote)
'        End Select
'
'
'
'        lsup = 0
'        Select Case C(amt.iTempo)     '這是拍子
'            Case " "
'                c_Tempo = C(amt.iTempo)
'            Case "-", "2"
'                lsup = 1
'                c_Tempo = C(amt.iTempo)
'            Case "=", "4", "3"
'                lsup = 2
'                c_Tempo = C(amt.iTempo)
'            Case "6", "8", "A"
'                lsup = 3
'                c_Tempo = C(amt.iTempo)
'            Case "|"
'                c_Tempo = C(amt.iTempo)
'            Case Else
'                IsEmpty C(amt.iTempo)
'                c_Tempo = C(amt.iTempo)
'        End Select
'
'
'
'        Select Case C(amt.iFinge)     '這是指法
'            Case " "
'            Case "("
'            Case "|"
'
'            Case "a" To "z", "A" To "Z", "-", "="
'            Case chr(21) To chr(125)
'                c_Finge = C(amt.iFinge)
'            Case Else
'                c_Finge = C(amt.iFinge)
'        End Select
'
'        Select Case C(amt.iTowFinge)     '這是指法2 第二行
'            Case "a" To "z", "A" To "Z", "-", "="
'                c_TowFinge = C(amt.iTowFinge)
'            Case "1" To "7"
'                c_TowFinge = C(amt.iTowFinge)
'            Case " ", "(", "|"
'                c_TowFinge = C(amt.iTowFinge)
'            Case Else
'                c_TowFinge = C(amt.iTowFinge)
'        End Select
'
'
'
'
'        c_TONE = C(amt.iTONE)
'        c_Scale = C(amt.iScale)
'        c_Slur = C(amt.iSlur)   '滑音行
'        c_Finge = C(amt.iFinge)
'        c_Add = C(amt.iAdd)     '合音行
'
'        Set objNote = New MusicNoteItem
'
'        objNote.mtone = c_TONE     ' * 行
'        objNote.mnote = c_Note      '這為主行       1234567.|l
'        objNote.mfingering = c_Finge    '這是指法行     _+)(*&
'        objNote.mtow_fingering = c_TowFinge  '這是指法行第二行  _+)(*&
'        objNote.mtempo = c_Tempo   '這是拍子       -=368acefz
'        objNote.mscale = c_Scale   '這是高低音行   .,:
'
'
'
'
'        If c_Add = "]" Then
'            isAdd = False
'            objMusic.typs = Cg.note
'            objMusic.notes.Push objNote
'            objMusic.mtempo = c_Tempo   '這是拍子       -=368acefz
'
'            mMusic(ntrack).Push objMusic
'            mSize(ntrack) = mSize(ntrack) + 1
'        ElseIf c_Add = "[" Or isAdd = True Then
'            If c_Add = "[" Then
'                Set objMusic = New MusicItem
'                Set objMusic.notes = New iArray
'            End If
'            isAdd = True
'            objMusic.typs = Cg.note
'            objMusic.notes.Push objNote
'            objMusic.mtempo = c_Tempo   '這是拍子       -=368acefz
'        Else
'            Set objMusic = New MusicItem
'            Set objMusic.notes = New iArray
'
'            objMusic.typs = Cg.note
'            objMusic.notes.Push objNote
'            objMusic.mtempo = c_Tempo   '這是拍子       -=368acefz
'
'            mMusic(ntrack).Push objMusic
'            mSize(ntrack) = mSize(ntrack) + 1
'        End If
'
'        If c_Slur = "[" Or c_Slur = "(" Then
'            objMusic.slurStart = True       '二胡連音線，(古箏是合音)
'        ElseIf c_Slur = "]" Or c_Slur = ")" Then
'            objMusic.slurEnd = True
'        End If
'
'
'        objMusic.ln = ln  '寫入第幾行
'        objMusic.WD = i   '寫入第幾字
'
'nogood:
'    Next i
End Function
Function getVoiceListData(trackNum As Integer) As VoiceABCList
    If UBound(GroupABCLists) >= trackNum Then
        Set getVoiceListData = GroupABCLists(trackNum)
    End If

End Function
Function ConverToVoiceABCList(trackNum As Integer) As VoiceABCList

    Dim mItem As MusicItem
    Dim trackMaxLen As Integer
    Dim currenCount As Integer
    Dim sarr() As String
    Dim reg As New RegExp
    Dim cc As String
    Dim sNote As String
    Dim iTempo As Integer
    Dim sTempo As Integer
    Dim iScale As Integer
    Dim sScale As Integer
    Dim i As Integer
    Dim vABC As VoiceABC

'取得關鍵字  主音 AMT.iNote
    Dim noteListCode As New iArray
    Dim noteListType As iArray
            
        noteListCode.PushArray Array("0 M-NOTE0", _
            "1 M-NOTE1", _
            "2 M-NOTE2", _
            "3 M-NOTE3", _
            "4 M-NOTE4", _
            "5 M-NOTE5", _
            "6 M-NOTE6", _
            "7 M-NOTE7", _
            ". M-NOTE.", _
            "- M-NOTE-", _
            "o M-NOTEo", _
            "x M-NOTEx", _
            "X M-NOTEX2", _
            "e M-NOTEe", _
            "E M-NOTEE2")
            
    Dim iLe As Integer
    Dim cn As String
    Dim tempoListCode As New iArray

    tempoListCode.PushArray Array( _
            "1 M-TEMPO1", _
            "2 M-TEMPO2", _
            "3 M-TEMPO3", _
            "4 M-TEMPO4")
            
    
    Dim scaleListCode As New iArray
    scaleListCode.PushArray Array( _
            ". M-OCTAVE1 1", _
            ": M-OCTAVE2 2", _
            "! M-OCTAVE3 3", _
            ", M-OCTAVEa -1", _
            "  M-OCTAVEb -2", _
            "? M-OCTAVEc -3")
            
    '取得升降字 -特疏字法
    Dim toneListCode As New iArray
    toneListCode.PushArray Array( _
            "# MT-SHARP", _
            "b MT-FLAT", _
            "o MT-NATURAL")


    
    trackMaxLen = GetTrackBufferSize(trackNum)
    For i = 0 To trackMaxLen - 1
        Set mItem = GetData(trackNum, i)
                
        cc = ConverRegexList(noteListCode, "mItem.notes")
        
'        For j = 0 To noteListCode.Count - 1
'            sarr = Split(noteListCode(i), " ")
'            If cc = sarr(0) Then
'                MFS(currenCount).sNote = sarr(1)
'                Exit For
'            Else
'                MFS(currenCount).sNote = ""
'            End If
'        Next
        
        
    Next
    
    cc = ""
    
'
'
'    ReDim MFS(MData.notes.Count - 1)
'    For currenCount = 0 To MData.notes.Count - 1
'
'        cc = MData.notes(currenCount).mnote
'        For i = 0 To noteListCode.Count - 1
'            sarr = Split(noteListCode(i), " ")
'            If cc = sarr(0) Then
'                MFS(currenCount).sNote = sarr(1)
'                Exit For
'            Else
'                MFS(currenCount).sNote = ""
'            End If
'        Next
'
'
'        '取得關鍵字 拍子  -=368acefz amt.iTempo
'        iLe = Tempo_c2line(MData.notes(currenCount).mtempo)
'        cc = MData.notes(currenCount).mtempo
'        For i = 0 To tempoListCode.Count - 1
'            sarr = Split(tempoListCode(i), " ")
'            If iLe = sarr(0) Then
'                MFS(currenCount).sTempo = sarr(1)
'                MFS(currenCount).iTempo = iLe
'                Exit For
'            Else
'                MFS(currenCount).sTempo = cc
'                MFS(currenCount).iTempo = iLe
'            End If
'        Next
'
'
'        '取得關鍵字高低音行   .:! , ?
'        cc = MData.notes(currenCount).mscale
'        For i = 0 To scaleListCode.Count - 1
'            sarr = Split(scaleListCode(i), " ")
'            If cc = sarr(0) Then
'                MFS(currenCount).sScale = sarr(1)
'                MFS(currenCount).iScale = sarr(2)
'                Exit For
'            Else
'                MFS(currenCount).sScale = ""
'                MFS(currenCount).iScale = 0
'            End If
'        Next
'
'
'        '取得關鍵字 -指法1
'        MFS(currenCount).sFinge = ""
'        cc = MData.notes(currenCount).mfingering
'        Select Case cc
'            Case "a" To "z", "A" To "Z", "-", "=", "@"
'                MFS(currenCount).sFinge = kFing(Asc(cc))
'                Set MFS(currenCount).mfPosition = posFing(Asc(cc)).clone
'            Case Else
'            MFS(currenCount).sFinge = ""
'            Set MFS(currenCount).mfPosition = New point
'        End Select
'
'
'
'    '    '取得關鍵字 -指法2
'        cc = MData.notes(currenCount).mtow_fingering
'        MFS(currenCount).sTowFinge = ""
'        Select Case cc
'            Case "a" To "z", "A" To "Z", "-", "=", "@"
'                MFS(currenCount).sTowFinge = kTowFing(Asc(cc))
'                Set MFS(currenCount).mfTowPosition = posTowFing(Asc(cc)).clone
'            Case Else
'            MFS(currenCount).sTowFinge = ""
'            Set MFS(currenCount).mfTowPosition = New point
'        End Select
'
'        '取得升降字 -特疏字法
'        cc = MData.notes(currenCount).mtone
'        For i = 0 To toneListCode.Count - 1
'            sarr = Split(toneListCode(i), " ")
'            If cc = sarr(0) Then
'                MFS(currenCount).sTONE = sarr(1)
'                Exit For
'            Else
'                MFS(currenCount).sTONE = cc
'            End If
'        Next
'
'
'    Next

End Function

Attribute VB_Name = "Dictionary"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Attribute VB_Description = "A wrapper that extends Scripting.Dictionary functionality."
' Copyright 2023 Sam Vanderslink
' sam.vanderslink@notis.net.au
'
' Permission is hereby granted, free of charge, to any person obtaining a copy
' of this software and associated documentation files (the "Software"), to deal
' in the Software without restriction, including without limitation the rights
' to use, copy, modify, merge, publish, distribute, sublicense, and/or sell
' copies of the Software, and to permit persons to whom the Software is
' furnished to do so, subject to the following conditions:
'
' The above copyright notice and this permission notice shall be included in
' all copies or substantial portions of the Software.
'
' THE SOFTWARE IS PROVIDED "AS IS", WITHOUT WARRANTY OF ANY KIND, EXPRESS OR
' IMPLIED, INCLUDING BUT NOT LIMITED TO THE WARRANTIES OF MERCHANTABILITY,
' FITNESS FOR A PARTICULAR PURPOSE AND NONINFRINGEMENT. IN NO EVENT SHALL THE
' AUTHORS OR COPYRIGHT HOLDERS BE LIABLE FOR ANY CLAIM, DAMAGES OR OTHER
' LIABILITY, WHETHER IN AN ACTION OF CONTRACT, TORT OR OTHERWISE, ARISING
' FROM, OUT OF OR IN CONNECTION WITH THE SOFTWARE OR THE USE OR OTHER DEALINGS
' IN THE SOFTWARE.

Option Explicit

'-------------------------------------------------------------------------------
'   Class: Dictionary
'   A wrapper that extends Scripting.Dictionary functionality.
'-------------------------------------------------------------------------------

' Enums
'-------------------------------------------------------------------------------
Enum CompareModeType
'   Performs a comparison by using the setting of the Option Compare statement.
    vbUseCompareOption = -1

'   Performs a binary comparison.
    vbBinaryCompare = 0

'   Performs a textual comparison.
    vbTextCompare = 1

'   Microsoft Access only.
'   Performs a comparison based on information in your database.
    vbDatabaseCompare = 2
End Enum


' Private Backing Store
'-------------------------------------------------------------------------------
Private mBaseDict As Object
Private mOptionNoItemFail As Boolean
Private mLargestValueSize

Public LabelPos As Integer

' Properties
'-------------------------------------------------------------------------------
Public Property Let OptionNoItemFail(var As Boolean)
Attribute OptionNoItemFail.VB_Description = "Prevents a duplicative item add from raising an exception."
'   Prevents a duplicative item add from raising an exception.
'
'   When setting an item, it overwrites the existing one.
'   When getting an item, it prevents the key from being added.
'
    mOptionNoItemFail = var
End Property

Public Property Get OptionNoItemFail() As Boolean
    OptionNoItemFail = mOptionNoItemFail
End Property

Public Property Let CompareMode(var As CompareModeType)
Attribute CompareMode.VB_Description = "Sets the compare mode for the dictionary."
'   Sets the compare mode for the dictionary.
'
'   A value representing the comparison mode used by functions such
'   as StrComp. Can only be changed while the dictionary has no data.
    mBaseDict.CompareMode = var
End Property

Public Property Get CompareMode() As CompareModeType
    CompareMode = mBaseDict.CompareMode
End Property

Public Property Get Count() As Variant
Attribute Count.VB_Description = "Gets the count of the items in the dictionary."
'   Gets the count of the items in the dictionary.
    Count = mBaseDict.Count
End Property

Public Property Let item(key As Variant, val As Variant)
Attribute item.VB_Description = "Sets or returns an item for a specified key in a Dictionary object."
Attribute item.VB_UserMemId = 0
'   Sets or returns an item for a specified key in a Dictionary object.
    If mOptionNoItemFail Then On Error Resume Next
    mBaseDict.item(key) = val
    If err = 0 Then MetaTrackingAdd val
End Property

Public Property Set item(key As Variant, val As Variant)
    If mOptionNoItemFail Then On Error Resume Next
    Set mBaseDict.item(key) = val
    If err = 0 Then MetaTrackingAdd val
End Property

Public Property Get item(key As Variant) As Variant
    If mOptionNoItemFail And Not mBaseDict.Exists(key) Then Exit Property

    If IsObject(mBaseDict.item(key)) Then
        Set item = mBaseDict.item(key)
    Else
        Dim ss
        item = mBaseDict.item(key)
        ss = item
    End If
End Property

Public Property Let key(key As Variant, NewKey As Variant)
Attribute key.VB_Description = "Updates an existing key with a new one."
'   Updates an existing key with a new one.
    mBaseDict.key(key) = NewKey
End Property

Public Property Get GetValue(key As Variant, ItemDefault As Variant) As Variant
Attribute GetValue.VB_Description = "Gets a value for the specified key or returns the deafult. if not found"
'   Gets a value for the specified key or returns the deafult if not found.
    If mBaseDict.Exists(key) Then
        If IsObject(mBaseDict.item(key)) Then
            Set GetValue = mBaseDict.item(key)
        Else
            GetValue = mBaseDict.item(key)
        End If
    Else
        If IsObject(ItemDefault) Then
            Set GetValue = ItemDefault
        Else
            GetValue = ItemDefault
        End If
    End If
End Property

Public Property Get DataRows(Optional OptionUseRowMode As Boolean) As Long
Attribute DataRows.VB_Description = "Returns the row count that would be returned by the GetData method"
'   Returns the row count that would be returned by the GetData method.
'   The values are always +1 to account for the first row being keys.
'
'   OptionUseRowMode=True:  Returns the longest array size of values
'                           plus row for keys (if they exist).
'   OptionUseRowMode=False: Returns the count of the keys.
    DataRows = IIf(OptionUseRowMode, mLargestValueSize + LongMin(1, Me.Count), Me.Count)
End Property

Public Property Get DataCols(Optional OptionUseRowMode As Boolean) As Long
Attribute DataCols.VB_Description = "Returns the column count that would be returned by the GetData method."
'   Returns the column count that would be returned by the GetData method.
'   The values are always +1 to account for the first col being keys.
'
'   OptionUseRowMode=True:  Returns the count of the keys.
'   OptionUseRowMode=False: Returns the longest array size of values
'                           plus 1 col for keys (if they exist).
    DataCols = IIf(OptionUseRowMode, Me.Count, mLargestValueSize + LongMin(1, Me.Count))
End Property

Public Property Get NewEnum() As IUnknown
Attribute NewEnum.VB_Description = "Enables iteration with a For Each loop."
Attribute NewEnum.VB_UserMemId = -4
'   Enables iteration with a For Each loop.
    Set NewEnum = mBaseDict.[_NewEnum]
End Property


' Constructor
'-------------------------------------------------------------------------------
Private Sub Class_Initialize()
    Set mBaseDict = CreateObject("Scripting.Dictionary")
End Sub


' Methods
'-------------------------------------------------------------------------------
Public Sub Add(key As Variant, val As Variant)
Attribute Add.VB_Description = "Adds a key and value pair to the dictionary."
'   Adds a key and value pair to the dictionary.
'
'   If the dictionary is in NoItemFail mode, and the key exists, the value
'   will be overwritten wrather than throwing a duplicate key exception.
'
'   Args:
'       Key: The key to add the value to.
'       val: The value to add.
'
    If mOptionNoItemFail Then On Error Resume Next
    mBaseDict.Add key, val
    
    If err = 457 Then
        If IsObject(val) Then
            Set item(key) = val
        Else
            item(key) = val
        End If
    Else
        MetaTrackingAdd val
    End If
End Sub

Public Sub Remove(key As Variant)
Attribute Remove.VB_Description = "Removes a key from the Scripting.Dictionary."
'   Removes a key from the Scripting.Dictionary.
'
'   Args:
'       Key: The key to remove.
'
    Dim val As Variant
    If IsObject(Me.item(key)) Then
        Set val = Me.item(key)
    Else
        val = Me.item(key)
    End If
    mBaseDict.Remove key
    MetaTrackingRemove val
End Sub

Public Sub RemoveAll()
Attribute RemoveAll.VB_Description = "Removes all keys from the dictionary."
'   Removes all keys from the dictionary.
'
    mBaseDict.RemoveAll
    mLargestValueSize = 0
End Sub

Public Sub AddBulk( _
    ValueArray2D As Variant, _
    Optional OptionUseRowMode As Boolean, _
    Optional OptionCountKeys As Boolean, _
    Optional DefaultValue As Variant, _
    Optional HeadersIndex As Long = 1)
Attribute AddBulk.VB_Description = "Adds key value pairs from a 2D array."
'   Adds key value pairs from a 2D array.
'
'   Supports keys as first row or firt column. Automatically detects array
'   size and adds values based on number of values per key.
'        0: Keys only (values are Nothing)
'        1: Single values only
'       >1: Values are a 1D array of values
'
'   Args:
'       ValueArray2D: The data to add to the dictionary.
'       OptionUseRowMode: Use the first row instead of column as keys.
'       OptionCountKeys: The value is the count of keys.
'       DefaultValue: Set a default item value.
'       HeadersIndex: Specify the header index or column.
'
'   Notes:
'       The use of OptionCountKeys implies duplicate keys so OptionNoItemFail
'       will be forced to True regardless of its current setting.
'
'       There is currently only support for 1-based arrays such that you would
'       get with a Range, e.g., Range("A1:B10").Value = (1 To 10, 1 To 2).
'
        ' Dictionary key
    Dim v As Variant    ' Dictionary value
    
    If OptionCountKeys Then mOptionNoItemFail = True

'   Transpose the array if we're using row mode so that we can use the same
'   logic to add bulk data to the dictionary (as if it is in column mode).
    If OptionUseRowMode Then
        ValueArray2D = Application.transpose(ValueArray2D)
    End If
    
'   Set the shape of the data.
    Dim rowCount As Long
    rowCount = UBound(ValueArray2D, 1)

    Dim colCount As Long
    colCount = UBound(ValueArray2D, 2)

'   Add the keys and values to the dictionary.
    Dim i As Long
    For i = 1 To rowCount
        Dim k As Variant
        k = ValueArray2D(i, HeadersIndex)

'       Determine the value and add it.
        Select Case True
            Case Is = OptionCountKeys:
                v = Me.GetValue(k, 0) + 1
            Case Is = colCount = 2:
                v = ValueArray2D(i, 2)
            Case Is = colCount > 2:
                v = GetDataValues(ValueArray2D, i, HeadersIndex)
            Case Else:
                If IsObject(DefaultValue) Then
                    Set v = DefaultValue
                Else
                    v = DefaultValue
                End If
        End Select
        Me.Add k, v
    Next i
End Sub

Public Function Exists(key As Variant) As Boolean
Attribute Exists.VB_Description = "Checks if a key exists in the dictionary."
'   Checks if a key exists in the dictionary.
'
'   Args:
'       Key: The key to check.
'
'   Returns:
'       True if the key exists.
'
    Exists = mBaseDict.Exists(key)
End Function

Public Function Items() As Variant
Attribute Items.VB_Description = "Returns all values in the dictionary."
'   Returns all values in the dictionary.
'
'   Returns:
'       An array of values.
'
    Items = mBaseDict.Items
End Function

Public Function keys() As Variant
Attribute keys.VB_Description = "Returns all keys in the dictionary."
'   Returns all keys in the dictionary.
'
'   Returns:
'       An array of keys.
'
    keys = mBaseDict.keys
End Function

Public Function GetData(Optional OptionUseRowMode As Boolean) As Variant
Attribute GetData.VB_Description = "Returns the dictionary data as a 2D array with keys representing headers."
'   Returns the dictionary data as a 2D array with keys representing headers.
'
'   Args:
'       OptionUseRowMode: Data is returned with keys as first column.
'
'   Returns:
'       A 2D array of keys and values. Arrays of values will be converted to
'       row data, or column data if OptionUseRowMode is True.
'
'   Set up the metadata to work with.
    Dim arrKeys As Variant
    arrKeys = mBaseDict.keys()

    Dim arrVals As Variant
    arrVals = mBaseDict.Items()

    Dim dataRowCount As Long
    dataRowCount = Me.DataRows()
    
    Dim dataColCount As Long
    dataColCount = Me.DataCols()
    
'   Set up results array in the shape of the keys and values
'   adding an additional column to fit the keys as a column
    Dim Results() As Variant
    ReDim Results(1 To dataRowCount, _
                  1 To dataColCount)

'   Populate the row(s) and column(s)
    Dim r As Long
    For r = 1 To dataRowCount
        Results(r, 1) = arrKeys(r - 1)
        If dataColCount > 2 Then
'           Populate columns for multi-column
            Dim maxCols As Long
            maxCols = UBound(arrVals(r - 1)) + 2
            Dim c As Long
            For c = 2 To dataColCount
                Results(r, c) = arrVals(r - 1)(c - 2)
                If c = maxCols Then Exit For
            Next c
        ElseIf dataColCount = 2 Then
'           Populate single value
            Results(r, 2) = arrVals(r - 1)
        End If
    Next r
    
'   Return the data as normal or row mode.
    If OptionUseRowMode Then
        GetData = Application.transpose(Results)
    Else
        GetData = Results
    End If
End Function


' Helpers
'-------------------------------------------------------------------------------
Private Function GetDataValues(arr As Variant, rIdx As Long, hIdx As Long) As Variant
Attribute GetDataValues.VB_Description = "Returns a 1D array of values from the data."
'   Returns a 1D array of values from the data.
'
'   Args:
'       arr: The source array of values.
'       rIdx: The index row.
'       hIdx: The header (key) index.
'
'   Returns:
'       An array of values, minus the key.
'
    Dim result As Variant
    ReDim result(UBound(arr, 2) - 2)
    
    Dim i As Long
    For i = 1 To UBound(arr, 2)
        If i <> hIdx Then
            result(i - IIf(i < hIdx, 1, 2)) = arr(rIdx, i)
        End If
    Next i

    GetDataValues = result
End Function

Private Function NArrayDimensions(arr As Variant) As Long
Attribute NArrayDimensions.VB_Description = "Returns the number of dimensions for the passed in array."
'   Returns the number of dimensions for the passed in array.
'
'   This is a hack that intentionally seeks to raise and catch an
'   exception as there is no property or elegant way to do this.
'
'   Args:
'       arr: The array to test.
'
'   Returns:
'       The number of dimensions for the passed in array.
'
'   Raises:
'
    
'   Test array dimensions until exception raised
    On Error GoTo result
    Dim i As Long
    Do
        i = i + 1
        NArrayDimensions = UBound(arr, i)
    Loop
    
result:
'   Expect to catch a Type mismatch exception.
'   Expect to catch a Subscript out of range exception.
    If err = 13 Or err = 9 Then NArrayDimensions = i - 1 Else err.Raise err
End Function

Private Sub MetaTrackingAdd(val As Variant)
Attribute MetaTrackingAdd.VB_Description = "Tracks the largest sized value array when adding a key to the dictionary."
'   Tracks the largest sized value array when adding a key to the dictionary.
'
'   Args:
'       val: The value being added.
'
    Dim valSize As Long
    valSize = GetValueOrArraySize(val)
    If valSize > mLargestValueSize Then
        mLargestValueSize = valSize
    End If
End Sub

Private Sub MetaTrackingRemove(remVal As Variant)
Attribute MetaTrackingRemove.VB_Description = "Tracks the largest sized value array when removing a key from the dictionary."
'   Tracks the largest sized value array when removing a key from the dictionary.
'
'   Args:
'       remVal: The value being removed.
'
'   Shortcut for when we have no values.
    If Count = 0 Then
        mLargestValueSize = 0
    End If

'   Get the count of the value array we're removing.
    Dim removedValSize As Long
    removedValSize = GetValueOrArraySize(remVal)
    
'   No need to test everything if the tracked value wasn't the largest.
    If mLargestValueSize > removedValSize Then Exit Sub

    Dim val As Variant
    Dim valSize As Long
    mLargestValueSize = 0
    For Each val In Me.Items
        valSize = GetValueOrArraySize(val)
        
'       Shortcut if next largest is the same as value we're untracking.
        If valSize = removedValSize Then
            mLargestValueSize = valSize
            Exit Sub
        End If
        
        If valSize > mLargestValueSize Then
            mLargestValueSize = valSize
        End If
    Next val
End Sub

Private Function GetValueOrArraySize(val As Variant) As Long
Attribute GetValueOrArraySize.VB_Description = "Returns the length of the array, 1 if not an array, and 0 if Nothing."
'   Returns the length of the array, 1 if not an array, and 0 if Nothing.
'
'   Args:
'       val: The value or array to be tested.
'
'   Returns:
'       The count of values in an array, 1 if not an array, and 0 if Nothing.
'
'   Type checking like this prevents an exception if not an object.
    If TypeName(val) = "Nothing" Then Exit Function
    
    Dim dims As Long
    dims = NArrayDimensions(val)

    If dims = 0 Then
'       Not an array and not nothing.
        GetValueOrArraySize = 1
    Else
'       Is an array, return the count.
'       Assumes a single dimension, but that's all we'll have here.
        GetValueOrArraySize = UBound(val) + 1
    End If
End Function

Private Function LongMin(a As Long, B As Long) As Long
Attribute LongMin.VB_Description = "Returns the smaller of the two passed in values."
'   Returns the smaller of the two passed in values.
'
'   Args:
'       a: A value to be tested.
'       b: A value to be tested.
'
'   Returns:
'       a if a is smaller, else b.
'
    LongMin = IIf(a < B, a, B)
End Function

Attribute VB_Name = "DictionaryTests"
' Copyright 2023 Sam Vanderslink
'
' Permission is hereby granted, free of charge, to any person obtaining a copy
' of this software and associated documentation files (the "Software"), to deal
' in the Software without restriction, including without limitation the rights
' to use, copy, modify, merge, publish, distribute, sublicense, and/or sell
' copies of the Software, and to permit persons to whom the Software is
' furnished to do so, subject to the following conditions:
'
' The above copyright notice and this permission notice shall be included in
' all copies or substantial portions of the Software.
'
' THE SOFTWARE IS PROVIDED "AS IS", WITHOUT WARRANTY OF ANY KIND, EXPRESS OR
' IMPLIED, INCLUDING BUT NOT LIMITED TO THE WARRANTIES OF MERCHANTABILITY,
' FITNESS FOR A PARTICULAR PURPOSE AND NONINFRINGEMENT. IN NO EVENT SHALL THE
' AUTHORS OR COPYRIGHT HOLDERS BE LIABLE FOR ANY CLAIM, DAMAGES OR OTHER
' LIABILITY, WHETHER IN AN ACTION OF CONTRACT, TORT OR OTHERWISE, ARISING
' FROM, OUT OF OR IN CONNECTION WITH THE SOFTWARE OR THE USE OR OTHER DEALINGS
' IN THE SOFTWARE.

Option Explicit


Private passTests As New Collection
Private failTests As New Collection

Public Sub RunTests()
Attribute RunTests.VB_Description = "Runs all tests."
'   Runs all tests.
'
    Set passTests = New Collection
    Set failTests = New Collection

    Dim testName As Variant
    For Each testName In GetTestNames()
        RunTest CStr(testName)
    Next testName

    Dim p As Long, f As Long
    p = passTests.Count
    f = failTests.Count

    Debug.Print "-------------------------------------------"
    Debug.Print "   Passed: " & p & " (" & Format(p / (p + f), "0.00%)")
    Debug.Print "   Failed: " & f & " (" & Format(f / (p + f), "0.00%)")
    Debug.Print "-------------------------------------------"
    
End Sub

Sub RunSingle()
    Dim tr As TestResult
    Set tr = TestDictionary_ItemReturnsItem()
    Debug.Print tr.ToString
End Sub

Private Sub RunTest(testName As String)
Attribute RunTest.VB_Description = "Runs the named test and stores the result."
'   Runs the named test and stores the result.
'
'   Args:
'       testName: The name of the function returning a TestResult.
'
    Dim tr As TestResult
    Set tr = Application.Run(testName)
    tr.Name = testName
    Debug.Print tr.ToString

    If tr.Failed Then failTests.Add tr Else passTests.Add tr
End Sub

Private Function GetTestNames() As Collection
Attribute GetTestNames.VB_Description = "Gets the test names from this module."
'   Gets the test names from this module.
'   A valid test starts with Private Function TestDictionary_ and takes no args.
'
'   Returns:
'       A collection of strings representing names of tests.
'
    Const MODULENAME As String = "DictionaryTests"
    Const FUNCTIONID As String = "Private Function "
    Const TESTSTARTW As String = "Private Function TestDictionary_"

    Dim tswLen As Long
    tswLen = Len(TESTSTARTW)

    Dim codeMod As Object
    Set codeMod = ThisWorkbook.VBProject.VBComponents(MODULENAME).CodeModule

    Dim i As Long
    Dim Results As New Collection
    For i = 1 To codeMod.CountOfLines
        Dim lineContent As String
        lineContent = codeMod.lines(i, 1)

        If left(lineContent, tswLen) = TESTSTARTW Then
            Dim funcName As String
            funcName = Split(Split(lineContent, FUNCTIONID)(1), "(")(0)
            Results.Add funcName
        End If
    Next i
    
    Set GetTestNames = Results
End Function

Private Function TestDictionary_Add() As TestResult
Attribute TestDictionary_Add.VB_Description = "Add an item to the dictionary."
'   Add an item to the dictionary.
    Dim tr As New TestResult

'   Arrange
    Const ADDKEY As String = "K"
    Const ADDVAL As String = "V"
    Dim d As New Dictionary

'   Act
    On Error Resume Next
    d.Add ADDKEY, ADDVAL

'   Assert
    If tr.AssertNoException() Then GoTo Finally
    On Error GoTo 0

    If tr.AssertAreEqual(1, d.Count) Then GoTo Finally
    If tr.AssertAreEqual(ADDVAL, d(ADDKEY)) Then GoTo Finally

Finally:
    On Error GoTo 0
    Set TestDictionary_Add = tr
End Function

Private Function TestDictionary_AddBulkColMode() As TestResult
Attribute TestDictionary_AddBulkColMode.VB_Description = "Add bulk items to the dictionary."
'   Add bulk items to the dictionary.
    Dim tr As New TestResult

'   Arrange
    Dim bulkData() As Variant
    ReDim bulkData(1 To 3, 1 To 4)

    Const HDRS As String = "ABC"
    Const VALS As String = " 123"

    Dim i As Long
    For i = 1 To UBound(bulkData, 1)
        Dim j As Long
        For j = 1 To UBound(bulkData, 2)
            If j = 1 Then
                bulkData(i, j) = Mid(HDRS, i, 1)
            Else
                bulkData(i, j) = Mid(HDRS, i, 1) & Mid(VALS, j, 1)
            End If
        Next j
    Next i

    Dim d As New Dictionary

'   Act
    On Error Resume Next
    d.AddBulk bulkData

'   Assert
    If tr.AssertNoException() Then GoTo Finally
    On Error GoTo 0

    If tr.AssertAreEqual(Len(HDRS), d.Count) Then GoTo Finally

    For i = 1 To UBound(bulkData, 1)
        For j = 2 To UBound(bulkData, 2)
            If d(bulkData(i, 1))(j - 2) <> bulkData(i, j) Then
                tr.Failed = True
                tr.Message = "Dictionary data failed validation."
            End If
        Next j
    Next i

Finally:
    On Error GoTo 0
    Set TestDictionary_AddBulkColMode = tr
End Function

Private Function TestDictionary_AddBulkRowMode() As TestResult
Attribute TestDictionary_AddBulkRowMode.VB_Description = "Add bulk items to the dictionary."
'   Add bulk items to the dictionary.
    Dim tr As New TestResult

'   Arrange
    Dim bulkData() As Variant
    ReDim bulkData(1 To 3, 1 To 4)

    Const HDRS As String = "ABC"
    Const VALS As String = " 123"

    Dim i As Long
    For i = 1 To UBound(bulkData, 1)
        Dim j As Long
        For j = 1 To UBound(bulkData, 2)
            If j = 1 Then
                bulkData(i, j) = Mid(HDRS, i, 1)
            Else
                bulkData(i, j) = Mid(HDRS, i, 1) & Mid(VALS, j, 1)
            End If
        Next j
    Next i

    Dim d As New Dictionary

'   Act
    On Error Resume Next
    d.AddBulk Application.transpose(bulkData), OptionUseRowMode:=True

'   Assert
    If tr.AssertNoException() Then GoTo Finally
    On Error GoTo 0

    If tr.AssertAreEqual(Len(HDRS), d.Count, "count headers") Then GoTo Finally

    For i = 1 To UBound(bulkData, 1)
        For j = 2 To UBound(bulkData, 2)
            If d(bulkData(i, 1))(j - 2) <> bulkData(i, j) Then
                tr.Failed = True
                tr.Message = "Dictionary data failed validation."
            End If
        Next j
    Next i

Finally:
    On Error GoTo 0
    Set TestDictionary_AddBulkRowMode = tr
End Function

Private Function TestDictionary_AddBulkCountKeys() As TestResult
Attribute TestDictionary_AddBulkCountKeys.VB_Description = "Add bulk items to the dictionary."
'   Add bulk items to the dictionary.
    Dim tr As New TestResult

'   Arrange
    Dim bulkData() As Variant
    ReDim bulkData(1 To 6, 1 To 1)

    Const HDRS As String = "ABC"
    Const VALS As String = "123"

    Dim i As Long
    For i = 1 To Len(HDRS)
        Dim j As Long
        For j = 1 To CLng(Mid(VALS, i, 1))
            Dim N As Long
            N = N + 1
            bulkData(N, 1) = Mid(HDRS, i, 1)
        Next j
    Next i

    Dim d As New Dictionary

'   Act
    On Error Resume Next
    d.AddBulk bulkData, OptionCountKeys:=True

'   Assert
    If tr.AssertNoException() Then GoTo Finally
    On Error GoTo 0

    If tr.AssertAreEqual(Len(HDRS), d.Count, "count keys") Then GoTo Finally

    For i = 1 To Len(HDRS)
        Dim h As String, v As Long
        h = Mid(HDRS, i, 1)
        v = CLng(Mid(VALS, i, 1))
        If tr.AssertAreEqual(v, d(h), h) Then Exit For
    Next i

Finally:
    Set TestDictionary_AddBulkCountKeys = tr
End Function

Private Function TestDictionary_AddBulkCountKeysRowMode() As TestResult
Attribute TestDictionary_AddBulkCountKeysRowMode.VB_Description = "Github issue #4 Counting keys using row mode errors with duplicate key."
'   Github issue #4 Counting keys using row mode errors with duplicate key.
    Dim tr As New TestResult

'   Arrange
    Dim bulkData() As Variant
    ReDim bulkData(1 To 6, 1 To 1)

    Const HDRS As String = "ABC"
    Const VALS As String = "123"

    Dim i As Long
    For i = 1 To Len(HDRS)
        Dim j As Long
        For j = 1 To CLng(Mid(VALS, i, 1))
            Dim N As Long
            N = N + 1
            bulkData(N, 1) = Mid(HDRS, i, 1)
        Next j
    Next i

    Dim d As New Dictionary

'   Act
    On Error Resume Next
    d.AddBulk Application.transpose(bulkData), _
        OptionCountKeys:=True, _
        OptionUseRowMode:=True

'   Assert
    If tr.AssertNoException() Then GoTo Finally
    On Error GoTo 0

    If tr.AssertAreEqual(Len(HDRS), d.Count, "count keys") Then GoTo Finally

    For i = 1 To Len(HDRS)
        Dim h As String, v As Long
        h = Mid(HDRS, i, 1)
        v = CLng(Mid(VALS, i, 1))
        If tr.AssertAreEqual(v, d(h), h) Then Exit For
    Next i

Finally:
    Set TestDictionary_AddBulkCountKeysRowMode = tr
End Function

Private Function TestDictionary_CountItems() As TestResult
Attribute TestDictionary_CountItems.VB_Description = "Tests the Count property of the dictionary."
'   Tests the Count property of the dictionary.
'
    Dim tr As New TestResult

'   Arrange
    Const ADDKEYS As String = "ABCDEFGHIJKLMNOP"

'   Act and Assert
    Dim d As New Dictionary
    If tr.AssertAreEqual(0, d.Count, "count keys") Then GoTo Finally

    Dim i As Long
    For i = 1 To Len(ADDKEYS)
        d.Add Mid(ADDKEYS, i, 1), Nothing
        If tr.AssertAreEqual(i, d.Count, "count keys at " & i) Then Exit For
    Next i

Finally:
    Set TestDictionary_CountItems = tr
End Function

Private Function TestDictionary_ItemReturnsItem() As TestResult
Attribute TestDictionary_ItemReturnsItem.VB_Description = "Tests the default and explicit item return."
'   Tests the default and explicit item return.
    Dim tr As New TestResult

'   Arrange
    Const EXPRESA As String = "A Result"
    Const EXPRESB As String = "B Result"
    Const INPKEYA As String = "A"
    Const INPKEYB As String = "B"

'   Act
    Dim d As New Dictionary
    d.Add INPKEYA, EXPRESA
    d.Add INPKEYB, EXPRESB

'   Assert
    If tr.AssertAreEqual(EXPRESA, d.item(INPKEYA), INPKEYA) Then GoTo Finally
    If tr.AssertAreEqual(EXPRESB, d(INPKEYB), INPKEYB) Then GoTo Finally

Finally:
    Set TestDictionary_ItemReturnsItem = tr
End Function

Private Function TestDictionary_Exists() As TestResult
Attribute TestDictionary_Exists.VB_Description = "Tests Exists property works positively and negatively."
'   Tests Exists property works positively and negatively.
    Dim tr As New TestResult

'   Arrange
    Const INPKEYA As String = "A"
    Const INPKEYB As String = "B"
    Dim d As New Dictionary
    d.Add INPKEYA, Nothing

'   Act
    Dim posResult As Boolean
    posResult = d.Exists(INPKEYA)

    Dim negResult As Boolean
    negResult = d.Exists(INPKEYB)

'   Assert
    If tr.AssertIsTrue(posResult, "positive check") Then GoTo Finally
    If tr.AssertIsFalse(negResult, "negative check") Then GoTo Finally

Finally:
    Set TestDictionary_Exists = tr
End Function

Private Function TestDictionary_GetItemsReturnsAllItems() As TestResult
Attribute TestDictionary_GetItemsReturnsAllItems.VB_Description = "Test Items returns all items."
'   Test Items returns all items.
    Dim tr As New TestResult

'   Arrange
    Const EXPRESA As String = "A Result"
    Const EXPRESB As String = "B Result"
    Const INPKEYA As String = "A"
    Const INPKEYB As String = "B"
    
    Dim d As New Dictionary
    d.Add INPKEYA, EXPRESA
    d.Add INPKEYB, EXPRESB

'   Act
    Dim result As Variant
    result = d.Items()

'   Assert
    On Error Resume Next
    If tr.AssertAreEqual(EXPRESA, result(0), INPKEYA) Then GoTo Finally
    If tr.AssertAreEqual(EXPRESB, result(1), INPKEYB) Then GoTo Finally
    If tr.AssertNoException() Then GoTo Finally

Finally:
    Set TestDictionary_GetItemsReturnsAllItems = tr
End Function

Private Function TestDictionary_GetKeysReturnsKeys() As TestResult
Attribute TestDictionary_GetKeysReturnsKeys.VB_Description = "Test Keys returns all keys."
'   Test Keys returns all keys.
    Dim tr As New TestResult

'   Arrange
    Const INPKEYA As String = "A"
    Const INPKEYB As String = "B"
    
    Dim d As New Dictionary
    d.Add INPKEYA, Nothing
    d.Add INPKEYB, Nothing

'   Act
    Dim result As Variant
    result = d.keys()

'   Assert
    On Error Resume Next
    If tr.AssertAreEqual(INPKEYA, result(0)) Then GoTo Finally
    If tr.AssertAreEqual(INPKEYB, result(1)) Then GoTo Finally
    If tr.AssertNoException() Then GoTo Finally

Finally:
    Set TestDictionary_GetKeysReturnsKeys = tr
End Function

Private Function TestDictionary_GetDataReturnsData() As TestResult
Attribute TestDictionary_GetDataReturnsData.VB_Description = "Test data out matches data in."
'   Test data out matches data in.
    Dim tr As New TestResult

'   Arrange
    Dim bulkData() As Variant
    ReDim bulkData(1 To 3, 1 To 4)

    Const HDRS As String = "ABC"
    Const VALS As String = " 123"

    Dim i As Long
    For i = 1 To UBound(bulkData, 1)
        Dim j As Long
        For j = 1 To UBound(bulkData, 2)
            If j = 1 Then
                bulkData(i, j) = Mid(HDRS, i, 1)
            Else
                bulkData(i, j) = Mid(HDRS, i, 1) & Mid(VALS, j, 1)
            End If
        Next j
    Next i

    On Error Resume Next
    Dim d As New Dictionary
    d.AddBulk bulkData

'   Act
    Dim Results As Variant
    Results = d.GetData()

'   Assert
    If tr.AssertNoException() Then GoTo Finally
    On Error GoTo 0

    For i = 1 To UBound(bulkData, 1)
        For j = 2 To UBound(bulkData, 2)
            If Results(i, j) <> bulkData(i, j) Then
                tr.Failed = True
                tr.Message = "Dictionary data failed validation."
            End If
        Next j
    Next i

Finally:
    Set TestDictionary_GetDataReturnsData = tr
End Function

Private Function TestDictionary_OptionNoItemFailOverwrites() As TestResult
Attribute TestDictionary_OptionNoItemFailOverwrites.VB_Description = "OptionNoItemFail overwrites rather than throwing."
'   OptionNoItemFail overwrites rather than throwing.
    Dim tr As New TestResult

'   Arrange
    Const INPKEYA As String = "A"
    Const inpValA As String = "A Value"
    Const inpValB As String = "Visibly different value to A"
    
'   Act
    Dim d As New Dictionary
    d.OptionNoItemFail = True

    On Error Resume Next
    d.Add INPKEYA, inpValA
    d.Add INPKEYA, inpValB

'   Assert
    If tr.AssertNoException() Then GoTo Finally
    On Error GoTo 0

    If tr.AssertAreEqual(1, d.Count, "count") Then GoTo Finally
    If tr.AssertAreEqual(inpValB, d(INPKEYA), INPKEYA) Then GoTo Finally

Finally:
    Set TestDictionary_OptionNoItemFailOverwrites = tr
End Function

Private Function TestDictionary_NoOptionNoItemFailThrows() As TestResult
Attribute TestDictionary_NoOptionNoItemFailThrows.VB_Description = "Without OptionNoItemFail throws rather than overwriting."
'   Without OptionNoItemFail throws rather than overwriting.
'   This test requires "Error Handling > Break on Unhandled Errors" set.
'   If "Break in class module" is set, the
    Dim tr As New TestResult

'   Arrange
    Const DUPLICATEKEYEX As Long = 457
    Const INPKEYA As String = "A"
    Const inpValA As String = "A Value"
    Const inpValB As String = "A Value"
    
'   Act
    Dim d As New Dictionary
    d.OptionNoItemFail = False

    d.Add INPKEYA, inpValA
    On Error Resume Next
    d.Add INPKEYA, inpValB

'   Assert
    If tr.AssertRaised(DUPLICATEKEYEX) Then GoTo Finally
    On Error GoTo 0

    If tr.AssertAreEqual(1, d.Count, "count") Then GoTo Finally
    If tr.AssertAreEqual(inpValA, d(INPKEYA), INPKEYA) Then GoTo Finally

Finally:
    Set TestDictionary_NoOptionNoItemFailThrows = tr
End Function

Private Function TestDictionary_DataRowsAndColsCorrect() As TestResult
Attribute TestDictionary_DataRowsAndColsCorrect.VB_Description = "Tests the DataRows and DataCols properties."
'   Tests the DataRows and DataCols properties.
    Dim tr As New TestResult

'   Arrange
    Dim bulkData() As Variant
    ReDim bulkData(1 To 3, 1 To 4)

    Const HDRS As String = "ABC"
    Const VALS As String = " 123"

    Dim i As Long
    For i = 1 To UBound(bulkData, 1)
        Dim j As Long
        For j = 1 To UBound(bulkData, 2)
            If j = 1 Then
                bulkData(i, j) = Mid(HDRS, i, 1)
            Else
                bulkData(i, j) = Mid(HDRS, i, 1) & Mid(VALS, j, 1)
            End If
        Next j
    Next i

    On Error Resume Next
    Dim d As New Dictionary
    d.AddBulk bulkData

'   Act
    Dim dRowsColMode As Long
    dRowsColMode = d.DataRows()

    Dim dColsColMode As Long
    dColsColMode = d.DataCols()

    Dim dRowsRowMode As Long
    dRowsRowMode = d.DataRows(OptionUseRowMode:=True)

    Dim dColsRowMode As Long
    dColsRowMode = d.DataCols(OptionUseRowMode:=True)

'   Assert
    If tr.AssertNoException() Then GoTo Finally
    On Error GoTo 0

    If tr.AssertAreEqual(UBound(bulkData, 1), dRowsColMode) Then GoTo Finally
    If tr.AssertAreEqual(UBound(bulkData, 2), dColsColMode) Then GoTo Finally
    If tr.AssertAreEqual(UBound(bulkData, 2), dRowsRowMode) Then GoTo Finally
    If tr.AssertAreEqual(UBound(bulkData, 1), dColsRowMode) Then GoTo Finally

Finally:
    Set TestDictionary_DataRowsAndColsCorrect = tr
End Function

Private Function TestDictionary_RemoveRemovesKey() As TestResult
Attribute TestDictionary_RemoveRemovesKey.VB_Description = "Test that remove removes the key."
'   Test that remove removes the key.
    Dim tr As New TestResult

'   Arrange
    Const INPKEYA As String = "A"
    Const INPKEYB As String = "B"
    
    Dim d As New Dictionary
    d.Add INPKEYA, Nothing
    d.Add INPKEYB, Nothing

'   Act
    d.Remove (INPKEYA)

'   Assert
    On Error Resume Next
    If tr.AssertIsFalse(d.Exists(INPKEYA), "key A exists") Then GoTo Finally
    If tr.AssertIsTrue(d.Exists(INPKEYB), "key B exists") Then GoTo Finally
    If tr.AssertNoException() Then GoTo Finally

Finally:
    On Error GoTo 0
    Set TestDictionary_RemoveRemovesKey = tr
End Function

Private Function TestDictionary_RemoveUpdatesMeta() As TestResult
Attribute TestDictionary_RemoveUpdatesMeta.VB_Description = "Github issue #3 Array tracking when largest element is removed."
'   Github issue #3 Array tracking when largest element is removed.
    Dim tr As New TestResult

'   Arrange
    Const INPKEYA As String = "A"
    Const INPKEYB As String = "B"

    Dim inpValA() As Variant
    inpValA = Array(1, 2)

    Dim inpValB() As Variant
    inpValB = Array(1, 2, 3, 4)

    Dim d As New Dictionary
    d.Add INPKEYA, inpValA
    d.Add INPKEYB, inpValB

'   Act
    Dim beforeRemoveColCount As Long
    beforeRemoveColCount = d.DataCols()

    d.Remove INPKEYB

    Dim afterRemoveColCount As Long
    afterRemoveColCount = d.DataCols()

'   Assert
    On Error Resume Next
    If tr.AssertAreNotEqual(beforeRemoveColCount, afterRemoveColCount, "row counts") Then GoTo Finally
    If tr.AssertAreEqual(UBound(inpValB) + 2, beforeRemoveColCount) Then GoTo Finally
    If tr.AssertAreEqual(UBound(inpValA) + 2, afterRemoveColCount) Then GoTo Finally
    If tr.AssertNoException() Then GoTo Finally

Finally:
    On Error GoTo 0
    Set TestDictionary_RemoveUpdatesMeta = tr
End Function

Private Function TestDictionary_ExistWorksWithInteger() As TestResult
Attribute TestDictionary_ExistWorksWithInteger.VB_Description = "Github Issue #5 Integer keys are never found with .Exists method."
'   Github Issue #5 Integer keys are never found with .Exists method.
    Dim tr As New TestResult

'   Arrange
    Dim d As New Dictionary
    d.Add 0, Nothing

'   Act
    Dim result As Boolean
    result = d.Exists(0)

'   Assert
    If tr.AssertIsTrue(result, "result exists") Then GoTo Finally


Finally:
    Set TestDictionary_ExistWorksWithInteger = tr
End Function

Private Function TestDictionary_GetDataWorksWithVariableArrays() As TestResult
Attribute TestDictionary_GetDataWorksWithVariableArrays.VB_Description = "Github issue #2 Unexpected value array sizes can cause GetData to raise out of bounds error."
'   Github issue #2 Unexpected value array sizes can cause GetData to raise out of bounds error.
    Dim tr As New TestResult

'   Arrange
    Const INPKEYA As String = "A"
    Const INPKEYB As String = "B"

    Dim inpValA() As Variant
    inpValA = Array(1, 2)

    Dim inpValB() As Variant
    inpValB = Array(1, 2, 3, 4)

    Dim d As New Dictionary
    d.Add INPKEYA, inpValA
    d.Add INPKEYB, inpValB

'   Act
    Dim Results() As Variant
    Results = d.GetData()

'   Assert
    If tr.AssertAreEqual(UBound(inpValB) + 2, UBound(Results, 2)) Then GoTo Finally

Finally:
    Set TestDictionary_GetDataWorksWithVariableArrays = tr
End Function

Private Function TestDictionary_ForEach() As TestResult
Attribute TestDictionary_ForEach.VB_Description = "Tests the For Each functionality on keys."
'   Tests the For Each functionality on keys.
    Dim tr As New TestResult

'   Arrange
    Dim inpKeys() As Variant
    inpKeys = Array("a", "b", "c")

    Dim inpVals() As Variant
    inpVals = Array(1, 2, 3)

    Dim d As New Dictionary
    Dim i As Long
    For i = 0 To UBound(inpKeys)
        d.Add inpKeys(i), inpVals(i)
    Next i

'   Act and Assert
    i = 0
    Dim k As Variant
    For Each k In d.keys
        If Not tr.AssertAreEqual(inpKeys(i), k) Then GoTo Finally
        If Not tr.AssertAreEqual(inpVals(i), d(k)) Then GoTo Finally
        i = i + 1
    Next k

Finally:
    Set TestDictionary_ForEach = tr
End Function

Attribute VB_Name = "DrawModule"
Option Explicit

Type Rect
    left As Double
    top As Double
    width As Double
    height As Double
End Type
Type positionxxx
    x As Double
    y As Double
End Type
Type SVGRect
    x As Double
    y As Double
    width As Double
    height As Double
End Type
Type box
    left As Double
    top As Double
    rigth  As Double
    bottom  As Double
End Type

Type size
    width As Double
    height As Double
End Type

'Public Enum positionEnum
'below = "below"
'above = "above"
'Hidden = "hidden"
'left = "left"
'right = "right"
'relative = "relative"
'End Enum

Enum spacing
    FONTEM = 360
    fontsize = 30
    Step = 30 * 93 / 720 '/*spacing.FONTSIZE*/
    space = 10
    TOPNOTE = 15
    STAVEHEIGHT = 100
    INDENT = 50
End Enum



'Enum VoiceElemTYPS
'    note = "note"
'    bar = "bar"
'    meter = "meter"
'    clef = "clef"
'    Key = "key"
'    stem = "stem"
'    part = "part"
'    tempo = "tempo"
'    style = "style"
'    hint = "hint"
'    midi = "midi"
'    'SCALE = "scale"
'    color = "color"
'
'    Gap = "gap"
'    overlay = "overlay"
'    Transpose = "transpose"
'    beam = "beam"
'
'
'End Enum


'Enum AbsoluteTYPS
'    symbol = "symbol"
'    tempo = "tempo"
'    part = "part"
'    rest = "rest"
'    note = "note"
'    bar = "bar"
'    staff_extra = "staff-extra"
'    staff_extra_clef = "staff_extra_clef"
'    staff_extra_key_signature = "staff_extra_key_signature"
'    staff_extra_time_signature = "staff_extra_time_signature"
'End Enum

'Type FixedCoords
'     x As Double
'     y As Double
'     w As Double
'     h As Double
'     t As Double
'     b As Double
'End Type
'Type RelativeOptions
'    typs As String
'    klass As String * 20
'    name As String * 20
'    anchor As String * 20 '"start" | "middle" | "end"
'    position As String
'    dim As Variant
'    pitch2 As Double
'    realWidth As Double
'    lineWidth As Double
'    thickness As Double
'    stemHeight As Double
'    scalex As Double
'    scaley As Double
'    top As Double
'    bottom As Double
'    height As Double
'    width As Double
'End Type


'Type TempoProperties
'    type As String
'    duration As iArray
'    bpm As Double
'    preString As String
'    postString As String
'    startChar As Integer
'    endChar As Integer
'    suppress As Boolean
'    suppressBpm As Boolean
'End If




Public gTuneLine As TuneLine

Attribute VB_Name = "EngraverController"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public classes As Dictionary
Public dragColor As String
Public dragIndex As Double
Public dragMouseStart As point 'as  { x as  number, y as  number  }
Public dragTarget 'as  null | any
Public dragYStep As Double
Public dragging As Boolean
Public engraver As AbstractEngraver
Public GetFontAttr As GetFontAndAttr
Public getTxtSize As getTextSize
Public listeners As iArray     'ClickListener []
Public rangeHighlight 'as  any
Public renderer As RendererModule
Public responsive As String
Public scale_ As Double
Public initialClef 'as  any
Public selectTypes As iArray  'boolean | Array<DragTypes>
Public selectables As iArray '  Array<Selectable>
Public selected As iArray  'Array<any>
Public selectionColor As String
Public space As Double
Public staffgroups As iArray 'StaffGroupElement
Public staffwidthPrint As Double
Public staffwidthScreen As Double
Public width As Double
Public oneSvgPerLine
Public jazzchords
Public germanAlphabet
Public lineThickness
Public svgs As iArray 'SVGmodel

    
Public Sub init(paper, params As Dictionary)

        'params = params || {}
        Set params = New Dictionary
        Me.oneSvgPerLine = params("oneSvgPerLine")
        Me.selectionColor = params("selectionColor")
        Me.dragColor = IIf(params("dragColor") <> Empty, params("dragColor"), params("selectionColor"))
        Me.dragging = IIf(params("dragging") <> Empty, True, False)
       'line Set Me.selectTypes = params("selectTypes")
        Me.responsive = params("responsive")
        Me.space = 3 * spacing.space
        Me.initialClef = params("initialClef")
        Me.scale_ = IIf(params("scale") <> 0, CDbl(params("scale")), 1)
        Set Me.classes = New Dictionary 'Classes({ shouldAddClasses: params("add_classes") })
        If (Not (Me.scale_ > 0.1)) Then
            Me.scale_ = 0
        End If

        If (params("staffwidth") <> Empty) Then
            '' Note: Normally all measurements to the engraver are in POINTS. However, if a person is formatting for the
            '' screen and directly inputting the width, then it is more logical to have the measurement in pixels.
            Me.staffwidthScreen = params("staffwidth")
            Me.staffwidthPrint = params("staffwidth")
         Else
            Me.staffwidthScreen = 740  '' TODO-PER: Not sure where this number comes from, but this is how it's always been.
            Me.staffwidthPrint = 680  '' The number of pixels in 8.5", after 1cm of margin has been removed.
        End If
       Set Me.listeners = New iArray
        If (params("clickListener") <> Empty) Then
            Me.addSelectListener (params("clickListener"))
        End If

       Set Me.renderer = New RendererModule   ' Renderer(paper)
       Me.renderer.init
       Me.renderer.setPaddingOverride params
        If (params("showDebug") <> Empty) Then
            Me.renderer.showDebug = params("showDebug")
        End If
        If (params("jazzchords") <> Empty) Then
            Me.jazzchords = params("jazzchords")
        End If
        If (params("germanAlphabet") <> Empty) Then
            Me.germanAlphabet = params("germanAlphabet")
        End If
        If (params("lineThickness") <> Empty) Then
            Me.lineThickness = params("lineThickness")
        End If
        Set Me.renderer.controller = Me  '' TODO-GD needed for highlighting
        If params("foregroundColor") <> Empty Then
            Me.renderer.foregroundColor = params("foregroundColor")
        Else
            Me.renderer.foregroundColor = "currentColor"
        End If
        If (params("ariaLabel") <> Empty) Then
            Me.renderer.ariaLabel = params("ariaLabel")
        End If
        
        If (params("minPadding") <> Empty) Then
           Me.renderer.minPadding = params("minPadding")
        Else
           Me.renderer.minPadding = 0
        End If
        Me.reset

End Sub

Public Sub reset()

        Set Me.selected = New iArray
        Set Me.staffgroups = New iArray 'StaffGroupElement
        If Not (Me.engraver Is Nothing) Then
            Me.engraver.reset
        End If
        Set Me.engraver = Nothing
        Me.renderer.reset
        Set Me.dragTarget = Nothing
        Me.dragIndex = -1
        Set Me.dragMouseStart = New point
        Me.dragMouseStart.x = -1
        Me.dragMouseStart.y = -1
        Me.dragYStep = 0
        If (Me.lineThickness) Then
            Me.renderer.setLineThickness Me.lineThickness
        End If

End Sub

'    /**
'     * run the engraving process
'     */
Public Sub engraveABC(abctunes As TuneData, Optional tuneNumber As Integer = 0, Optional lineOffset As Integer = 0)
'        If (abctunes(0) = Empty) Then
'            abctunes = Array(abctunes)
'        End If
        Me.reset
        Dim i As Integer
        'For i = 0 To i < abctunes.Count
            If (tuneNumber = 0) Then
                tuneNumber = i
            End If
            Set Me.GetFontAttr = New GetFontAndAttr
            Set Me.getTxtSize = New getTextSize
            Me.GetFontAttr.init abctunes.formatting, Me.classes
            Me.getTxtSize.init Me.GetFontAttr, Me.renderer.paper
            Me.engraveTune abctunes, tuneNumber, lineOffset
        'End If
End Sub

'    /**
'     * Some of the items on the page are not scaled, so adjust them in the opposite direction of scaling to cancel out the scaling.
'     */
Public Sub adjustNonScaledItems(scale_ As Double)
        Me.width = Me.width / scale_
        Me.renderer.adjustNonScaledItems scale_
End Sub
Public Function getMeasureWidths(abcTune As Dictionary) As iArray

        Me.reset
        Set Me.GetFontAttr = New GetFontAndAttr
        Set Me.getTxtSize = New getTextSize
        Me.GetFontAttr.init abcTune.formatting, Me.classes
        Me.getTxtSize.init Me.GetFontAttr, Me.renderer.paper

        Call Me.setupTune(abcTune, 0)
        Call Me.constructTuneElements(abcTune)
        '' layout() sets the x-coordinate of the abcTune element here:
        '' abcTune.lines[0].staffGroup.voices[0].children[0].x
        Call layout(Me.renderer, abcTune, 0, Me.space)

        Dim ret As New iArray
        Dim section As New Dictionary
        Dim abcLine
        Dim i As Integer
        Dim needNewSection   As Boolean
        
        needNewSection = True
        For i = 0 To i < abcTune.lines.Count
            abcLine = abcTune.lines(i)
            If Not (abcLine.Staff Is Nothing) Then
                If (needNewSection = True) Then
                    section("left") = 0
                    Set section("measureWidths") = New iArray
                    section("height") = Me.renderer.padding.top + Me.renderer.spacing.music + Me.renderer.padding.bottom + 24  '' the 24 is the empirical value added to the bottom of all tunes.
                    section("total") = 0
                    
                    ret.Push section
                    needNewSection = False
                End If
                '' At this point, the voices are laid out so that the bar lines are even with each other. So we just need to get the placement of the first voice.
                If (abcLine.staffGroup.voices.Length > 0) Then
                    Dim voice As VoiceElement
                    Dim foundNotStaffExtra  As Boolean
                    Dim lastXPosition As Double
                    Dim k As Integer
                    Dim child As AbsoluteElement
                    Set voice = abcLine.staffGroup.voices(0)
                    foundNotStaffExtra = False
                    lastXPosition = 0
                    For k = 0 To voice.children.Count - 1
                        Set child = voice.children(k)
                        If (foundNotStaffExtra = False And child.isClef = False And child.isKeySig = False) Then
                            foundNotStaffExtra = True
                            section.left = child.x
                            lastXPosition = child.x
                        End If
                        If (child.typs = "bar") Then
                            section("measureWidths").Push (child.x - lastXPosition)
                            section("total") = section("total") + (child.x - lastXPosition)
                            lastXPosition = child.x
                        End If
                    Next
                End If
                ''section.height += calcHeight(abcLine.staffGroup) * spacing.STEP
             Else
                needNewSection = True
        Next
        Set getMeasureWidths = ret

End Function
Public Function setupTune(abcTune As TuneData, tuneNumber As Integer) As Double
        'line Me.classes.reset

        If IsEmpty(abcTune.formatting.jazzchords) Then
            Me.jazzchords = abcTune.formatting.jazzchords
        End If
        
        Me.renderer.newTune abcTune
        Dim tDic As New Dictionary
        tDic("bagpipes") = abcTune.formatting.bagpipes
        tDic("flatbeams") = abcTune.formatting.flatBeams
        tDic("graceSlurs") = abcTune.formatting.graceSlurs <> False '' undefined is the default, which is true
        Set tDic("percmap") = abcTune.formatting.percmap
        tDic("initialClef") = Me.initialClef
        tDic("jazzchords") = Me.jazzchords
        tDic("germanAlphabet") = Me.germanAlphabet
        Set Me.engraver = N.AbstractEng(Me.getTxtSize, tuneNumber, tDic)
        Me.engraver.setStemHeight Me.renderer.spacingRenderer.stemHeight
        Me.engraver.measureLength = abcTune.getMeterFraction().num / abcTune.getMeterFraction().den
        If (abcTune.formatting.staffwidth <> 0) Then
            Me.width = abcTune.formatting.staffwidth * 1.33  '' The width is expressed in pt  convert to px.
         Else
            If (Me.renderer.isPrint = True) Then
                Me.width = Me.staffwidthPrint
            Else
                Me.width = Me.staffwidthScreen
            End If
        End If

        Dim scale_ As Double
        If abcTune.formatting.scale_ <> 0 Then
            scale_ = abcTune.formatting.scale_
        Else
            scale_ = Me.scale_
        End If
        If (Me.responsive = "resize") Then '' The resizing will mess with the scaling, so just don't do it explicitly.
            scale_ = 0
        End If
        If (scale_ = 0) Then
            If Me.renderer.isPrint = True Then
                scale_ = 0.75
            Else
                scale_ = 1
            End If
        End If
        Me.adjustNonScaledItems scale_
        setupTune = scale_
End Function
    
Public Sub constructTuneElements(abcTune As TuneData)
'/** 生成原始五線譜數據  */

        'line abcTune.topText = new TopText(abcTune.metaText, abcTune.metaTextInfo, abcTune.formatting, abcTune.lines, me.width, me.renderer.isPrint, me.renderer.padding.left, me.renderer.spacing, me.GetTxtSize)

        '' Generate the raw staff line data
        Dim i As Integer
        Dim abcLine As TuneLine
        Dim hasPrintedTempo  As Boolean
        Dim hasSeenNonSubtitle As Boolean
        Dim tmpPrintTempo As vtempoProperties
        hasPrintedTempo = False
        hasSeenNonSubtitle = False
        If hasPrintedTempo = False Then
            Set tmpPrintTempo = abcTune.metaText.tempo
        End If
        
        '自訂
        Set abcLine = New TuneLine
        Set abcLine.staffGroup = Me.engraver.createABCLine(abcTune.lines(0).Staffs, tmpPrintTempo, i)
        
'        for (i = 0  i < abcTune.lines.length  i++) {
'            abcLine = abcTune.lines[i]
'            if (abcLine.staff) {
'                hasSeenNonSubtitle = True
'                abcLine.staffGroup = me.engraver.createABCLine(abcLine.staff, !hasPrintedTempo ? abcTune.metaText.tempo : null, i)
'                hasPrintedTempo = True
'            } else if (abcLine.subtitle) {
'                '' If the subtitle is at the top, then it was already accounted for. So skip all subtitles until the first non-subtitle line.
'                if (hasSeenNonSubtitle) {
'                    var center = Me.width / 2 + Me.renderer.padding.left
'                    abcLine.nonMusic = new Subtitle(me.renderer.spacing.subtitle, abcTune.formatting, abcLine.subtitle, center, me.renderer.padding.left, me.GetTxtSize)
'                }
'            } else if (abcLine.text !== undefined) {
'                hasSeenNonSubtitle = True
'                abcLine.nonMusic = new FreeText(abcLine.text, abcLine.vskip, me.GetFontAttr, me.renderer.padding.left, me.width, me.GetTxtSize)
'            } else if (abcLine.separator !== undefined && abcLine.separator.lineLength) {
'                hasSeenNonSubtitle = True
'                abcLine.nonMusic = new Separator(abcLine.separator.spaceAbove, abcLine.separator.lineLength, abcLine.separator.spaceBelow)
'            }
'        }
'        abcTune.bottomText = new BottomText(abcTune.metaText, me.width, me.renderer.isPrint, me.renderer.padding.left, me.renderer.spacing, me.GetTxtSize)
End Sub

 Public Sub engraveTune(abcTune As TuneData, tuneNumber As Integer, lineOffset As Integer)

 
        Dim scale_ As Double
        scale_ = Me.setupTune(abcTune, tuneNumber)

        '' Create all of the element objects that will appear on the page.
        '' 建立將出現在頁面上的所有元素物件。
        '' 將建立 StaffGroup 物件
        Me.constructTuneElements abcTune

        '' Do all the positioning, both horizontally and vertically
        '' 進行所有的水平和垂直定位 x 的位置
        Dim maxWidth  As Double
        maxWidth = layout(Me.renderer, abcTune, Me.width, Me.space)

        '' Deal with tablature for staff
        '' 處理五線譜的樂譜
'        If Not (abctune.tablatures Is Nothing) Then
'            tablatures.layoutTablatures Me.renderer, abctune
'        End If

'        '' Do all the writing to the SVG
'        '' 用 StaffGroup 將所有內容寫入 SVG
'        Dim ret
'        Set ret = draw(Me.renderer, Me.classes, abctune, Me.width, maxWidth, Me.responsive, scale_, Me.selectTypes, tuneNumber, lineOffset)
'        Set Me.staffgroups = ret.staffgroups
'        Set Me.selectables = ret.selectables
'
'        If (Me.oneSvgPerLine) Then
'            var div = Me.renderer.paper.svg.parentNode
'            Me.svgs = splitSvgIntoLines(Me.renderer, div, abctune.metaText.title, Me.responsive)
'         Else
'            Me.svgs = Array(Me.renderer.paper.svg)
'        End If
'        setupSelection Me, Me.svgs
End Sub


Public Function getDim(historyEl As Dictionary) As Dictionary


        '' Get the dimensions on demand because the getBBox call is expensive.
        If IsEmpty(historyEl("dim")) Then
            Dim sRect As Dictionary
            Dim tdict As New Dictionary
            sRect = historyEl.svgEl.getBBox()
            
            tdict("left") = Int(sRect("x"))
            tdict("top") = Int(sRect("y"))
            tdict("rigth") = Int(sRect("x") + sRect("width"))
            tdict("bottom") = Int(sRect("y") + sRect("height"))
            Set historyEl("dim") = tdict
        End If
        getDim = historyEl("dim")
End Function

Public Sub addSelectListener(clickListener)
        Me.listeners(Me.listeners.Count) = clickListener
    End Sub

Attribute VB_Name = "GetFontAndAttr"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit


Public formatting As vFormatting
Public classes As Dictionary '     classes
Public Sub init(formatting As vFormatting, classes As Dictionary)
        Set Me.formatting = formatting
        Set Me.classes = classes
    End Sub

Public Sub updateFonts(fontOverrides As Staff)

   If Not fontOverrides.gchordfont Is Nothing Then Set Me.formatting.gchordfont = fontOverrides.gchordfont
   If Not fontOverrides.tripletfont Is Nothing Then Set Me.formatting.tripletfont = fontOverrides.tripletfont
   If Not fontOverrides.annotationfont Is Nothing Then Set Me.formatting.annotationfont = fontOverrides.annotationfont
   If Not fontOverrides.vocalfont Is Nothing Then Set Me.formatting.vocalfont = fontOverrides.vocalfont


End Sub

Public Function calc(typs, klass) As Dictionary


        Dim font As vFont
        If (VarType(typs) = vbString) Then
            Set font = Me.formatting(typs)
            '' Raphael deliberately changes the font units to pixels for some reason, so we need to change points to pixels here.
            If Not font Is Nothing Then
                font.face = font.face
                font.size = Int(font.size * 4 / 3)
                font.decoration = font.decoration
                font.style = font.style
                font.weight = font.weight
                font.box = font.box
                
            Else
                font.face = "Arial"
                font.size = Int(12 * 4 / 3)
                font.decoration = "underline"
                font.style = "normal"
                font.weight = "normal"
         Else
             If TypeOf typs Is vFont Then
                font.face = typs.face
                font.size = Int(typs.size * 4 / 3)
                font.decoration = typs.decoration
                font.style = typs.style
                font.weight = typs.weight
                font.box = typs.box
            End If
        End If
        Dim paddingPercent
        paddingPercent = IIf(Me.formatting.fontboxpadding = True, Me.formatting.fontboxpadding, 0.1)
        
        font.padding = font.size * paddingPercent

        Dim attr As New Dictionary
        attr("font-size") = font.size
        attr("font-style") = font.style
        attr("font-family") = font.face
        attr("font-weight") = font.weight
        attr("text-decoration") = font.decoration
        attr("class") = Me.classes.generate(klass)
        Set calc = New Dictionary
        Set calc("font") = font
        Set calc("attr") = attr
End Function

Attribute VB_Name = "GetTextSize"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public gFontAndAttr As GetFontAndAttr
Public svg As SVGmodel        'svg
Public Sub init(g_FontAndAttr As GetFontAndAttr, Optional svg As SVGmodel)
        Set Me.gFontAndAttr = g_FontAndAttr
        Set Me.svg = svg
End Sub

Public Sub updateFonts(fontOverrides As Staff)
        Me.gFontAndAttr.updateFonts fontOverrides
End Sub

Public Function attr(typs, klass)
        attr = Me.gFontAndAttr.calc(typs, klass)
End Function

Public Function calc(text, typs, klass, Optional el As Dictionary) As size
        Dim hash As Dictionary
        '' This can be passed in either a string or a font. If it is a string it names one of the standard fonts.
        If (VarType(typs) = vbString) Then
            hash = Me.attr(typs, klass)
        Else
            Dim f As New vFont
            Dim ar As New Dictionary
            f.face = typs.face
            f.size = typs.size
            f.decoration = typs.decoration
            f.style = typs.style
            f.weight = typs.weight
            
            aa("font-size") = typs.size
            aa("font-style") = typs.style
            aa("font-family") = typs.face
            aa("font-weight") = typs.weight
            aa("text-decoration") = typs.decoration
            aa("class") = Me.GetFontAttr.classes.generate(klass)
            hash("font") = f
            hash("attr") = ar
        End If
        
        Dim si As size
        si = Me.svg.getTxtSize(text, hash("attr"), el)
        If (hash.font.box) Then
            '' Add padding and an equal margin to each side.
            si.height = size.height + hash.font.padding * 4
            si.width = size.width + hash.font.padding * 4
        End If
        calc = si
End Function

Public Function baselineToCenter(text As String, typs As String, klass As String, index As Integer, total As Double) As Double
        '' This is for the case where SVG wants to use the baseline of the first line as the Y coordinate.
        '' If there are multiple lines of text or there is an array of text then that will not be centered so this adjusts it.
        Dim height  As Double
        Dim fontHeight  As Double
        height = Me.calc(text, typs, klass).height
        fontHeight = Me.attr(typs, klass).font.size

        baselineToCenter = height * 0.5 + (total - index - 2) * fontHeight
End Function

Attribute VB_Name = "GlyphsModule"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'Option Explicit
''
''import spacing from '../helpers/spacing'
''import Svg from '../svg'

Public glyphs As New Dictionary


Public Function pathClone(pathArray)
    Dim res(UBound(pathArray))
    'Dim charr()
    Dim i As Integer
    Dim j As Integer
    
    For i = 0 To UBound(pathArray) - 1
        res [i] = []
        Dim charr(UBound(pathArray(i)))
        For j = 0 To UBound(pathArray(i)) - 1
        
            charr(j) = pathArray(i, j)
        Next
        res(i) = charr
    Next
    pathClone = res
End Function

Public Sub pathScale(ByRef pathArray, kx, ky)
    Dim i As Integer, ii As Integer
    Dim j As Integer, jj As Integer
    Dim p
    ii = UBound(pathArray) - 1
    For i = 0 To ii
        Set p = pathArray(i)
        jj = UBound(p) - 1
        For j = 1 To jj
            p(j) = p(j) * IIf((j Mod 2), kx, ky)
        Next
    Next
End Sub

Public Function printSymbol(x As Double, y As Double, symb As String, paper As SVGmodel, attrs As Dictionary)
        Dim pathArray, path, i
        If (glyphs(symb) Is Nothing) Then
            Set printSymbol = Nothing
        End If

        Set pathArray = pathClone(glyphs(symb).d)
        pathArray(0)(1) = pathArray(0)(1) + x
        pathArray(0)(2) = pathArray(0)(2) + y
        path = ""
        For i = 0 To UBound(pathArray) - 1
            path = path + Join(pathArray(i), " ")
        Next
        attrs.path = path
        Debug.Print "svg 要繪圖的地方: code:123ew81as2"
        'return paper.path(attrs)
End Function

Public Function getPathForSymbol(x As Double, y As Double, symb As String, scalex As Double, scaley As Double)
        scalex = IIf(scalex, scalex, 1)
        scaley = IIf(scaley, scaley, 1)
        If (glyphs(symb) Is Nothing) Then
            Set getPathForSymbol = Nothing
            Exit Function
        End If
        Dim pathArray
        pathArray = pathClone(glyphs(symb).d)
        If (scalex <> 1 Or scaley <> 1) Then pathScale pathArray, scalex, scaley
        pathArray(0, 1) = pathArray(0, 1) + x
        pathArray(0, 2) = pathArray(0, 2) + y

        getPathForSymbol = pathArray
End Function

Public Function getSymbolWidth(symbol As String) As Double
        If Not (glyphs(symbol) Is Nothing) Then
            getSymbolWidth = glyphs(symbol).w
        Else
            getSymbolWidth = 0
        End If
End Function

Public Function symbolHeightInPitches(symbol As String) As Double
        Dim height As Double
        height = IIf(Not glyphs(symbol) Is Nothing, glyphs(symbol).h, 0)
        symbolHeightInPitches = height / spacing.Step
End Function

Public Function getSymbolAlign(symbol As String) As String
        If (InStr(1, symbol, "scripts") > 0 And _
            symbol <> "scripts.roll") Then
            getSymbolAlign = "center"
        End If
        getSymbolAlign = "left"
End Function

Public Function getYCorr(symbol As String) As Integer
        Select Case (symbol)
            Case "0", "1", "2":
            Case "3", "4", "5", "6", "7", "8", "9", "+":
                getYCorr = -1
            Case "timesig.common", "timesig.cut": getYCorr = 0
            Case "flags.d32nd": getYCorr = -1
            Case "flags.d64th": getYCorr = -2
            Case "flags.u32nd": getYCorr = 1
            Case "flags.u64th": getYCorr = 3
            Case "rests.whole": getYCorr = 1
            Case "rests.half": getYCorr = -1
            Case "rests.8th": getYCorr = -1
            Case "rests.quarter": getYCorr = -1
            Case "rests.16th": getYCorr = -1
            Case "rests.32nd": getYCorr = -1
            Case "rests.64th": getYCorr = -1
            Case "f", "m", "p", "s", "z":
                getYCorr = -4
            Case "scripts.trill", "scripts.upbow", "scripts.downbow":
                getYCorr = -2
            Case "scripts.ufermata", "scripts.wedge", "scripts.roll", "scripts.shortphrase", "scripts.longphrase":
                getYCorr = -1
            Case "scripts.dfermata":
                getYCorr = 1
            Case Else
                getYCorr = 0
        End Select
End Function
Public Sub setSymbol(Name, path)
        glyphs("name") = path
    
End Sub

Function createSym(d As String, w As Double, h As Double) As vGlyphTyps
    Set createSym = New vGlyphTyps
    createSym.d = d
    createSym.w = w
    createSym.h = h

End Function

Private Sub Class_Initialize()


    
    Set glyphs("note.0") = createSym("path as string", 14, 16)
    Set glyphs("note.1") = createSym("path as string", 14, 16)
    Set glyphs("note.2") = createSym("path as string", 14, 16)
    Set glyphs("note.3") = createSym("path as string", 14, 16)
    Set glyphs("note.4") = createSym("path as string", 14, 16)
    Set glyphs("note.5") = createSym("path as string", 14, 16)
    Set glyphs("note.6") = createSym("path as string", 14, 16)
    Set glyphs("note.7") = createSym("path as string", 14, 16)
    Set glyphs("note.8") = createSym("path as string", 14, 16)
    Set glyphs("note.9") = createSym("path as string", 14, 16)
    Set glyphs("clefs.none") = createSym("path as string", 9, 9)
    Set glyphs("0") = createSym("path as string", 10.78, 14.959)
    Set glyphs("1") = createSym("path as string", 8.94, 15.058)
    Set glyphs("2") = createSym("path as string", 10.764, 14.97)
    Set glyphs("3") = createSym("path as string", 9.735, 14.967)
    Set glyphs("4") = createSym("path as string", 11.795, 14.994)
    Set glyphs("5") = createSym("path as string", 10.212, 14.997)
    Set glyphs("6") = createSym("path as string", 9.956, 14.982)
    Set glyphs("7") = createSym("path as string", 10.561, 15.093)
    Set glyphs("8") = createSym("path as string", 10.926, 14.989)
    Set glyphs("9") = createSym("path as string", 9.959, 14.986)
    Set glyphs("rests.multimeasure") = createSym("path as string", 42, 18)
    Set glyphs("rests.whole") = createSym("path as string", 11.25, 4.68)
    Set glyphs("rests.half") = createSym("path as string", 11.25, 4.68)
    Set glyphs("rests.quarter") = createSym("path as string", 7.888, 21.435)
    Set glyphs("rests.8th") = createSym("path as string", 7.534, 13.883)
    Set glyphs("rests.16th") = createSym("path as string", 9.724, 21.383)
    Set glyphs("rests.32nd") = createSym("path as string", 11.373, 28.883)
    Set glyphs("rests.64th") = createSym("path as string", 12.453, 36.383)
    Set glyphs("rests.128th") = createSym("path as string", 12.992, 43.883)
    Set glyphs("accidentals.sharp") = createSym("path as string", 8.25, 22.462)
    Set glyphs("accidentals.halfsharp") = createSym("path as string", 5.25, 20.174)
    Set glyphs("accidentals.nat") = createSym("path as string", 5.4, 22.8)
    Set glyphs("accidentals.flat") = createSym("path as string", 6.75, 18.801)
    Set glyphs("accidentals.halfflat") = createSym("path as string", 6.728, 18.801)
    Set glyphs("accidentals.dblflat") = createSym("path as string", 12.1, 18.804)
    Set glyphs("accidentals.dblsharp") = createSym("path as string", 7.95, 7.977)
    Set glyphs("dots.dot") = createSym("path as string", 3.45, 3.45)
    Set glyphs("noteheads.dbl") = createSym("path as string", 16.83, 8.145)
    Set glyphs("noteheads.whole") = createSym("path as string", 14.985, 8.097)
    Set glyphs("noteheads.half") = createSym("path as string", 10.37, 8.132)
    Set glyphs("noteheads.quarter") = createSym("path as string", 9.81, 8.094)
    Set glyphs("noteheads.slash.nostem") = createSym("path as string", 12.81, 15.63)
    Set glyphs("noteheads.indeterminate") = createSym("path as string", 9.843, 8.139)
    Set glyphs("scripts.ufermata") = createSym("path as string", 19.748, 11.289)
    Set glyphs("scripts.dfermata") = createSym("path as string", 19.744, 11.274)
    Set glyphs("scripts.sforzato") = createSym("path as string", 13.5, 7.5)
    Set glyphs("scripts.staccato") = createSym("path as string", 2.989, 3.004)
    Set glyphs("scripts.tenuto") = createSym("path as string", 8.985, 1.08)
    Set glyphs("scripts.umarcato") = createSym("path as string", 7.5, 8.245)
    Set glyphs("scripts.dmarcato") = createSym("path as string", 7.5, 8.25)
    Set glyphs("scripts.stopped") = createSym("path as string", 8.295, 8.295)
    Set glyphs("scripts.upbow") = createSym("path as string", 9.73, 15.608)
    Set glyphs("scripts.downbow") = createSym("path as string", 11.22, 9.992)
    Set glyphs("scripts.turn") = createSym("path as string", 16.366, 7.893)
    Set glyphs("scripts.trill") = createSym("path as string", 17.963, 16.49)
    Set glyphs("scripts.segno") = createSym("path as string", 15, 22.504)
    Set glyphs("scripts.coda") = createSym("path as string", 16.035, 21.062)
    Set glyphs("scripts.comma") = createSym("path as string", 3.042, 9.237)
    Set glyphs("scripts.roll") = createSym("path as string", 10.817, 6.125)
    Set glyphs("scripts.prall") = createSym("path as string", 15.011, 7.5)
    Set glyphs("scripts.arpeggio") = createSym("path as string", 5, 10)
    Set glyphs("scripts.mordent") = createSym("path as string", 15.011, 10.012)
    Set glyphs("flags.u8th") = createSym("path as string", 6.692, 22.59)
    Set glyphs("flags.u16th") = createSym("path as string", 6.693, 26.337)
    Set glyphs("flags.u32nd") = createSym("path as string", 6.697, 32.145)
    Set glyphs("flags.u64th") = createSym("path as string", 6.682, 39.694)
    Set glyphs("flags.d8th") = createSym("path as string", 8.492, 21.691)
    Set glyphs("flags.ugrace") = createSym("path as string", 12.019, 9.954)
    Set glyphs("flags.dgrace") = createSym("path as string", 15.12, 9.212)
    Set glyphs("flags.d16th") = createSym("path as string", 8.475, 22.591)
    Set glyphs("flags.d32nd") = createSym("path as string", 8.385, 29.191)
    Set glyphs("flags.d64th") = createSym("path as string", 8.485, 32.932)
    Set glyphs("clefs.C") = createSym("path as string", 20.31, 29.97)
    Set glyphs("clefs.F") = createSym("path as string", 20.153, 23.142)
    Set glyphs("clefs.G") = createSym("path as string", 19.051, 57.057)
    Set glyphs("clefs.perc") = createSym("path as string", 21, 14.97)
    Set glyphs("tab.big") = createSym("path as string", 19.643, 43.325)
    Set glyphs("tab.tiny") = createSym("path as string", 15.709, 34.656)
    Set glyphs("timesig.common") = createSym("path as string", 13.038, 15.689)
    Set glyphs("timesig.cut") = createSym("path as string", 13.038, 20.97)
    Set glyphs("timesig.imperfectum") = createSym("path as string", 13.038, 20.97)
    Set glyphs("timesig.imperfectum2") = createSym("path as string", 13.038, 20.97)
    Set glyphs("timesig.perfectum") = createSym("path as string", 13.038, 20.97)
    Set glyphs("timesig.perfectum2") = createSym("path as string", 13.038, 20.97)
    Set glyphs("f") = createSym("path as string", 16.155, 19.445)
    Set glyphs("m") = createSym("path as string", 14.687, 9.126)
    Set glyphs("p") = createSym("path as string", 14.689, 13.127)
    Set glyphs("r") = createSym("path as string", 9.41, 9.132)
    Set glyphs("s") = createSym("path as string", 6.632, 8.758)
    Set glyphs("z") = createSym("path as string", 8.573, 8.743)
    Set glyphs("+") = createSym("path as string", 7.507, 7.515)
    Set glyphs(",") = createSym("path as string", 3.452, 8.143)
    Set glyphs("-") = createSym("path as string", 5.001, 0.81)
    Set glyphs(".") = createSym("path as string", 3.413, 3.402)
    Set glyphs("scripts.wedge") = createSym("path as string", 7.49, 7.752)
    Set glyphs("scripts.thumb") = createSym("path as string", 5.955, 9.75)
    Set glyphs("scripts.open") = createSym("path as string", 5.955, 7.5)
    Set glyphs("scripts.longphrase") = createSym("path as string", 2.16, 23.04)
    Set glyphs("scripts.mediumphrase") = createSym("path as string", 2.16, 15.54)
    Set glyphs("scripts.shortphrase") = createSym("path as string", 2.16, 8.04)
    Set glyphs("scripts.snap") = createSym("path as string", 10.38, 6.84)
    Set glyphs("noteheads.slash.whole") = createSym("path as string", 10.81, 15.63)
    Set glyphs("noteheads.slash.quarter") = createSym("path as string", 9, 9)
    Set glyphs("noteheads.harmonic.quarter") = createSym("path as string", 7.5, 8.165)
    Set glyphs("noteheads.triangle.quarter") = createSym("path as string", 9, 9)

End Sub

Attribute VB_Name = "GlyphsUtility"
Option Explicit

Type SymbolFormat
    c As String * 20
    w As Double
    h As Double
    wLeft As Double
    wRight As Double
    hTob As Double
    hBottom As Double
End Type

Public Enum GLS
    asdferr
End Enum


    
    Sub printREF()
        
        Dim rr As Object
        Set rr = ThisDrawing.Blocks
        Dim blockRefObj As AcadBlockReference
        Dim comm As Collection
        Dim i
        Dim ccs As String
        Dim cName As String
        Dim w, h
        Dim midDownPt(0 To 2) As Double
        Dim height As Double
        Dim minExt As Variant
        Dim maxExt As Variant
        Dim sf As SymbolFormat

        midDownPt(0) = 0
        midDownPt(1) = 0
        midDownPt(2) = 0
        For i = 0 To rr.Count - 1
            cName = ThisDrawing.Blocks.item(i).Name
            ccs = Mid(ThisDrawing.Blocks.item(i).Name, 1, 1)
            
            'midDownPt(0) = (i \ 20) * 2
            'midDownPt(1) = i / 20 * 2
            If ccs = "M" Then
            
                Set blockRefObj = ThisDrawing.ModelSpace.InsertBlock(midDownPt, ThisDrawing.Blocks.item(i).Name, 1, 1, 1, 0)
                blockRefObj.GetBoundingBox minExt, maxExt  ' 取的大小
                If minExt(0) < 0 Then
                    If maxExt(0) > 0 Then
                        sf.w = minExt(0)
                        sf.wLeft = minExt(0)
                        sf.wRight = maxExt(0)
                    Else
                        sf.w = minExt(0)
                        sf.wLeft = minExt(0)
                        sf.wRight = 0
                    End If
                Else
                        sf.w = maxExt(0)
                        sf.wLeft = 0
                        sf.wRight = maxExt(0)
                End If
                
                If minExt(1) <= 0 Then
                    If maxExt(1) > 0 Then
                        sf.h = Format(minExt(1), "0.00")
                        sf.hBottom = Format(minExt(1), "0.00")
                        sf.hTob = Format(maxExt(1), "0.00")
                    Else
                        sf.w = Format(minExt(1), "0.00")
                        sf.hBottom = Format(minExt(1), "0.00")
                        sf.hTob = 0
                    End If
                Else
                        sf.h = Format(maxExt(1), "0.00")
                        sf.hBottom = 0
                        sf.hTob = Format(maxExt(1), "0.00")
                End If
                
                Debug.Print cName & " w:" & Format(w, "0.00") & " " & Format(minExt(0), "0.00") & " " & Format(maxExt(0), "0.00") & _
                " h:" & Format(h, "0.00") & " " & Format(minExt(1), "0.00") & " " & Format(maxExt(1), "0.00")
                
                glyphs.Push cName & " " & Format(sf.w, "0.00") _
                    & " " & Format(sf.h, "0.00") _
                    & " " & Format(sf.wLeft, "0.00") _
                    & " " & Format(sf.wRight, "0.00") _
                    & " " & Format(sf.hBottom, "0.00") _
                    & " " & Format(sf.hTob, "0.00")
            End If

        Next
        
        Debug.Print glyphs.ToString(vbCrLf)
'    For i = 0 To glyphs.Count - 1
'        Set sf = glyphs(i)
'
'        Debug.Print sf.c & " " & sf.w & " " & sf.h & " " & sf.wLeft & " " & sf.wRight & " " & sf.hBottom & " " & sf.hTob
'    Next
        
      
    
        
    End Sub

Sub glyphsInit()


    Dim sf As SymbolFormat
    
    sf.c = "MT0122 " & _
"MT0120" & _
"MT0099" & _
"MT0118" & _
"MT0097" & _
"MT0115" & _
"MT0100" & _
"MT0112" & _
"MT0090" & _
"MT0065" & _
"MT0045" & _
"MT0061" & _
"MT0116" & _
"MT0119" & _
"MT0064"

    Dim arr As New iArray
    
    arr.Push "MT" & Format(Asc("z"), "0000") 'ASC_z 122 ChrW(&H6416)  ' z 大指
   arr.Push "MT" & Format(Asc("x"), "0000") 'ASC_x 120 ChrW(&H641A)  ' x 食指
arr.Push "MT" & Format(Asc("c"), "0000") 'ASC_c 99 ChrW(&H641C)  ' c 中指
arr.Push "MT" & Format(Asc("v"), "0000") 'ASC_v 118 ChrW(&H641F)  ' v 無名指
arr.Push "MT" & Format(Asc("a"), "0000") 'ASC_a 97 ChrW(&H6421)  ' a 八度
arr.Push "MT" & Format(Asc("s"), "0000") 'ASC_s 115 ChrW(&H66FC)  ' s 王字指法
arr.Push "MT" & Format(Asc("d"), "0000") 'ASC_d 100 ChrW(&H6700)  ' d 搖指
arr.Push "MT" & Format(Asc("p"), "0000")  'ASC_p 112 ChrW(&H6381)  ' p 卜指法
arr.Push "MT" & Format(Asc("Z"), "0000") 'ASC_Z 90 ChrW(&H6418)  ' 大寫Z 反大指法
arr.Push "MT" & Format(Asc("A"), "0000") 'ASC_A 65 ChrW(&H6413)  ' 大寫A 反八度
arr.Push "MT" & Format(Asc("-"), "0000") 'ASC_- 45 ChrW(&H66F7)  ' - 間一旋
arr.Push "MT" & Format(Asc("="), "0000") 'ASC_= 61 ChrW(&H66F8)  ' = 間二旋
arr.Push "MT" & Format(Asc("t"), "0000")  'ASC_t 116 ChrW(&H670B)  ' t 打圓 托勾
arr.Push "MT" & Format(Asc("w"), "0000") 'ASC_w 119 ChrW(&H670B)  ' w 柔音
arr.Push "MT" & Format(Asc("@"), "0000") 'ASC_w 119 ChrW(&H670B)  '
{"MT0122"
"MT0120"
"MT0099"
"MT0118"
"MT0097"
"MT0115"
"MT0100"
"MT0112"
"MT0090"
"MT0065"
"MT0045"
"MT0061"
"MT0116"
"MT0119"
"MT0064"}
Debug.Print arr.ToString(vbCrLf)
End Sub

Attribute VB_Name = "JavascriptModule"
Option Explicit
'可以用 網頁的 javascript
Public WD As SeleniumBasic.IWebDriver
Dim abcJSON As String
Sub Baidu_Chrome()
    On Error GoTo Err1
    Dim Service As SeleniumBasic.ChromeDriverService
    Dim options As SeleniumBasic.ChromeOptions
    Set WD = New SeleniumBasic.IWebDriver
    Set Service = New SeleniumBasic.ChromeDriverService
    With Service
        .CreateDefaultService driverPath:="C:\GitHub\SeleniumBasic\Drivers"
        .HideCommandPromptWindow = True
    End With
    Set options = New SeleniumBasic.ChromeOptions
    With options
        .BinaryLocation = "C:\Program Files (x86)\Google\Chrome\Application\chrome.exe"
        .AddExcludedArgument "enable-automation"
        .AddArgument "--start-maximized"
        '.DebuggerAddress = "127.0.0.1:9999" '不要与其他几?混用
    End With
    WD.New_ChromeDriver Service:=Service, options:=options
    'WD.URL = "https:''www.baidu.com"
    WD.url = "file:''/C:/GitHub/abc2svg/zabc/edit-lin.html"
    Dim form As SeleniumBasic.IWebElement
    Dim Keyword As SeleniumBasic.IWebElement
    Dim button As SeleniumBasic.IWebElement
    Set form = WD.FindElementById("form")
    Set Keyword = form.FindElementById("kw")
    Keyword.Clear
    Keyword.SendKeys "好看的人"
    Set button = form.FindElementById("su")
    button.Click
    Debug.Print WD.title, WD.url
    Debug.Print WD.PageSource
    'MsgBox "下面退出 Web。"
    'WD.Quit
    Exit Sub
Err1:
    MsgBox err.Description, vbCritical
End Sub

Sub aas()
'WD.URL = "file:''/C:/GitHub/abc2svg/zabc/edit-lin.html"
Baidu_appition
Call WD.ExecuteScript("alert('Hello,ryueifu！')")

End Sub
Sub ttm55()
Dim prod As Variant
Baidu_appition
prod = WD.ExecuteScript("return ttm.ui")
Debug.Print prod
prod = WD.ExecuteScript("return toAcadMusicJSON()")
Debug.Print prod

End Sub
Sub tt123()
Dim prod As Variant
Dim aas As SeleniumBasic.IOptions
prod = WD.ExecuteScript("return tt123")
Debug.Print prod

End Sub

Function getAbcJson()
    Dim prod As Variant
    Baidu_appition
    
    prod = WD.ExecuteScript("return toAcadMusicJSON()")
    Debug.Print prod

End Function
Function testJSON()
    Dim JsonString As String
    Dim JsonObject
    Dim Json As Dictionary
    Set Json = JsonConverter.ParseJson("{""a"":123,""b"":[1,2,3,4],""c"":{""d"":456}}")
    
    ' Json("a") -> 123
    ' Json("b")(2) -> 2
    ' Json("c")("d") -> 456
    Json("c")("e") = 789
    
    Debug.Print JsonConverter.ConvertToJson(Json)
    ' -> "{"a":123,"b":[1,2,3,4],"c":{"d":456,"e":789}}"
    
    Debug.Print JsonConverter.ConvertToJson(Json, Whitespace:=2)
    Debug.Print Json.Count

End Function

Function voieMusic()
    Dim vvbase As New voiceBase
    Debug.Print vvbase.typs
    vvbase.typs = 3
    Debug.Print vvbase.typs
    
    Dim vvbar As New voiceBar
    Debug.Print vvbar.typs
End Function

Sub Baidu_Opera()
    On Error GoTo Err1
    Dim Service As SeleniumBasic.OperaDriverService
    Dim options As SeleniumBasic.OperaOptions
    Set WD = New SeleniumBasic.IWebDriver
    Set Service = New SeleniumBasic.OperaDriverService
    With Service
        .CreateDefaultService driverPath:="C:\GitHub\SeleniumBasic\Drivers", driverexecutablefilename:="chromedriver.exe"
        .HideCommandPromptWindow = True
    End With
    Set options = New SeleniumBasic.OperaOptions
    With options
        '.BinaryLocation = "C:\Users\Administrator\AppData\Local\Programs\Opera\71.0.3770.148\opera.exe"
        .BinaryLocation = "C:\Program Files (x86)\Google\Chrome\Application\chrome.exe"
    End With
    WD.New_OperaDriver Service:=Service, options:=options
    WD.Navigate.GoToUrl "https:''www.baidu.com"
    Dim form As SeleniumBasic.IWebElement
    Dim Keyword As SeleniumBasic.IWebElement
    Dim button As SeleniumBasic.IWebElement
    Set form = WD.FindElementById("form")
    Set Keyword = form.FindElementById("kw")
    Keyword.Clear
    Keyword.SendKeys "VBA Selenium"
    Set button = form.FindElementById("su")
    button.Click
    Debug.Print WD.title, WD.url
    Debug.Print WD.PageSource
    MsgBox "狟醱豖堤銡擬ん﹝"
    WD.Quit
    Exit Sub
Err1:
    MsgBox err.Description, vbCritical
End Sub

Sub Baidu2()
    On Error GoTo Err1
    Set WD = New SeleniumBasic.IWebDriver
    WD.New_ChromeDriver
    WD.url = "https:''www.baidu.com"
    MsgBox "下面退出??器。"
    WD.Quit
    Exit Sub
Err1:
    MsgBox err.Description, vbCritical
End Sub


Sub Baidu_appition()
    Dim Service As SeleniumBasic.ChromeDriverService
    Dim options As SeleniumBasic.ChromeOptions
    Set WD = New SeleniumBasic.IWebDriver
    Set Service = New SeleniumBasic.ChromeDriverService
    With Service
        .CreateDefaultService driverPath:="C:\GitHub\SeleniumBasic\Drivers"
        .HideCommandPromptWindow = True
    End With
    Set options = New SeleniumBasic.ChromeOptions
    With options
        .BinaryLocation = "C:\Program Files (x86)\Google\Chrome\Application\chrome.exe"
        '.AddExcludedArgument "enable-automation"
        '.AddArgument "--start-maximized"
        .DebuggerAddress = "127.0.0.1:9999" '不要与其他幾個混用
    End With

    WD.New_ChromeDriver Service:=Service, options:=options
    'WD.URL = "file:''/C:/GitHub/abc2svg/zabc/edit-lin.html"
End Sub

Attribute VB_Name = "JsonConverter"
''
' VBA-JSON v2.3.1
' (c) Tim Hall - https:''github.com/VBA-tools/VBA-JSON
'
' JSON Converter for VBA
'
' Errors:
' 10001 - JSON parse error
'
' @class JsonConverter
' @author tim.hall.engr@gmail.com
' @license MIT (http:''www.opensource.org/licenses/mit-license.php)
'' ~~~~~~~~~~~~~~~~~~~~~~~~~~~~~~~~~~~~~~~~~~~~~~~~~~~~~~~~~~~~~~~~~~~~~~ '
'
' Based originally on vba-json (with extensive changes)
' BSD license included below
'
' JSONLib, http:''code.google.com/p/vba-json/
'
' Copyright (c) 2013, Ryo Yokoyama
' All rights reserved.
'
' Redistribution and use in source and binary forms, with or without
' modification, are permitted provided that the following conditions are met:
'     * Redistributions of source code must retain the above copyright
'       notice, this list of conditions and the following disclaimer.
'     * Redistributions in binary form must reproduce the above copyright
'       notice, this list of conditions and the following disclaimer in the
'       documentation and/or other materials provided with the distribution.
'     * Neither the name of the <organization> nor the
'       names of its contributors may be used to endorse or promote products
'       derived from this software without specific prior written permission.
'
' THIS SOFTWARE IS PROVIDED BY THE COPYRIGHT HOLDERS AND CONTRIBUTORS "AS IS" AND
' ANY EXPRESS OR IMPLIED WARRANTIES, INCLUDING, BUT NOT LIMITED TO, THE IMPLIED
' WARRANTIES OF MERCHANTABILITY AND FITNESS FOR A PARTICULAR PURPOSE ARE
' DISCLAIMED. IN NO EVENT SHALL <COPYRIGHT HOLDER> BE LIABLE FOR ANY
' DIRECT, INDIRECT, INCIDENTAL, SPECIAL, EXEMPLARY, OR CONSEQUENTIAL DAMAGES
' (INCLUDING, BUT NOT LIMITED TO, PROCUREMENT OF SUBSTITUTE GOODS OR SERVICES
' LOSS OF USE, DATA, OR PROFITS  OR BUSINESS INTERRUPTION) HOWEVER CAUSED AND
' ON ANY THEORY OF LIABILITY, WHETHER IN CONTRACT, STRICT LIABILITY, OR TORT
' (INCLUDING NEGLIGENCE OR OTHERWISE) ARISING IN ANY WAY OUT OF THE USE OF THIS
' SOFTWARE, EVEN IF ADVISED OF THE POSSIBILITY OF SUCH DAMAGE.
' ~~~~~~~~~~~~~~~~~~~~~~~~~~~~~~~~~~~~~~~~~~~~~~~~~~~~~~~~~~~~~~~~~~~~~~ '
Option Explicit

' === VBA-UTC Headers
#If Mac Then

#If VBA7 Then

' 64-bit Mac (2016)
Private Declare PtrSafe Function utc_popen Lib "/usr/lib/libc.dylib" Alias "popen" _
    (ByVal utc_Command As String, ByVal utc_Mode As String) As LongPtr
Private Declare PtrSafe Function utc_pclose Lib "/usr/lib/libc.dylib" Alias "pclose" _
    (ByVal utc_File As LongPtr) As LongPtr
Private Declare PtrSafe Function utc_fread Lib "/usr/lib/libc.dylib" Alias "fread" _
    (ByVal utc_Buffer As String, ByVal utc_Size As LongPtr, ByVal utc_Number As LongPtr, ByVal utc_File As LongPtr) As LongPtr
Private Declare PtrSafe Function utc_feof Lib "/usr/lib/libc.dylib" Alias "feof" _
    (ByVal utc_File As LongPtr) As LongPtr

#Else

' 32-bit Mac
Private Declare Function utc_popen Lib "libc.dylib" Alias "popen" _
    (ByVal utc_Command As String, ByVal utc_Mode As String) As Long
Private Declare Function utc_pclose Lib "libc.dylib" Alias "pclose" _
    (ByVal utc_File As Long) As Long
Private Declare Function utc_fread Lib "libc.dylib" Alias "fread" _
    (ByVal utc_Buffer As String, ByVal utc_Size As Long, ByVal utc_Number As Long, ByVal utc_File As Long) As Long
Private Declare Function utc_feof Lib "libc.dylib" Alias "feof" _
    (ByVal utc_File As Long) As Long

#End If

#ElseIf VBA7 Then

' http:''msdn.microsoft.com/en-us/library/windows/desktop/ms724421.aspx
' http:''msdn.microsoft.com/en-us/library/windows/desktop/ms724949.aspx
' http:''msdn.microsoft.com/en-us/library/windows/desktop/ms725485.aspx
Private Declare PtrSafe Function utc_GetTimeZoneInformation Lib "kernel32" Alias "GetTimeZoneInformation" _
    (utc_lpTimeZoneInformation As utc_TIME_ZONE_INFORMATION) As Long
Private Declare PtrSafe Function utc_SystemTimeToTzSpecificLocalTime Lib "kernel32" Alias "SystemTimeToTzSpecificLocalTime" _
    (utc_lpTimeZoneInformation As utc_TIME_ZONE_INFORMATION, utc_lpUniversalTime As utc_SYSTEMTIME, utc_lpLocalTime As utc_SYSTEMTIME) As Long
Private Declare PtrSafe Function utc_TzSpecificLocalTimeToSystemTime Lib "kernel32" Alias "TzSpecificLocalTimeToSystemTime" _
    (utc_lpTimeZoneInformation As utc_TIME_ZONE_INFORMATION, utc_lpLocalTime As utc_SYSTEMTIME, utc_lpUniversalTime As utc_SYSTEMTIME) As Long

#Else

Private Declare Function utc_GetTimeZoneInformation Lib "kernel32" Alias "GetTimeZoneInformation" _
    (utc_lpTimeZoneInformation As utc_TIME_ZONE_INFORMATION) As Long
Private Declare Function utc_SystemTimeToTzSpecificLocalTime Lib "kernel32" Alias "SystemTimeToTzSpecificLocalTime" _
    (utc_lpTimeZoneInformation As utc_TIME_ZONE_INFORMATION, utc_lpUniversalTime As utc_SYSTEMTIME, utc_lpLocalTime As utc_SYSTEMTIME) As Long
Private Declare Function utc_TzSpecificLocalTimeToSystemTime Lib "kernel32" Alias "TzSpecificLocalTimeToSystemTime" _
    (utc_lpTimeZoneInformation As utc_TIME_ZONE_INFORMATION, utc_lpLocalTime As utc_SYSTEMTIME, utc_lpUniversalTime As utc_SYSTEMTIME) As Long

#End If

#If Mac Then

#If VBA7 Then
Private Type utc_ShellResult
    utc_Output As String
    utc_ExitCode As LongPtr
End Type

#Else

Private Type utc_ShellResult
    utc_Output As String
    utc_ExitCode As Long
End Type

#End If

#Else

Private Type utc_SYSTEMTIME
    utc_wYear As Integer
    utc_wMonth As Integer
    utc_wDayOfWeek As Integer
    utc_wDay As Integer
    utc_wHour As Integer
    utc_wMinute As Integer
    utc_wSecond As Integer
    utc_wMilliseconds As Integer
End Type

Private Type utc_TIME_ZONE_INFORMATION
    utc_Bias As Long
    utc_StandardName(0 To 31) As Integer
    utc_StandardDate As utc_SYSTEMTIME
    utc_StandardBias As Long
    utc_DaylightName(0 To 31) As Integer
    utc_DaylightDate As utc_SYSTEMTIME
    utc_DaylightBias As Long
End Type

#End If
' === End VBA-UTC

Private Type json_Options
    ' VBA only stores 15 significant digits, so any numbers larger than that are truncated
    ' This can lead to issues when BIGINT's are used (e.g. for Ids or Credit Cards), as they will be invalid above 15 digits
    ' See: http:''support.microsoft.com/kb/269370
    '
    ' By default, VBA-JSON will use String for numbers longer than 15 characters that contain only digits
    ' to override set `JsonConverter.JsonOptions.UseDoubleForLargeNumbers = True`
    UseDoubleForLargeNumbers As Boolean

    ' The JSON standard requires object keys to be quoted (" or '), use this option to allow unquoted keys
    AllowUnquotedKeys As Boolean

    ' The solidus (/) is not required to be escaped, use this option to escape them as \/ in ConvertToJson
    EscapeSolidus As Boolean
End Type
Public JsonOptions As json_Options

' ============================================= '
' Public Methods
' ============================================= '

''
' Convert JSON string to object (Dictionary/Collection)
'
' @method ParseJson
' @param {String} json_String
' @return {Object} (Dictionary or Collection)
' @throws 10001 - JSON parse error
''
Public Function ParseJson(ByVal JsonString As String) As Dictionary
    Dim json_Index As Long
    json_Index = 1

    ' Remove vbCr, vbLf, and vbTab from json_String
    JsonString = VBA.Replace(VBA.Replace(VBA.Replace(JsonString, VBA.vbCr, ""), VBA.vbLf, ""), VBA.vbTab, "")

    json_SkipSpaces JsonString, json_Index
    Select Case VBA.Mid$(JsonString, json_Index, 1)
    Case "{"
        Set ParseJson = json_ParseObject(JsonString, json_Index)
    Case "["
        Set ParseJson = json_ParseArray(JsonString, json_Index)
    Case Else
        ' Error: Invalid JSON string
        MsgBox "不知為何 error line 10aaa"
        err.Raise 10001, "JSONConverter", json_ParseErrorMessage(JsonString, json_Index, "Expecting '{' or '['")
    End Select
End Function

''
' Convert object (Dictionary/Collection/Array) to JSON
'
' @method ConvertToJson
' @param {Variant} JsonValue (Dictionary, Collection, or Array)
' @param {Integer|String} Whitespace "Pretty" print json with given number of spaces per indentation (Integer) or given string
' @return {String}
''
Public Function ConvertToJson(ByVal JsonValue As Variant, Optional ByVal Whitespace As Variant, Optional ByVal json_CurrentIndentation As Long = 0) As String
    Dim json_Buffer As String
    Dim json_BufferPosition As Long
    Dim json_BufferLength As Long
    Dim json_Index As Long
    Dim json_LBound As Long
    Dim json_UBound As Long
    Dim json_IsFirstItem As Boolean
    Dim json_Index2D As Long
    Dim json_LBound2D As Long
    Dim json_UBound2D As Long
    Dim json_IsFirstItem2D As Boolean
    Dim json_Key As Variant
    Dim json_Value As Variant
    Dim json_DateStr As String
    Dim json_Converted As String
    Dim json_SkipItem As Boolean
    Dim json_PrettyPrint As Boolean
    Dim json_Indentation As String
    Dim json_InnerIndentation As String

    json_LBound = -1
    json_UBound = -1
    json_IsFirstItem = True
    json_LBound2D = -1
    json_UBound2D = -1
    json_IsFirstItem2D = True
    json_PrettyPrint = Not IsMissing(Whitespace)

    Select Case VBA.VarType(JsonValue)
    Case VBA.vbNull
        ConvertToJson = "null"
    Case VBA.vbDate
        ' Date
        json_DateStr = ConvertToIso(VBA.CDate(JsonValue))

        ConvertToJson = """" & json_DateStr & """"
    Case VBA.vbString
        ' String (or large number encoded as string)
        If Not JsonOptions.UseDoubleForLargeNumbers And json_StringIsLargeNumber(JsonValue) Then
            ConvertToJson = JsonValue
        Else
            ConvertToJson = """" & json_Encode(JsonValue) & """"
        End If
    Case VBA.vbBoolean
        If JsonValue Then
            ConvertToJson = "true"
        Else
            ConvertToJson = "false"
        End If
    Case VBA.vbArray To VBA.vbArray + VBA.vbByte
        If json_PrettyPrint Then
            If VBA.VarType(Whitespace) = VBA.vbString Then
                json_Indentation = VBA.String$(json_CurrentIndentation + 1, Whitespace)
                json_InnerIndentation = VBA.String$(json_CurrentIndentation + 2, Whitespace)
            Else
                json_Indentation = VBA.space$((json_CurrentIndentation + 1) * Whitespace)
                json_InnerIndentation = VBA.space$((json_CurrentIndentation + 2) * Whitespace)
            End If
        End If

        ' Array
        json_BufferAppend json_Buffer, "[", json_BufferPosition, json_BufferLength

        On Error Resume Next

        json_LBound = LBound(JsonValue, 1)
        json_UBound = UBound(JsonValue, 1)
        json_LBound2D = LBound(JsonValue, 2)
        json_UBound2D = UBound(JsonValue, 2)

        If json_LBound >= 0 And json_UBound >= 0 Then
            For json_Index = json_LBound To json_UBound
                If json_IsFirstItem Then
                    json_IsFirstItem = False
                Else
                    ' Append comma to previous line
                    json_BufferAppend json_Buffer, ",", json_BufferPosition, json_BufferLength
                End If

                If json_LBound2D >= 0 And json_UBound2D >= 0 Then
                    ' 2D Array
                    If json_PrettyPrint Then
                        json_BufferAppend json_Buffer, vbNewLine, json_BufferPosition, json_BufferLength
                    End If
                    json_BufferAppend json_Buffer, json_Indentation & "[", json_BufferPosition, json_BufferLength

                    For json_Index2D = json_LBound2D To json_UBound2D
                        If json_IsFirstItem2D Then
                            json_IsFirstItem2D = False
                        Else
                            json_BufferAppend json_Buffer, ",", json_BufferPosition, json_BufferLength
                        End If

                        json_Converted = ConvertToJson(JsonValue(json_Index, json_Index2D), Whitespace, json_CurrentIndentation + 2)

                        ' For Arrays/Collections, undefined (Empty/Nothing) is treated as null
                        If json_Converted = "" Then
                            ' (nest to only check if converted = "")
                            If json_IsUndefined(JsonValue(json_Index, json_Index2D)) Then
                                json_Converted = "null"
                            End If
                        End If

                        If json_PrettyPrint Then
                            json_Converted = vbNewLine & json_InnerIndentation & json_Converted
                        End If

                        json_BufferAppend json_Buffer, json_Converted, json_BufferPosition, json_BufferLength
                    Next json_Index2D

                    If json_PrettyPrint Then
                        json_BufferAppend json_Buffer, vbNewLine, json_BufferPosition, json_BufferLength
                    End If

                    json_BufferAppend json_Buffer, json_Indentation & "]", json_BufferPosition, json_BufferLength
                    json_IsFirstItem2D = True
                Else
                    ' 1D Array
                    json_Converted = ConvertToJson(JsonValue(json_Index), Whitespace, json_CurrentIndentation + 1)

                    ' For Arrays/Collections, undefined (Empty/Nothing) is treated as null
                    If json_Converted = "" Then
                        ' (nest to only check if converted = "")
                        If json_IsUndefined(JsonValue(json_Index)) Then
                            json_Converted = "null"
                        End If
                    End If

                    If json_PrettyPrint Then
                        json_Converted = vbNewLine & json_Indentation & json_Converted
                    End If

                    json_BufferAppend json_Buffer, json_Converted, json_BufferPosition, json_BufferLength
                End If
            Next json_Index
        End If

        On Error GoTo 0

        If json_PrettyPrint Then
            json_BufferAppend json_Buffer, vbNewLine, json_BufferPosition, json_BufferLength

            If VBA.VarType(Whitespace) = VBA.vbString Then
                json_Indentation = VBA.String$(json_CurrentIndentation, Whitespace)
            Else
                json_Indentation = VBA.space$(json_CurrentIndentation * Whitespace)
            End If
        End If

        json_BufferAppend json_Buffer, json_Indentation & "]", json_BufferPosition, json_BufferLength

        ConvertToJson = json_BufferToString(json_Buffer, json_BufferPosition)

    ' Dictionary or Collection
    Case VBA.vbObject
        If json_PrettyPrint Then
            If VBA.VarType(Whitespace) = VBA.vbString Then
                json_Indentation = VBA.String$(json_CurrentIndentation + 1, Whitespace)
            Else
                json_Indentation = VBA.space$((json_CurrentIndentation + 1) * Whitespace)
            End If
        End If

        ' Dictionary
        If VBA.typsName(JsonValue) = "Dictionary" Then
            json_BufferAppend json_Buffer, "{", json_BufferPosition, json_BufferLength
            For Each json_Key In JsonValue.keys
                ' For Objects, undefined (Empty/Nothing) is not added to object
                json_Converted = ConvertToJson(JsonValue(json_Key), Whitespace, json_CurrentIndentation + 1)
                If json_Converted = "" Then
                    json_SkipItem = json_IsUndefined(JsonValue(json_Key))
                Else
                    json_SkipItem = False
                End If

                If Not json_SkipItem Then
                    If json_IsFirstItem Then
                        json_IsFirstItem = False
                    Else
                        json_BufferAppend json_Buffer, ",", json_BufferPosition, json_BufferLength
                    End If

                    If json_PrettyPrint Then
                        json_Converted = vbNewLine & json_Indentation & """" & json_Key & """: " & json_Converted
                    Else
                        json_Converted = """" & json_Key & """:" & json_Converted
                    End If

                    json_BufferAppend json_Buffer, json_Converted, json_BufferPosition, json_BufferLength
                End If
            Next json_Key

            If json_PrettyPrint Then
                json_BufferAppend json_Buffer, vbNewLine, json_BufferPosition, json_BufferLength

                If VBA.VarType(Whitespace) = VBA.vbString Then
                    json_Indentation = VBA.String$(json_CurrentIndentation, Whitespace)
                Else
                    json_Indentation = VBA.space$(json_CurrentIndentation * Whitespace)
                End If
            End If

            json_BufferAppend json_Buffer, json_Indentation & "}", json_BufferPosition, json_BufferLength

        ' Collection
        ElseIf VBA.typsName(JsonValue) = "Collection" Then
            json_BufferAppend json_Buffer, "[", json_BufferPosition, json_BufferLength
            For Each json_Value In JsonValue
                If json_IsFirstItem Then
                    json_IsFirstItem = False
                Else
                    json_BufferAppend json_Buffer, ",", json_BufferPosition, json_BufferLength
                End If

                json_Converted = ConvertToJson(json_Value, Whitespace, json_CurrentIndentation + 1)

                ' For Arrays/Collections, undefined (Empty/Nothing) is treated as null
                If json_Converted = "" Then
                    ' (nest to only check if converted = "")
                    If json_IsUndefined(json_Value) Then
                        json_Converted = "null"
                    End If
                End If

                If json_PrettyPrint Then
                    json_Converted = vbNewLine & json_Indentation & json_Converted
                End If

                json_BufferAppend json_Buffer, json_Converted, json_BufferPosition, json_BufferLength
            Next json_Value

            If json_PrettyPrint Then
                json_BufferAppend json_Buffer, vbNewLine, json_BufferPosition, json_BufferLength

                If VBA.VarType(Whitespace) = VBA.vbString Then
                    json_Indentation = VBA.String$(json_CurrentIndentation, Whitespace)
                Else
                    json_Indentation = VBA.space$(json_CurrentIndentation * Whitespace)
                End If
            End If

            json_BufferAppend json_Buffer, json_Indentation & "]", json_BufferPosition, json_BufferLength
        End If

        ConvertToJson = json_BufferToString(json_Buffer, json_BufferPosition)
    Case VBA.vbInteger, VBA.vbLong, VBA.vbSingle, VBA.vbDouble, VBA.vbCurrency, VBA.vbDecimal
        ' Number (use decimals for numbers)
        ConvertToJson = VBA.Replace(JsonValue, ",", ".")
    Case Else
        ' vbEmpty, vbError, vbDataObject, vbByte, vbUserDefinedType
        ' Use VBA's built-in to-string
        On Error Resume Next
        ConvertToJson = JsonValue
        On Error GoTo 0
    End Select
End Function

' ============================================= '
' Private Functions
' ============================================= '

Private Function json_ParseObject(json_String As String, ByRef json_Index As Long) As Dictionary
    Dim json_Key As String
    Dim json_NextChar As String
    Static json_ParseObjectPos As Integer
    Set json_ParseObject = New Dictionary
    
    json_ParseObjectPos = json_ParseObjectPos + 1
    json_ParseObject.LabelPos = json_ParseObjectPos
    json_SkipSpaces json_String, json_Index
    If VBA.Mid$(json_String, json_Index, 1) <> "{" Then
        MsgBox "不知為何 error line 10bbbb"
        err.Raise 10001, "JSONConverter", json_ParseErrorMessage(json_String, json_Index, "Expecting '{'")
    Else
        json_Index = json_Index + 1

        Do
            json_SkipSpaces json_String, json_Index
            If VBA.Mid$(json_String, json_Index, 1) = "}" Then
                json_Index = json_Index + 1
                Exit Function
            ElseIf VBA.Mid$(json_String, json_Index, 1) = "," Then
                json_Index = json_Index + 1
                json_SkipSpaces json_String, json_Index
            End If

            json_Key = json_ParseKey(json_String, json_Index)
            json_NextChar = json_Peek(json_String, json_Index)
            If json_NextChar = "[" Or json_NextChar = "{" Then
                Set json_ParseObject.item(json_Key) = json_ParseValue(json_String, json_Index)
            Else
                json_ParseObject.item(json_Key) = json_ParseValue(json_String, json_Index)
            End If
        Loop
    End If
End Function

Private Function json_ParseArray(json_String As String, ByRef json_Index As Long) As Collection
    Set json_ParseArray = New Collection

    json_SkipSpaces json_String, json_Index
    If VBA.Mid$(json_String, json_Index, 1) <> "[" Then
        MsgBox "不知為何 error line 10cccc"
        err.Raise 10001, "JSONConverter", json_ParseErrorMessage(json_String, json_Index, "Expecting '['")
    Else
        json_Index = json_Index + 1

        Do
            json_SkipSpaces json_String, json_Index
            If VBA.Mid$(json_String, json_Index, 1) = "]" Then
                json_Index = json_Index + 1
                Exit Function
            ElseIf VBA.Mid$(json_String, json_Index, 1) = "," Then
                json_Index = json_Index + 1
                json_SkipSpaces json_String, json_Index
            End If

            json_ParseArray.Add json_ParseValue(json_String, json_Index)
        Loop
    End If
End Function

Private Function json_ParseValue(json_String As String, ByRef json_Index As Long) As Variant
    json_SkipSpaces json_String, json_Index
    Select Case VBA.Mid$(json_String, json_Index, 1)
    Case "{"
        Set json_ParseValue = json_ParseObject(json_String, json_Index)
    Case "["
        Set json_ParseValue = json_ParseArray(json_String, json_Index)
    Case """", "'"
        json_ParseValue = json_ParseString(json_String, json_Index)
    Case Else
        If VBA.Mid$(json_String, json_Index, 4) = "true" Then
            json_ParseValue = True
            json_Index = json_Index + 4
        ElseIf VBA.Mid$(json_String, json_Index, 5) = "false" Then
            json_ParseValue = False
            json_Index = json_Index + 5
        ElseIf VBA.Mid$(json_String, json_Index, 4) = "null" Then
            json_ParseValue = Null
            json_Index = json_Index + 4
        ElseIf VBA.instr("+-0123456789", VBA.Mid$(json_String, json_Index, 1)) Then
            json_ParseValue = json_ParseNumber(json_String, json_Index)
        Else
            MsgBox "不知為何 error line 3322"
            err.Raise 10001, "JSONConverter", json_ParseErrorMessage(json_String, json_Index, "Expecting 'STRING', 'NUMBER', null, true, false, '{', or '['")
        End If
    End Select
End Function

Private Function json_ParseString(json_String As String, ByRef json_Index As Long) As String
    Dim json_Quote As String
    Dim json_Char As String
    Dim json_Code As String
    Dim json_Buffer As String
    Dim json_BufferPosition As Long
    Dim json_BufferLength As Long

    json_SkipSpaces json_String, json_Index

    ' Store opening quote to look for matching closing quote
    json_Quote = VBA.Mid$(json_String, json_Index, 1)
    json_Index = json_Index + 1

    Do While json_Index > 0 And json_Index <= Len(json_String)
        json_Char = VBA.Mid$(json_String, json_Index, 1)

        Select Case json_Char
        Case "\"
            ' Escaped string, \\, or \/
            json_Index = json_Index + 1
            json_Char = VBA.Mid$(json_String, json_Index, 1)

            Select Case json_Char
            Case """", "\", "/", "'"
                json_BufferAppend json_Buffer, json_Char, json_BufferPosition, json_BufferLength
                json_Index = json_Index + 1
            Case "b"
                json_BufferAppend json_Buffer, vbBack, json_BufferPosition, json_BufferLength
                json_Index = json_Index + 1
            Case "f"
                json_BufferAppend json_Buffer, vbFormFeed, json_BufferPosition, json_BufferLength
                json_Index = json_Index + 1
            Case "n"
                json_BufferAppend json_Buffer, vbCrLf, json_BufferPosition, json_BufferLength
                json_Index = json_Index + 1
            Case "r"
                json_BufferAppend json_Buffer, vbCr, json_BufferPosition, json_BufferLength
                json_Index = json_Index + 1
            Case "t"
                json_BufferAppend json_Buffer, vbTab, json_BufferPosition, json_BufferLength
                json_Index = json_Index + 1
            Case "u"
                ' Unicode character escape (e.g. \u00a9 = Copyright)
                json_Index = json_Index + 1
                json_Code = VBA.Mid$(json_String, json_Index, 4)
                json_BufferAppend json_Buffer, VBA.ChrW(VBA.val("&h" + json_Code)), json_BufferPosition, json_BufferLength
                json_Index = json_Index + 4
            End Select
        Case json_Quote
            json_ParseString = json_BufferToString(json_Buffer, json_BufferPosition)
            json_Index = json_Index + 1
            Exit Function
        Case Else
            json_BufferAppend json_Buffer, json_Char, json_BufferPosition, json_BufferLength
            json_Index = json_Index + 1
        End Select
    Loop
End Function

Private Function json_ParseNumber(json_String As String, ByRef json_Index As Long) As Variant
    Dim json_Char As String
    Dim json_Value As String
    Dim json_IsLargeNumber As Boolean

    json_SkipSpaces json_String, json_Index

    Do While json_Index > 0 And json_Index <= Len(json_String)
        json_Char = VBA.Mid$(json_String, json_Index, 1)

        If VBA.instr("+-0123456789.eE", json_Char) Then
            ' Unlikely to have massive number, so use simple append rather than buffer here
            json_Value = json_Value & json_Char
            json_Index = json_Index + 1
        Else
            ' Excel only stores 15 significant digits, so any numbers larger than that are truncated
            ' This can lead to issues when BIGINT's are used (e.g. for Ids or Credit Cards), as they will be invalid above 15 digits
            ' See: http:''support.microsoft.com/kb/269370
            '
            ' Fix: Parse -> String, Convert -> String longer than 15/16 characters containing only numbers and decimal points -> Number
            ' (decimal doesn't factor into significant digit count, so if present check for 15 digits + decimal = 16)
            json_IsLargeNumber = IIf(InStr(json_Value, "."), Len(json_Value) >= 17, Len(json_Value) >= 16)
            If Not JsonOptions.UseDoubleForLargeNumbers And json_IsLargeNumber Then
                json_ParseNumber = json_Value
            Else
                ' VBA.Val does not use regional settings, so guard for comma is not needed
                json_ParseNumber = VBA.val(json_Value)
            End If
            Exit Function
        End If
    Loop
End Function

Private Function json_ParseKey(json_String As String, ByRef json_Index As Long) As String
    ' Parse key with single or double quotes
    If VBA.Mid$(json_String, json_Index, 1) = """" Or VBA.Mid$(json_String, json_Index, 1) = "'" Then
        json_ParseKey = json_ParseString(json_String, json_Index)
    ElseIf JsonOptions.AllowUnquotedKeys Then
        Dim json_Char As String
        Do While json_Index > 0 And json_Index <= Len(json_String)
            json_Char = VBA.Mid$(json_String, json_Index, 1)
            If (json_Char <> " ") And (json_Char <> ":") Then
                json_ParseKey = json_ParseKey & json_Char
                json_Index = json_Index + 1
            Else
                Exit Do
            End If
        Loop
    Else
        MsgBox "不知為何 error line 4444"
        err.Raise 10001, "JSONConverter", json_ParseErrorMessage(json_String, json_Index, "Expecting '""' or '''")
    End If

    ' Check for colon and skip if present or throw if not present
    json_SkipSpaces json_String, json_Index
    If VBA.Mid$(json_String, json_Index, 1) <> ":" Then
        MsgBox "不知為何 error line 5555"
        err.Raise 10001, "JSONConverter", json_ParseErrorMessage(json_String, json_Index, "Expecting ':'")
    Else
        json_Index = json_Index + 1
    End If
End Function

Private Function json_IsUndefined(ByVal json_Value As Variant) As Boolean
    ' Empty / Nothing -> undefined
    Select Case VBA.VarType(json_Value)
    Case VBA.vbEmpty
        json_IsUndefined = True
    Case VBA.vbObject
        Select Case VBA.typsName(json_Value)
        Case "Empty", "Nothing"
            json_IsUndefined = True
        End Select
    End Select
End Function

Private Function json_Encode(ByVal json_Text As Variant) As String
    ' Reference: http:''www.ietf.org/rfc/rfc4627.txt
    ' Escape: ", \, /, backspace, form feed, line feed, carriage return, tab
    Dim json_Index As Long
    Dim json_Char As String
    Dim json_AscCode As Long
    Dim json_Buffer As String
    Dim json_BufferPosition As Long
    Dim json_BufferLength As Long

    For json_Index = 1 To VBA.Len(json_Text)
        json_Char = VBA.Mid$(json_Text, json_Index, 1)
        json_AscCode = VBA.AscW(json_Char)

        ' When AscW returns a negative number, it returns the twos complement form of that number.
        ' To convert the twos complement notation into normal binary notation, add 0xFFF to the return result.
        ' https:''support.microsoft.com/en-us/kb/272138
        If json_AscCode < 0 Then
            json_AscCode = json_AscCode + 65536
        End If

        ' From spec, ", \, and control characters must be escaped (solidus is optional)

        Select Case json_AscCode
        Case 34
            ' " -> 34 -> \"
            json_Char = "\"""
        Case 92
            ' \ -> 92 -> \\
            json_Char = "\\"
        Case 47
            ' / -> 47 -> \/ (optional)
            If JsonOptions.EscapeSolidus Then
                json_Char = "\/"
            End If
        Case 8
            ' backspace -> 8 -> \b
            json_Char = "\b"
        Case 12
            ' form feed -> 12 -> \f
            json_Char = "\f"
        Case 10
            ' line feed -> 10 -> \n
            json_Char = "\n"
        Case 13
            ' carriage return -> 13 -> \r
            json_Char = "\r"
        Case 9
            ' tab -> 9 -> \t
            json_Char = "\t"
        Case 0 To 31, 127 To 65535
            ' Non-ascii characters -> convert to 4-digit hex
            json_Char = "\u" & VBA.right$("0000" & VBA.Hex$(json_AscCode), 4)
        End Select

        json_BufferAppend json_Buffer, json_Char, json_BufferPosition, json_BufferLength
    Next json_Index

    json_Encode = json_BufferToString(json_Buffer, json_BufferPosition)
End Function

Private Function json_Peek(json_String As String, ByVal json_Index As Long, Optional json_NumberOfCharacters As Long = 1) As String
    ' "Peek" at the next number of characters without incrementing json_Index (ByVal instead of ByRef)
    json_SkipSpaces json_String, json_Index
    json_Peek = VBA.Mid$(json_String, json_Index, json_NumberOfCharacters)
End Function

Private Sub json_SkipSpaces(json_String As String, ByRef json_Index As Long)
    ' Increment index to skip over spaces
    Do While json_Index > 0 And json_Index <= VBA.Len(json_String) And VBA.Mid$(json_String, json_Index, 1) = " "
        json_Index = json_Index + 1
    Loop
End Sub

Private Function json_StringIsLargeNumber(json_String As Variant) As Boolean
    ' Check if the given string is considered a "large number"
    ' (See json_ParseNumber)

    Dim json_Length As Long
    Dim json_CharIndex As Long
    json_Length = VBA.Len(json_String)

    ' Length with be at least 16 characters and assume will be less than 100 characters
    If json_Length >= 16 And json_Length <= 100 Then
        Dim json_CharCode As String

        json_StringIsLargeNumber = True

        For json_CharIndex = 1 To json_Length
            json_CharCode = VBA.Asc(VBA.Mid$(json_String, json_CharIndex, 1))
            Select Case json_CharCode
            ' Look for .|0-9|E|e
            Case 46, 48 To 57, 69, 101
                ' Continue through characters
            Case Else
                json_StringIsLargeNumber = False
                Exit Function
            End Select
        Next json_CharIndex
    End If
End Function

Private Function json_ParseErrorMessage(json_String As String, ByRef json_Index As Long, ErrorMessage As String)
    ' Provide detailed parse error message, including details of where and what occurred
    '
    ' Example:
    ' Error parsing JSON:
    ' {"abcde":True}
    '          ^
    ' Expecting 'STRING', 'NUMBER', null, true, false, '{', or '['

    Dim json_StartIndex As Long
    Dim json_StopIndex As Long

    ' Include 10 characters before and after error (if possible)
    json_StartIndex = json_Index - 10
    json_StopIndex = json_Index + 10
    If json_StartIndex <= 0 Then
        json_StartIndex = 1
    End If
    If json_StopIndex > VBA.Len(json_String) Then
        json_StopIndex = VBA.Len(json_String)
    End If

    json_ParseErrorMessage = "Error parsing JSON:" & VBA.vbNewLine & _
                             VBA.Mid$(json_String, json_StartIndex, json_StopIndex - json_StartIndex + 1) & VBA.vbNewLine & _
                             VBA.space$(json_Index - json_StartIndex) & "^" & VBA.vbNewLine & _
                             ErrorMessage
End Function

Private Sub json_BufferAppend(ByRef json_Buffer As String, _
                              ByRef json_Append As Variant, _
                              ByRef json_BufferPosition As Long, _
                              ByRef json_BufferLength As Long)
    ' VBA can be slow to append strings due to allocating a new string for each append
    ' Instead of using the traditional append, allocate a large empty string and then copy string at append position
    '
    ' Example:
    ' Buffer: "abc  "
    ' Append: "def"
    ' Buffer Position: 3
    ' Buffer Length: 5
    '
    ' Buffer position + Append length > Buffer length -> Append chunk of blank space to buffer
    ' Buffer: "abc       "
    ' Buffer Length: 10
    '
    ' Put "def" into buffer at position 3 (0-based)
    ' Buffer: "abcdef    "
    '
    ' Approach based on cStringBuilder from vbAccelerator
    ' http:''www.vbaccelerator.com/home/VB/Code/Techniques/RunTime_Debug_Tracing/VB6_Tracer_Utility_zip_cStringBuilder_cls.asp
    '
    ' and clsStringAppend from Philip Swannell
    ' https:''github.com/VBA-tools/VBA-JSON/pull/82

    Dim json_AppendLength As Long
    Dim json_LengthPlusPosition As Long

    json_AppendLength = VBA.Len(json_Append)
    json_LengthPlusPosition = json_AppendLength + json_BufferPosition

    If json_LengthPlusPosition > json_BufferLength Then
        ' Appending would overflow buffer, add chunk
        ' (double buffer length or append length, whichever is bigger)
        Dim json_AddedLength As Long
        json_AddedLength = IIf(json_AppendLength > json_BufferLength, json_AppendLength, json_BufferLength)

        json_Buffer = json_Buffer & VBA.space$(json_AddedLength)
        json_BufferLength = json_BufferLength + json_AddedLength
    End If

    ' Note: Namespacing with VBA.Mid$ doesn't work properly here, throwing compile error:
    ' Function call on left-hand side of assignment must return Variant or Object
    Mid$(json_Buffer, json_BufferPosition + 1, json_AppendLength) = CStr(json_Append)
    json_BufferPosition = json_BufferPosition + json_AppendLength
End Sub

Private Function json_BufferToString(ByRef json_Buffer As String, ByVal json_BufferPosition As Long) As String
    If json_BufferPosition > 0 Then
        json_BufferToString = VBA.left$(json_Buffer, json_BufferPosition)
    End If
End Function

''
' VBA-UTC v1.0.6
' (c) Tim Hall - https:''github.com/VBA-tools/VBA-UtcConverter
'
' UTC/ISO 8601 Converter for VBA
'
' Errors:
' 10011 - UTC parsing error
' 10012 - UTC conversion error
' 10013 - ISO 8601 parsing error
' 10014 - ISO 8601 conversion error
'
' @module UtcConverter
' @author tim.hall.engr@gmail.com
' @license MIT (http:''www.opensource.org/licenses/mit-license.php)
'' ~~~~~~~~~~~~~~~~~~~~~~~~~~~~~~~~~~~~~~~~~~~~~~~~~~~~~~~~~~~~~~~~~~~~~~ '

' (Declarations moved to top)

' ============================================= '
' Public Methods
' ============================================= '

''
' Parse UTC date to local date
'
' @method ParseUtc
' @param {Date} UtcDate
' @return {Date} Local date
' @throws 10011 - UTC parsing error
''
Public Function ParseUtc(utc_UtcDate As Date) As Date
    On Error GoTo utc_ErrorHandling

#If Mac Then
    ParseUtc = utc_ConvertDate(utc_UtcDate)
#Else
    Dim utc_TimeZoneInfo As utc_TIME_ZONE_INFORMATION
    Dim utc_LocalDate As utc_SYSTEMTIME

    utc_GetTimeZoneInformation utc_TimeZoneInfo
    utc_SystemTimeToTzSpecificLocalTime utc_TimeZoneInfo, utc_DateToSystemTime(utc_UtcDate), utc_LocalDate

    ParseUtc = utc_SystemTimeToDate(utc_LocalDate)
#End If

    Exit Function

utc_ErrorHandling:
    MsgBox "不知為何 error line 6666"
    err.Raise 10011, "UtcConverter.ParseUtc", "UTC parsing error: " & err.Number & " - " & err.Description
End Function

''
' Convert local date to UTC date
'
' @method ConvertToUrc
' @param {Date} utc_LocalDate
' @return {Date} UTC date
' @throws 10012 - UTC conversion error
''
Public Function ConvertToUtc(utc_LocalDate As Date) As Date
    On Error GoTo utc_ErrorHandling

#If Mac Then
    ConvertToUtc = utc_ConvertDate(utc_LocalDate, utc_ConvertToUtc:=True)
#Else
    Dim utc_TimeZoneInfo As utc_TIME_ZONE_INFORMATION
    Dim utc_UtcDate As utc_SYSTEMTIME

    utc_GetTimeZoneInformation utc_TimeZoneInfo
    utc_TzSpecificLocalTimeToSystemTime utc_TimeZoneInfo, utc_DateToSystemTime(utc_LocalDate), utc_UtcDate

    ConvertToUtc = utc_SystemTimeToDate(utc_UtcDate)
#End If

    Exit Function

utc_ErrorHandling:
    MsgBox "不知為何 error line 7777"
    err.Raise 10012, "UtcConverter.ConvertToUtc", "UTC conversion error: " & err.Number & " - " & err.Description
End Function

''
' Parse ISO 8601 date string to local date
'
' @method ParseIso
' @param {Date} utc_IsoString
' @return {Date} Local date
' @throws 10013 - ISO 8601 parsing error
''
Public Function ParseIso(utc_IsoString As String) As Date
    On Error GoTo utc_ErrorHandling

    Dim utc_Parts() As String
    Dim utc_DateParts() As String
    Dim utc_TimeParts() As String
    Dim utc_OffsetIndex As Long
    Dim utc_HasOffset As Boolean
    Dim utc_NegativeOffset As Boolean
    Dim utc_OffsetParts() As String
    Dim utc_Offset As Date

    utc_Parts = VBA.Split(utc_IsoString, "T")
    utc_DateParts = VBA.Split(utc_Parts(0), "-")
    ParseIso = VBA.DateSerial(VBA.CInt(utc_DateParts(0)), VBA.CInt(utc_DateParts(1)), VBA.CInt(utc_DateParts(2)))

    If UBound(utc_Parts) > 0 Then
        If VBA.instr(utc_Parts(1), "Z") Then
            utc_TimeParts = VBA.Split(VBA.Replace(utc_Parts(1), "Z", ""), ":")
        Else
            utc_OffsetIndex = VBA.instr(1, utc_Parts(1), "+")
            If utc_OffsetIndex = 0 Then
                utc_NegativeOffset = True
                utc_OffsetIndex = VBA.instr(1, utc_Parts(1), "-")
            End If

            If utc_OffsetIndex > 0 Then
                utc_HasOffset = True
                utc_TimeParts = VBA.Split(VBA.left$(utc_Parts(1), utc_OffsetIndex - 1), ":")
                utc_OffsetParts = VBA.Split(VBA.right$(utc_Parts(1), Len(utc_Parts(1)) - utc_OffsetIndex), ":")

                Select Case UBound(utc_OffsetParts)
                Case 0
                    utc_Offset = TimeSerial(VBA.CInt(utc_OffsetParts(0)), 0, 0)
                Case 1
                    utc_Offset = TimeSerial(VBA.CInt(utc_OffsetParts(0)), VBA.CInt(utc_OffsetParts(1)), 0)
                Case 2
                    ' VBA.Val does not use regional settings, use for seconds to avoid decimal/comma issues
                    utc_Offset = TimeSerial(VBA.CInt(utc_OffsetParts(0)), VBA.CInt(utc_OffsetParts(1)), Int(VBA.val(utc_OffsetParts(2))))
                End Select

                If utc_NegativeOffset Then: utc_Offset = -utc_Offset
            Else
                utc_TimeParts = VBA.Split(utc_Parts(1), ":")
            End If
        End If

        Select Case UBound(utc_TimeParts)
        Case 0
            ParseIso = ParseIso + VBA.TimeSerial(VBA.CInt(utc_TimeParts(0)), 0, 0)
        Case 1
            ParseIso = ParseIso + VBA.TimeSerial(VBA.CInt(utc_TimeParts(0)), VBA.CInt(utc_TimeParts(1)), 0)
        Case 2
            ' VBA.Val does not use regional settings, use for seconds to avoid decimal/comma issues
            ParseIso = ParseIso + VBA.TimeSerial(VBA.CInt(utc_TimeParts(0)), VBA.CInt(utc_TimeParts(1)), Int(VBA.val(utc_TimeParts(2))))
        End Select

        ParseIso = ParseUtc(ParseIso)

        If utc_HasOffset Then
            ParseIso = ParseIso - utc_Offset
        End If
    End If

    Exit Function

utc_ErrorHandling:
    MsgBox "不知為何 error line 8888"
    err.Raise 10013, "UtcConverter.ParseIso", "ISO 8601 parsing error for " & utc_IsoString & ": " & err.Number & " - " & err.Description
End Function

''
' Convert local date to ISO 8601 string
'
' @method ConvertToIso
' @param {Date} utc_LocalDate
' @return {Date} ISO 8601 string
' @throws 10014 - ISO 8601 conversion error
''
Public Function ConvertToIso(utc_LocalDate As Date) As String
    On Error GoTo utc_ErrorHandling

    ConvertToIso = VBA.Format$(ConvertToUtc(utc_LocalDate), "yyyy-mm-ddTHH:mm:ss.000Z")

    Exit Function

utc_ErrorHandling:
    MsgBox "不知為何 error line 9999"
    err.Raise 10014, "UtcConverter.ConvertToIso", "ISO 8601 conversion error: " & err.Number & " - " & err.Description
End Function

' ============================================= '
' Private Functions
' ============================================= '

#If Mac Then

Private Function utc_ConvertDate(utc_Value As Date, Optional utc_ConvertToUtc As Boolean = False) As Date
    Dim utc_ShellCommand As String
    Dim utc_Result As utc_ShellResult
    Dim utc_Parts() As String
    Dim utc_DateParts() As String
    Dim utc_TimeParts() As String

    If utc_ConvertToUtc Then
        utc_ShellCommand = "date -ur `date -jf '%Y-%m-%d %H:%M:%S' " & _
            "'" & VBA.Format$(utc_Value, "yyyy-mm-dd HH:mm:ss") & "' " & _
            " +'%s'` +'%Y-%m-%d %H:%M:%S'"
    Else
        utc_ShellCommand = "date -jf '%Y-%m-%d %H:%M:%S %z' " & _
            "'" & VBA.Format$(utc_Value, "yyyy-mm-dd HH:mm:ss") & " +0000' " & _
            "+'%Y-%m-%d %H:%M:%S'"
    End If

    utc_Result = utc_ExecuteInShell(utc_ShellCommand)

    If utc_Result.utc_Output = "" Then
        MsgBox "不知為何 error line 10dddd"
        err.Raise 10015, "UtcConverter.utc_ConvertDate", "'date' command failed"
    Else
        utc_Parts = Split(utc_Result.utc_Output, " ")
        utc_DateParts = Split(utc_Parts(0), "-")
        utc_TimeParts = Split(utc_Parts(1), ":")

        utc_ConvertDate = DateSerial(utc_DateParts(0), utc_DateParts(1), utc_DateParts(2)) + _
            TimeSerial(utc_TimeParts(0), utc_TimeParts(1), utc_TimeParts(2))
    End If
End Function

Private Function utc_ExecuteInShell(utc_ShellCommand As String) As utc_ShellResult
#If VBA7 Then
    Dim utc_File As LongPtr
    Dim utc_Read As LongPtr
#Else
    Dim utc_File As Long
    Dim utc_Read As Long
#End If

    Dim utc_Chunk As String

    On Error GoTo utc_ErrorHandling
    utc_File = utc_popen(utc_ShellCommand, "r")

    If utc_File = 0 Then: Exit Function

    Do While utc_feof(utc_File) = 0
        utc_Chunk = VBA.space$(50)
        utc_Read = CLng(utc_fread(utc_Chunk, 1, Len(utc_Chunk) - 1, utc_File))
        If utc_Read > 0 Then
            utc_Chunk = VBA.left$(utc_Chunk, CLng(utc_Read))
            utc_ExecuteInShell.utc_Output = utc_ExecuteInShell.utc_Output & utc_Chunk
        End If
    Loop

utc_ErrorHandling:
    utc_ExecuteInShell.utc_ExitCode = CLng(utc_pclose(utc_File))
End Function

#Else

Private Function utc_DateToSystemTime(utc_Value As Date) As utc_SYSTEMTIME
    utc_DateToSystemTime.utc_wYear = VBA.Year(utc_Value)
    utc_DateToSystemTime.utc_wMonth = VBA.Month(utc_Value)
    utc_DateToSystemTime.utc_wDay = VBA.Day(utc_Value)
    utc_DateToSystemTime.utc_wHour = VBA.Hour(utc_Value)
    utc_DateToSystemTime.utc_wMinute = VBA.Minute(utc_Value)
    utc_DateToSystemTime.utc_wSecond = VBA.Second(utc_Value)
    utc_DateToSystemTime.utc_wMilliseconds = 0
End Function

Private Function utc_SystemTimeToDate(utc_Value As utc_SYSTEMTIME) As Date
    utc_SystemTimeToDate = DateSerial(utc_Value.utc_wYear, utc_Value.utc_wMonth, utc_Value.utc_wDay) + _
        TimeSerial(utc_Value.utc_wHour, utc_Value.utc_wMinute, utc_Value.utc_wSecond)
End Function

#End If

Attribute VB_Name = "LayoutModule"
Option Explicit


Function layout(abcTuneLines As TuneLineList, width As Double, space As Double) As Double
    Dim i As Integer
    Dim j As Integer
    
    Dim abcLine As TuneLine
    '' Adjust the x-coordinates to their absolute positions
    '' 將 x 坐標調整到其絕對位置
    Dim maxWidth  As Double
    maxWidth = width
    For i = 0 To abcTuneLines.Count - 1
        Set abcLine = abcTuneLines(i)
        If Not (abcLine.Staffs Is Nothing) Then
            debugVoices abcLine.staffGroup
            Call setXSpacing(New RendererModule, width, space, abcLine.staffGroup, New vFormatting, i = abcTuneLines.Count - 1, False)
            
            If (abcLine.staffGroup.w > maxWidth) Then
                maxWidth = abcLine.staffGroup.w
            End If
        End If
    Next
'
'    '' Layout the beams and add the stems to the beamed notes.
'    '' 佈局橫梁並將主幹添加到橫梁音符中。
'    For i = 0 To abctune.lines.clount - 1
'        Set abcLine = abctune.lines(i)
'        If Not (abcLine.StaffGroup Is Nothing) Then
'            If Not (abcLine.StaffGroup.voices Is Nothing) Then
'                For j = 0 To abcLine.StaffGroup.voices.Count
'                    layoutVoice (abcLine.StaffGroup.voices(j))
'                Next
'                setUpperAndLowerElements renderer, abcLine.StaffGroup
'            End If
'        End If
'    Next
'
'    '' Set the staff spacing
'    '' TODO-PER: we should have been able to do this by the time we called setUpperAndLowerElements, but for some reason the "bottom" element seems to be set as a side effect of setting the X spacing.
'    '' 設置五線譜間距
'    '' TODO-PER：當我們調用 setUpperAndLowerElements 時，我們應該能夠做到這一點，
'    ''但由於某種原因，“底部”元素似乎被設置為設置 X 間距的副作用。
'    For i = 0 To abctune.lines.Count - 1
'        Set abcLine = abctune.lines(i)
'        If Not (abcLine.StaffGroup Is Nothing) Then
'            abcLine.StaffGroup.setHeight
'        End If
'    Next
    layout = maxWidth
End Function
'/**
' * Do the x-axis positioning for a single line (a group of related staffs)
' * 對單線（一組相關人員）進行x軸定位
' */
Public Sub setXSpacing(renderer As RendererModule, width As Double, space As Double, staffGroup As StaffGroupElement, formatting As vFormatting, isLastLine As Boolean, isDebug As Boolean)
    Dim leftEdge As Double
    Dim newspace As Double
    Dim lastSpace As Double
    'leftEdge = getLeftEdgeOfStaff(renderer, StaffGroup.getTextSize, StaffGroup.voices, StaffGroup.brace, StaffGroup.bracket)
    leftEdge = 0
    newspace = space
    '' TODO-PER: shouldn't need multiple passes, but each pass gets it closer to the right spacing. (Only affects long lines: normal lines break out of this loop quickly.)
    '' TODO-PER：不需要多次通過，但每次通過都會使其更接近正確的間距。 （僅影響長行：普通行很快就會脫離此循環。）
    Dim it As Integer
    
    For it = 0 To 7
        Call layoutStaffGroup2(newspace, New RendererModule, isDebug, staffGroup, leftEdge)
        newspace = calcHorizontalSpacing(isLastLine, formatting.stretchLast, width - G.LeftSpace - G.RightSpace, staffGroup.w, newspace, staffGroup.spacingUnits, staffGroup.minSpace, G.LeftSpace + G.RightSpace) ', renderer.padding.left + renderer.padding.right)
        If Round(newspace, 3) <> Round(lastSpace, 3) Then
            lastSpace = newspace
        Else
            Exit For
        End If
'        If (isDebug) Then
'            console.log("setXSpace", it, staffGroup.w, newspace, staffGroup.minspace)
'        End If
        If (newspace = 0) Then
            Exit For
        End If
    Next
    '把休止符方置中
    ''centerWholeRests StaffGroup.voices
End Sub

Function calcHorizontalSpacing(isLastLine As Boolean, stretchLast As Double, targetWidth As Double, lineWidth As Double, spacing As Double, spacingUnits As Double, minSpace As Double, padding As Double) As Double
    If (isLastLine) Then
        If (stretchLast) Then
            If (lineWidth / targetWidth < 0.66) Then
                calcHorizontalSpacing = 0 '' keep this for backward compatibility. The break isn't quite the same for some reason.
            End If
         Else
            '' "Stretch the last music line of a tune when it lacks less than the float fraction of the page width."
            Dim lack As Double
            Dim stretch As Boolean
            lack = 1 - (lineWidth + padding) / targetWidth
            stretch = lack < stretchLast
            If Not (stretch) Then calcHorizontalSpacing = 0 '' don't stretch last line too much
        End If
    End If
    If (Abs(targetWidth - lineWidth) < 0.01) Then calcHorizontalSpacing = 0 '' if we are already near the target width, we're done.
    Dim relSpace As Double
    Dim constSpace As Double
    relSpace = spacingUnits * spacing
    constSpace = lineWidth - relSpace
    If (spacingUnits > 0) Then
        spacing = (targetWidth - constSpace) / spacingUnits
        If (spacing * minSpace > 50) Then
            spacing = 50 / minSpace
        End If
        calcHorizontalSpacing = spacing
        Exit Function
    End If
    calcHorizontalSpacing = 0
End Function
'/**
' * 休止符置中
' * 整個休止符是一種特殊情況：如果它們在一個小節中單獨存在，那麼它們應該居中。
' * (如果它們不是單獨存在，則可能是用戶錯誤，但我們將其置於兩側的兩個項目之間的中心。）
' * whole rests are a special case: if they are by themselves in a measure, then they should be centered.
' * (If they are not by themselves, that is probably a user error, but we'll just center it between the two items to either side of it.)
' */
Public Sub centerWholeRests(voices As VoiceElementList)
    '' whole rests are a special case: if they are by themselves in a measure, then they should be centered.
    '' (If they are not by themselves, that is probably a user error, but we'll just center it between the two items to either side of it.)
    Dim i As Integer, j As Integer
    Dim voice As VoiceElement
    Dim abselem As VoiceElement
    Dim befor As VoiceElement
    Dim after As VoiceElement
    For i = 0 To voices.Count - 1
        Set voice = voices(i)
        '' Look through all of the elements except for the first and last. If the whole note appears there then there isn't anything to center it between anyway.
        For j = 1 To voice.children.Count - 1
            Set abselem = voice.children(j)
            If Not (abselem.abcelem.rest Is Nothing) Then
                If (abselem.abcelem.rest.typs = "whole" Or abselem.abcelem.rest.typs = "multimeasure") Then
                Set before = voice.children(j - 1)
                Set after = voice.children(j + 1)
                abselem.center before, after
                End If
            End If
        Next
    Next
End Sub


'/** 找出每段樂器名最大的寬度  */
Function getLeftEdgeOfStaff(renderer As RendererModule, getTextSize As Double, voices As VoiceElementList, brace, bracket) As Double

    Dim x   As Double
    Dim voiceheaderw   As Double
    Dim size   As Double
    Dim sizeW As Double
    Dim ofs As Double
    Dim i   As Integer
    
    Dim x   As Double
    x = renderer.padding.left

    '' find out how much space will be taken up by voice headers
     voiceheaderw = 0
    Dim gTextSize As New getTextSize
    For i = 0 To voices.Length - 1
        If (voices(i).header Is Nothing) Then
            size = gTextSize.calc(voices(i).header, "voicefont", "")
            voiceheaderw = Math.max(voiceheaderw, size.width)
        End If
    Next
    voiceheaderw = addBraceSize(voiceheaderw, brace, getTextSize)
    voiceheaderw = addBraceSize(voiceheaderw, bracket, getTextSize)
    
    
    If (voiceheaderw > 0) Then
        '' Give enough spacing to the right - we use the width of an A for the amount of spacing.
        '' 給右側足夠的間距 - 我們使用 A 的寬度作為間距量。
        '' 在加上 1 個字的寬度
        sizeW = gTextSize.calc("A", "voicefont", "")
        voiceheaderw = voiceheaderw + sizeW.width
    End If
    x = x + voiceheaderw

    ofs = 0
    ofs = setBraceLocation(brace, x, ofs)
    ofs = setBraceLocation(bracket, x, ofs)
    getLeftEdgeOfStaff = x + ofs

End Function

Function addBraceSize(voiceheaderw, brace, getTextSize) As Double
    Dim i As Integer
    Dim size As Double
    If Not (brace Is Nothing) Then
        For i = 0 To i < brace.Length - 1
            If Not (brace(i).header Is Nothing) Then
                 size = gTextSize.calc(brace(i).header, "voicefont", "")
                voiceheaderw = Math.max(voiceheaderw, size.width)
            End If
        Next
    End If
    addBraceSize = voiceheaderw

End Function

Function setBraceLocation(brace, x, ofs) As Double
    Dim i As Integer
    If Not (brace Is Nothing) Then
        For i = 0 To brace.Length - 1
            Call setLocation(x, brace(i))
            ofs = Math.max(ofs, brace(i).getWidth())
        Next
    End If
    setBraceLocation = ofs


End Function

Function setLocation(x, element)
    element.x = x
End Function

Attribute VB_Name = "Math"


'Math module by arfu
Option Explicit
#If Win64 Then
    #If VBA7 Then
        Public Const MAX_INTEGER As LongLong = 2 ^ 63 - 1
    #Else
        Public Const MAX_INTEGER As Long = 2 ^ 63 - 1
    #End If
#Else
    Public Const MAX_INTEGER As Long = 2 ^ 31 - 1
#End If
Public Const PI As Double = 3.14159265359
Public Const E As Double = 2.71828182846
Public Const PI2 As Double = 1.57079632679
Public Const TAU As Double = 6.28318530718
Public Const GRatio As Double = 1.61803398875

Public Function IsPrime(ByVal x As Long) As Boolean
    Dim c As Integer
    IsPrime = True
    For c = 2 To Abs(x) - 1
        If Abs(x) Mod c = 0 Then
            IsPrime = False
            Exit Function
        End If
    Next
    If x = 0 Then IsPrime = False
End Function


Public Function Odd(ByVal Number As Long) As Long
    Odd = Number * 2 + 1
End Function


Public Function isDivisible(ByVal Number#, Optional ByVal DividedBy# = 2) As Boolean
    isDivisible = Number Mod DividedBy = 0
End Function


Public Function Evaluate(ByVal String1 As String) As Double
    On Error Resume Next
    Dim Excel As Object: Set Excel = CreateObject("Excel.Application")
    Evaluate = Excel.Evaluate(String1)
End Function

    
Public Function Pow(ByVal x#, Optional ByVal y# = 2) As Double
    Pow = (x ^ y)
End Function

Public Function Sqrt(ByVal x#) As Double
    
    If x > 0 Then
        Sqrt = Sqr(x)
    Else
        Sqrt = x
    End If
End Function


Public Function root(ByVal x#, Optional ByVal y As Double = 2) As Double
    root = Abs(x) ^ (1 / y)
End Function


Public Function RandomNum(Optional ByVal Minimum As Single, Optional ByVal Maximum As Single = 1, Optional ByVal Float As Integer, Optional RandomizeNumber As Variant) As Single
    If IsMissing(RandomizeNumber) Then
        Randomize
    Else
        Randomize RandomizeNumber
    End If
    RandomNum = Round((Maximum - Minimum) * Rnd + Minimum, Float)
End Function


Public Function Ceil(ByVal x#) As Long
    Ceil = IIf(Round(x, 0) >= x, Round(x, 0), Round(x, 0) + 1)
End Function


Public Function Trunc(ByVal x#) As Long
    Trunc = IIf(x > 0, Int(x), -Int(-x))
End Function


Public Function Floor(ByVal x#) As Long
    Floor = IIf(Round(x, 0) <= x, Round(x, 0), Round(x, 0) - 1)
End Function


Public Function delta(ByVal a#, Optional ByVal B# = 0, Optional ByVal c# = 0) As Double
    delta = B ^ 2 - 4 * a * c
End Function


Public Function Bhask(ByVal a#, Optional ByVal B# = 0, Optional ByVal c# = 0)
    If delta(a, B, c) < 0 Then Exit Function
    Bhask = Array((-B + Sqr(delta(a, B, c))) / (2 * a), (-B - Sqr(delta(a, B, c))) / (2 * a))
End Function


Public Function min(ParamArray x() As Variant) As Double
    Dim i%
    If UBound(x) = 0 Then      '只有一個
        min = x(0)(0)
        For i = LBound(x(0)) To UBound(x(0))
            If i = 0 Or x(0)(i) < min Then min = x(0)(i)
        Next
    ElseIf UBound(x) > 0 Then  '兩個以上
        min = x(0)
        For i = 0 To UBound(x)
            If x(i) < min Then
                min = x(i)
            End If
        Next
    End If
End Function


Public Function max(ParamArray x() As Variant) As Double
    Dim i%
    If UBound(x) = 0 Then      '只有一個
        For i = LBound(x(0)) To UBound(x(0))
            If i = 0 Or x(0)(i) > max Then
                max = x(0)(i)
            End If
        Next
    ElseIf UBound(x) > 0 Then  '兩個以上
        For i = 0 To UBound(x)
            If x(i) > max Then
                max = x(i)
            End If
        Next
    End If
End Function


Public Function GCD(ByVal a As Long, ByVal B As Long) As Long
    Dim remainder As Long
    If a = 0 Or B = 0 Then Exit Function
    Do
      remainder = Abs(a) Mod Abs(B)
      a = Abs(B)
      B = remainder
    Loop Until remainder = 0
    GCD = a
End Function


Public Function LCM(ByVal a As Long, ByVal B As Long) As Long
    If a = 0 Or B = 0 Then Exit Function
    LCM = (Abs(a) * Abs(B)) \ GCD(a, B)
End Function


Public Function Fact(ByVal N As Long, Optional ByVal StepValue As Long = 1) As Long
    Fact = 1
    For N = N To 1 Step -Abs(StepValue)
        Fact = Fact * N
    Next
End Function


Public Function Fibonacci(ByVal N As Long) As Long
    If N <= 0 Then Exit Function
    Fibonacci = IIf(N = 1, 1, Fibonacci(N - 1) + Fibonacci(N - 2))
End Function


Public Function Mean(ParamArray x() As Variant) As Double
    Dim i%
    For i = LBound(x) To UBound(x)
        Mean = Mean + x(i)
    Next
    Mean = Mean / (UBound(x) + 1)
End Function


Public Function Median(ParamArray x() As Variant) As Double
    Median = x(0)
    If UBound(x) = 0 Then Exit Function
    Median = IIf(UBound(x) Mod 2, (x(UBound(x) \ 2) + x(UBound(x) \ 2 + 1)) / 2, x(UBound(x) \ 2))
End Function


Public Function Variance(ByVal N1#, ByVal n2#) As Double
    Variance = (Mean(N1, n2) - N1) ^ 2 + (Mean(N1, n2) - n2) ^ 2
End Function


'Public Function Mid(ByVal X1#, ByVal X2#) As Double
'    Mid = (X1 + X2) / 2
'End Function


Public Function FindA(ByVal x1#, ByVal x2#, ByVal y1#, ByVal y2#) As Double
    If x1 = x2 Then Exit Function
    FindA = (y1 - y2) / (x1 - x2)
End Function


Public Function Lerp(ByVal x1#, ByVal x2#, ByVal y1#, ByVal y2#, ByVal x#) As Double
    If x1 = x2 Then Exit Function
    Lerp = y1 + (x - x1) * (y2 - y1) / (x2 - x1)
End Function


Public Function LineLineIntersect(ByVal x1#, ByVal y1#, ByVal x2#, ByVal y2#, ByVal x3#, ByVal y3#, ByVal x4#, ByVal y4#)
    Dim x As Double, y As Double
    If (x1 - x2) * (y3 - y4) = (y1 - y2) * (x3 - x4) Then Exit Function
    x = ((x1 * y2 - y1 * x2) * (x3 - x4) - (x1 - x2) * (x3 * y4 - y3 * x4)) / ((x1 - x2) * (y3 - y4) - (y1 - y2) * (x3 - x4))
    y = ((x1 * y2 - y1 * x2) * (y3 - y4) - (y1 - y2) * (x3 * y4 - y3 * x4)) / ((x1 - x2) * (y3 - y4) - (y1 - y2) * (x3 - x4))
    LineLineIntersect = Array(x, y)
End Function


Public Function Distance(ByVal x1#, ByVal x2#, ByVal y1#, ByVal y2#, Optional ByVal Sqrt As Boolean = True) As Double
    Distance = IIf(Sqrt, Sqr((x2 - x1) ^ 2 + (y2 - y1) ^ 2), (x2 - x1) ^ 2 + (y2 - y1) ^ 2)
End Function


Public Function Distance2(ByVal x1#, ByVal x2#, ByVal y1#, ByVal y2#, ByVal Z1#, ByVal Z2#, Optional ByVal Sqrt As Boolean = True) As Double
    Distance2 = IIf(Sqrt, Sqr((x2 - x1) ^ 2 + (y2 - y1) ^ 2 + (Z2 - Z1) ^ 2), (x2 - x1) ^ 2 + (y2 - y1) ^ 2 + (Z2 - Z1) ^ 2)
End Function


Public Function Hypot(ByVal x#, ByVal y#) As Double
    Hypot = Sqr(x ^ 2 + y ^ 2)
End Function


Public Function LogN(ByVal x#, ByVal y#) As Double
    LogN = Log(x) / Log(y)
End Function


Public Function ATn2(ByVal x#, ByVal y#) As Double
    ATn2 = IIf(x > 0, Atn(y / x), IIf(x < 0, Atn(y / x) + PI * Sgn(y) + IIf(y = 0, PI, 0), PI / 2 * Sgn(y)))
End Function


Public Function Sec(ByVal x#) As Double
    Sec = 1 / Cos(x)
End Function


Public Function Cosec(ByVal x#) As Double
    Cosec = 1 / Sin(x)
End Function


Public Function Cotan(ByVal x#) As Double
    Cotan = 1 / Tan(x)
End Function


Public Function Radians(ByVal Degrees#) As Double
    Radians = Degrees * 180 / PI
End Function


Public Function Degrees(ByVal Radians#) As Double
    Radians = Radians * PI / 180
End Function


Public Function ASin(ByVal x#) As Double
    ASin = Atn(x / Sqr(-x * x + 1))
End Function


Public Function ACos(ByVal x#) As Double
    ACos = Atn(-x / Sqr(-x * x + 1)) + 2 * Atn(1)
End Function


Public Function ASec(ByVal x#) As Double
    ASec = Atn(x / Sqr(x * x - 1)) + Sgn((x) - 1) * (2 * Atn(1))
End Function


Public Function ACosec(ByVal x#) As Double
    ACosec = Atn(x / Sqr(x * x - 1)) + (Sgn(x) - 1) * (2 * Atn(1))
End Function


Public Function ACotan(ByVal x#) As Double
    ACotan = Atn(x) + 2 * Atn(1)
End Function


Public Function HSin(ByVal x#) As Double
    HSin = (exp(x) - exp(-x)) / 2
End Function


Public Function HCos(ByVal x#) As Double
    HCos = (exp(x) + exp(-x)) / 2
End Function


Public Function HTan(ByVal x#) As Double
    HTan = (exp(x) - exp(-x)) / (exp(x) + exp(-x))
End Function


Public Function HSec(ByVal x#) As Double
    HSec = 2 / (exp(x) + exp(-x))
End Function


Public Function HCosec(ByVal x#) As Double
    HCosec = 2 / (exp(x) - exp(-x))
End Function


Public Function HCotan(ByVal x#) As Double
    HCotan = (exp(x) + exp(-x)) / (exp(x) - exp(-x))
End Function


Public Function HASin(ByVal x#) As Double
    HASin = Log(x + Sqr(x * x + 1))
End Function


Public Function HACos(ByVal x#) As Double
    HACos = Log(x + Sqr(x * x - 1))
End Function


Public Function HATan(ByVal x#) As Double
    HATan = Log((1 + x) / (1 - x)) / 2
End Function


Public Function HASec(ByVal x#) As Double
    HASec = Log((Sqr(-x * x + 1) + 1) / x)
End Function


Public Function HACosec(ByVal x#) As Double
    HACosec = Log((Sgn(x) * Sqr(x * x + 1) + 1) / x)
End Function


Public Function HACotan(ByVal x#) As Double
    HACotan = Log((x + 1) / (x - 1)) / 2
End Function

Public Function LawCos(ByVal B As Double, ByVal c As Double, ByVal Angle As Double) As Double
    LawCos = B ^ 2 + c ^ 2 - 2 * c * Cos(Angle)
End Function


Function BitMoveLeft(ByRef v As Long, num As Long) As Long
'左移位元 , 需要注意乘2的時候是否會溢出:
    Dim i As Long
    Dim flag As Boolean '是否要把第32位轉換為1
    
    For i = 1 To num
        '判斷第31位是否=1
        If v >= &H40000000 Then
            flag = True
            '把第31位置換為 0
            v = v And &H3FFFFFFF
        Else
            flag = False
        End If
        
        v = v * 2
    Next
    
    If flag Then
        v = v Or &H80000000
    End If
    
    BitMoveLeft = v
End Function




Function BitMoveRight(ByRef B As Long, num As Long) As Long
'右移位元 , 需要注意負數的情況:
    Dim iStart As Long
    
    iStart = 1
    If B < 0 Then
        '第32位置換為 0
        B = B And &H7FFFFFFF
        B = B \ 2
        
        '第31位置換為 1
        B = B Or &H40000000
        
        iStart = 2
    End If
    
    Dim i As Long
    For i = iStart To num
        B = B \ 2
    Next
    
    BitMoveRight = B
End Function

Attribute VB_Name = "Module1"
Option Explicit

#If VBA7 Then
Public Declare PtrSafe Function GetActiveWindow Lib "user32" () As Long '獲得活動視窗的句柄
Declare PtrSafe Function getPT Lib "CaiqsVBApinvoke.arx" Alias "getpt" (ByRef x As Double, ByRef Y As Double, ByRef z As Double) As Integer

'在Windows系統中加入一種字形資源。
Public Declare PtrSafe Function AddFontResource Lib "gdi32" Alias "AddFontResourceA" (ByVal lpFileName As String) As Long
Public Declare PtrSafe Function SendMessage Lib "user32" Alias "SendMessageA" (ByVal hWnd As Long, ByVal wMsg As Long, ByVal wParam As Long, lParam As Any) As Long
Public Const HWND_BROADCAST = &HFFFF&
Public Const WM_FONTCHANGE = &H1D

#Else

Public Declare Function GetActiveWindow Lib "user32" () As Long '獲得活動視窗的句柄
Declare Function getPT Lib "CaiqsVBApinvoke.arx" Alias "getpt" (ByRef x As Double, ByRef y As Double, ByRef Z As Double) As Integer

'在Windows系統中加入一種字形資源。
Public Declare Function AddFontResource Lib "gdi32" Alias "AddFontResourceA" (ByVal lpFileName As String) As Long
Public Declare Function SendMessage Lib "user32" Alias "SendMessageA" (ByVal hWnd As Long, ByVal wMsg As Long, ByVal wParam As Long, lParam As Any) As Long
Public Const HWND_BROADCAST = &HFFFF&
Public Const WM_FONTCHANGE = &H1D

#End If

Attribute VB_Name = "ModuleManager"
Option Explicit
Option Private Module

Private Const MY_NAME = "ModuleManager"
Private Const MY_NAMENOT = "ModuleManagerNOT"
Private Const ERR_SUPPORTED_APPS = MY_NAME & " currently only supports Microsoft Word and Excel."

#Const MANAGING_WORD = 0
#Const MANAGING_EXCEL = 0
#Const MANAGING_POWERPOINT = 0
#Const MANAGING_ACCESS = 0
#Const MANAGING_OUTLOOK = 0
#Const MANAGING_AUTOCAD = 1


Dim allComponents As VBComponents
Dim fileSys As Object
Dim alreadySaved As Boolean

Public Sub ImportModules(FromDirectory As String, Optional ShowMsgBox As Boolean = True)
    Set fileSys = CreateObject("Scripting.FileSystemObject")
    'Cache some references
    'If the given directory does not exist then show an error dialog and exit
    Dim fromPath As String: fromPath = FromDirectory
    If Not fileSys.FolderExists(fromPath) Then
        fromPath = getFilePath() & "\" & fromPath
        If Not fileSys.FolderExists(fromPath) Then
            MsgBox "Could not locate import directory:  " & FromDirectory
            Exit Sub
        End If
    End If
    Dim dir As Object:     Set dir = fileSys.GetFolder(fromPath)
                
    'Import all VB code files from the given directory if any)
    Dim f As Object
    Dim arrThisMain As New Collection
    Dim imports As Object 'Must be qualified to distinguish it from an MS Word Dictionary
    Set imports = CreateObject("Scripting.Dictionary")
    Dim numFiles As Integer: numFiles = 0
    For Each f In dir.Files
        Dim dotIndex As String: dotIndex = InStrRev(f.Name, ".")
        Dim ext As String: ext = UCase(right(f.Name, Len(f.Name) - dotIndex))
        Dim correctType As Boolean: correctType = (ext = "BAS" Or ext = "CLS" Or ext = "FRM")
        Dim allowedName As Boolean: allowedName = left(f.Name, InStrRev(f.Name, ".") - 1) <> MY_NAME
        If correctType And allowedName Then
            numFiles = numFiles + 1
            Dim replaced As Boolean: replaced = doImport(f)
            Dim replacedStr As String
            replacedStr = IIf(replaced, " (replaced)", " (new)")
            imports.Add f.Name, replacedStr
        End If

        If ext = "DOCCLS" Then
            arrThisMain.Add f
        End If
    Next f
    '注： ThisMain 要最後載入
    Dim thisDoc As Object
    For Each thisDoc In arrThisMain
        Dim fc As Object
        Set fc = thisDoc
        numFiles = numFiles + 1
        replaced = InsertThisMainCode(fc)
        replacedStr = IIf(replaced, " (replaced)", " (Failed)")
        imports.Add thisDoc.Name, replacedStr
    Next thisDoc

    'Show a success message box, if requested
    If ShowMsgBox Then
        Dim i As Integer
        Dim msg As String: msg = numFiles & " modules imported:" & vbCrLf & vbCrLf
        For i = 0 To imports.Count - 1
            msg = msg & "    " & imports.keys()(i) & imports.Items()(i) & vbCrLf
        Next i
        Dim result As VbMsgBoxResult: result = MsgBox(msg, vbOKOnly)
    End If
End Sub
Public Sub ExportModules(ToDirectory As String)
    Set fileSys = CreateObject("Scripting.FileSystemObject")
    'Cache some references
    'If the given directory does not exist then show an error dialog and exit
    Dim toPath As String: toPath = ToDirectory
    If Not fileSys.FolderExists(toPath) Then

#If MANAGING_AUTOCAD Then
            toPath = ToDirectory
            fileSys.CreateFolder (toPath)
#Else
        toPath = getFilePath() & "\" & toPath
        If Not fileSys.FolderExists(toPath) Then _
            fileSys.CreateFolder (toPath)
#End If
    End If
    Dim dir As Object
    Set dir = fileSys.GetFolder(toPath)
    
    'Export all modules from this file (except default MS Office modules)
    Dim vbc As VBComponent
    Dim allComponents As VBComponents
    Set allComponents = getAllComponents()
    For Each vbc In allComponents
        Dim correctType As Boolean
        correctType = (vbc.Type = vbext_ct_StdModule Or vbc.Type = vbext_ct_ClassModule Or vbc.Type = vbext_ct_MSForm Or vbc.Type = vbext_ct_Document)
        If correctType And vbc.Name <> MY_NAMENOT Then
            Call doExport(vbc, dir.path)
        End If
    Next vbc
End Sub
Public Sub RemoveModules(Optional ShowMsgBox As Boolean = True)
    'Check the saved flag to prevent a save event loop
    If alreadySaved Then
        alreadySaved = False
        Exit Sub
    End If

    'Remove all modules from this file (except default MS Office modules obviously)
    Dim removals As New Collection
    Dim vbc As VBComponent
    Dim numModules As Integer: numModules = 0
    Dim allComponents As VBComponents:     Set allComponents = getAllComponents()
    For Each vbc In allComponents
        Dim correctType As Boolean: correctType = (vbc.Type = vbext_ct_StdModule Or vbc.Type = vbext_ct_ClassModule Or vbc.Type = vbext_ct_MSForm)
        If correctType And vbc.Name <> MY_NAME Then
            numModules = numModules + 1
            removals.Add vbc.Name
            allComponents.Remove vbc
        End If
    Next vbc

    'Set the saved flag to prevent a save event loop
    'Save file again now that all modules have been removed
    alreadySaved = True
    Call saveFile

    'Show a success message box
    If ShowMsgBox Then
        Dim item As Variant
        Dim msg As String: msg = numModules & " modules successfully removed:" & vbCrLf & vbCrLf
        For Each item In removals
            msg = msg & "    " & item & vbCrLf
        Next item
        msg = msg & vbCrLf & "Don't forget to remove any empty lines after the Attribute lines in .frm files..." _
                  & vbCrLf & "ModuleManager will never be re-imported or exported.  You must do this manually if desired." _
                  & vbCrLf & "NEVER edit code in the VBE and a separate editor at the same time!"
        Dim result As VbMsgBoxResult: result = MsgBox(msg, vbOKOnly)
    End If
End Sub

Private Function getFilePath() As String
#If MANAGING_WORD Then
    getFilePath = ThisDocument.path
#ElseIf MANAGING_EXCEL Then
    getFilePath = ThisWorkbook.path
#ElseIf MANAGING_AUTOCAD Then
        getFilePath = ThisDrawing.path
#Else
        Call raiseUnsupportedAppError
#End If
End Function

Private Function getAllComponents() As VBComponents
    #If MANAGING_WORD Then
        Set getAllComponents = ThisDocument.VBProject.VBComponents
    #ElseIf MANAGING_EXCEL Then
        Set getAllComponents = ThisWorkbook.VBProject.VBComponents
    #ElseIf MANAGING_AUTOCAD Then
        Set getAllComponents = ThisDrawing.Application.vbe.ActiveVBProject.VBComponents
    #Else
        Call raiseUnsupportedAppError
    #End If
End Function



Public Sub Export()
    '您可以使用此程式碼匯出所有文件:
    Dim vbe As vbe
    Set vbe = ThisDrawing.Application.vbe
    Dim comp As VBComponent
    Dim outDir As String
    outDir = "C:\\Temp\\VbaOutput"
    If dir(outDir, vbDirectory) = "" Then
        MkDir outDir
    End If
    For Each comp In vbe.ActiveVBProject.VBComponents
        Select Case comp.Type
            Case vbext_ct_StdModule
                comp.Export outDir & "\" & comp.Name & ".bas"
            Case vbext_ct_Document, vbext_ct_ClassModule
                comp.Export outDir & "\" & comp.Name & ".cls"
            Case vbext_ct_MSForm
                comp.Export outDir & "\" & comp.Name & ".frm"
            Case Else
                comp.Export outDir & "\" & comp.Name
        End Select
    Next comp

    MsgBox "VBA files were exported to : " & outDir
End Sub


Private Sub saveFile()
#If MANAGING_WORD Then
    ThisDocument.save
#ElseIf MANAGING_EXCEL Then
    ThisWorkbook.save
#ElseIf MANAGING_AUTOCAD Then
        ThisDrawing.save
#Else
        Call raiseUnsupportedAppError
#End If
End Sub

Private Sub raiseUnsupportedAppError()
    err.Raise Number:=vbObjectError + 1, Description:=ERR_SUPPORTED_APPS
End Sub

Private Function doImport(ByRef codeFile As Object) As Boolean
    On Error Resume Next

    'Determine whether a module with this name already exists
    Dim Name As String: Name = left(codeFile.Name, Len(codeFile.Name) - 4)
    Dim allComponents As VBComponents:   Set allComponents = getAllComponents()
    Dim m As VBComponent:     Set m = allComponents.item(Name)
    If err.Number <> 0 Then
        Set m = Nothing
    End If
    On Error GoTo 0

    'If so, remove it
    Dim alreadyExists As Boolean: alreadyExists = Not (m Is Nothing)
    If alreadyExists Then
        allComponents.Remove m
    End If
    'Then import the new module
    allComponents.Import (codeFile.path)
    doImport = alreadyExists
End Function
Private Function InsertThisMainCode(ByRef codeFile As Object) As Boolean
    On Error Resume Next

    'Determine whether a module with this name already exists
    Dim Name As String: Name = left(codeFile.Name, Len(codeFile.Name) - 7)
    Dim allComponents As VBComponents:     Set allComponents = getAllComponents()
    Dim ThisMainModule As VBComponent:     Set ThisMainModule = allComponents.item(Name)
    If err.Number <> 0 Then
        Set ThisMainModule = Nothing
        InsertThisMainCode = False
        Exit Function
    End If

    'If so, remove it
    Dim alreadyExists As Boolean: alreadyExists = fileSys.FileExists(codeFile.path)

    'If so, remove it (even if its ReadOnly)
    If alreadyExists Then

        Dim LnAllCode As String
        Dim stream As Object
        Set stream = fileSys.OpenTextFile(codeFile.path, 1) '1 means ForReading
        Do Until stream.AtEndOfStream
            LnAllCode = LnAllCode + vbCrLf + stream.ReadLine
        Loop
        If ThisMainModule.CodeModule.CountOfLines > 1 Then
            ThisMainModule.CodeModule.DeleteLines 1, ThisMainModule.CodeModule.CountOfLines - 1
        End If
        ThisMainModule.CodeModule.InsertLines 1, LnAllCode
        ThisMainModule.CodeModule.DeleteLines 1, 1 '刪除第一行空白
    End If

    InsertThisMainCode = alreadyExists
End Function
Private Function doExport(ByRef module As VBComponent, dirPath As String) As Boolean
    'Determine whether a file with this component's name already exists
    Dim ext As String
    Select Case module.Type
        Case vbext_ct_MSForm
            ext = "frm"
        Case vbext_ct_ClassModule
            ext = "cls"
        Case vbext_ct_StdModule
            ext = "bas"
        Case vbext_ct_Document
            ext = "doccls"
    End Select
    Dim filePath As String: filePath = dirPath & "\" & module.Name & "." & ext
    Dim alreadyExists As Boolean: alreadyExists = fileSys.FileExists(filePath)

    'If so, remove it (even if its ReadOnly)
    If alreadyExists Then
        Dim f As Object:     Set f = fileSys.GetFile(filePath)
        If (f.Attributes And 1) Then _
            f.Attributes = f.Attributes - 1 'The bitmask for ReadOnly file attribute
        fileSys.DeleteFile (filePath)
    End If
    If module.Type = vbext_ct_Document Then
        ' ThisWork 匯出是不一樣的
        doExportThisMainCode module, filePath
    Else
        'Then export the module
        'Remove it also, so that the file stays small (and unchanged according to version control)
        module.Export (filePath)
    End If
    doExport = alreadyExists
End Function
Private Function doExportThisMainCode(ByRef module As VBComponent, filePath As String) As Boolean

    'Dim alreadyExists As Boolean: alreadyExists = fileSys.FileExists(filePath)
    Dim stream As Object
    Set stream = fileSys.OpenTextFile(filePath, 2, True) '如果不存在test1.xls將自動建立。
    If Not (stream Is Nothing) Then

        Dim LnAllCode As String


        If module.CodeModule.CountOfLines > 1 Then
            LnAllCode = module.CodeModule.lines(1, module.CodeModule.CountOfLines - 1)
        Else
            LnAllCode = module.CodeModule.lines(1, 1)
        End If

        stream.WriteLine LnAllCode

    End If

End Function



'Private Sub Workbook_Open()
'    'Provide the path to a directory with VBA code files. Paths may be relative or absolute.
'    'You can add additional ImportModules() statements to import from multiple locations.
'    'The boolean argument specifies whether or not to show a Message Box on completion.
'    'Remove or comment out these statements when you are ready to provide this workbook to end users,
'    'so that they don't get confused by message boxes about import errors.
'    Call ImportModules(ThisWorkbook.Name & ".modules", ShowMsgBox:=True)
'End Sub
'
'Private Sub Workbook_BeforeSave(ByVal SaveAsUI As Boolean, ByRef Cancel As Boolean)
'    'Provide the path to a directory where you want to export modules. Paths may be relative or absolute.
'    'You can add additional ExportModules() statements to export to multiple locations.
'    'Remove or comment out these statements when you are ready to provide this workbook to end users,
'    'so that they don't get confused by the appearance of a bunch of mysterious code files upon saving!
'    Call ExportModules(ThisWorkbook.Name & ".modules")
'End Sub

'Private Sub Workbook_BeforeClose__xxx(ByRef Cancel As Boolean)
'The boolean argument specifies whether or not to show a Message Box on completion.
'Remove or comment out this statement when you are ready to provide this workbook to end users,
'so that modules are not removed, and functionality is not broken the next time the workbook is opened.
'    Call RemoveModules(ShowMsgBox:=True)
'End Sub


Public Sub ExportExcelCode()
    'Excel Vba Code 匯出
    Call ExportModules(ThisWorkbook.Name & ".modules")

End Sub

Public Sub ImportExcelCode()
    'Excel Vba Code 匯入
    Call ImportModules(ThisWorkbook.Name & ".modules", ShowMsgBox:=True)

End Sub


Public Sub ThisImportModules()
    'AutoCAD Vba Code 匯入
    Dim objVBE As vbe
    Set objVBE = ThisDrawing.Application.vbe
    'MsgBox objVBE.ActiveVBProject.FileName
    Call ImportModules(objVBE.ActiveVBProject.fileName & ".modules", ShowMsgBox:=True)

End Sub
Public Sub ThisExportModules()
    'AutoCAD Vba Code 匯出
    Dim objVBE As vbe
    Set objVBE = ThisDrawing.Application.vbe
    'MsgBox objVBE.ActiveVBProject.Name

    Call ExportModules(objVBE.ActiveVBProject.fileName & ".modules")
End Sub

Attribute VB_Name = "ModuleTextStyle"
Option Explicit

'字體枚舉類型
Public Const LF_FACESIZE = 32

Public Type LOGFONT
        lfHeight As Long
        lfWidth As Long
        lfEscapement As Long
        lfOrientation As Long
        lfWeight As Long
        lfItalic As Byte
        lfUnderline As Byte
        lfStrikeOut As Byte
        lfCharSet As Byte
        lfOutPrecision As Byte
        lfClipPrecision As Byte
        lfQuality As Byte
        lfPitchAndFamily As Byte
        lfFaceName(LF_FACESIZE) As Byte
End Type

Public Type NEWTEXTMETRIC
        tmHeight As Long
        tmAscent As Long
        tmDescent As Long
        tmInternalLeading As Long
        tmExternalLeading As Long
        tmAveCharWidth As Long
        tmMaxCharWidth As Long
        tmWeight As Long
        tmOverhang As Long
        tmDigitizedAspectX As Long
        tmDigitizedAspectY As Long
        tmFirstChar As Byte
        tmLastChar As Byte
        tmDefaultChar As Byte
        tmBreakChar As Byte
        tmItalic As Byte
        tmUnderlined As Byte
        tmStruckOut As Byte
        tmPitchAndFamily As Byte
        tmCharSet As Byte
        ntmFlags As Long
        ntmSizeEM As Long
        ntmCellHeight As Long
        ntmAveWidth As Long
End Type

#If VBA7 Then
Public Declare PtrSafe Function EnumFontFamilies Lib "gdi32" Alias "EnumFontFamiliesA" (ByVal hDC As Long, ByVal lpszFamily As String, ByVal lpEnumFontFamProc As Long, lParam As Any) As Long
Public Declare PtrSafe Function GetDC Lib "user32" (ByVal hWnd As Long) As Long
Public Declare PtrSafe Function ReleaseDC Lib "user32" (ByVal hWnd As Long, ByVal hDC As Long) As Long
    
'複製以下代碼到一模塊中
Public Declare PtrSafe Function GetWindowsDirectory Lib "kernel32" Alias "GetWindowsDirectoryA" (ByVal lpBuffer As String, ByVal nSize As Long) As Long
Public Declare PtrSafe Function GetSystemDirectory Lib "kernel32" Alias "GetSystemDirectoryA" (ByVal lpBuffer As String, ByVal nSize As Long) As Long

#Else

Public Declare Function EnumFontFamilies Lib "gdi32" Alias "EnumFontFamiliesA" (ByVal hDC As Long, ByVal lpszFamily As String, ByVal lpEnumFontFamProc As Long, lParam As Any) As Long
Public Declare Function GetDC Lib "user32" (ByVal hWnd As Long) As Long
Public Declare Function ReleaseDC Lib "user32" (ByVal hWnd As Long, ByVal hDC As Long) As Long
    
'複製以下代碼到一模塊中
Public Declare Function GetWindowsDirectory Lib "kernel32" Alias "GetWindowsDirectoryA" (ByVal lpBuffer As String, ByVal nSize As Long) As Long
Public Declare Function GetSystemDirectory Lib "kernel32" Alias "GetSystemDirectoryA" (ByVal lpBuffer As String, ByVal nSize As Long) As Long

#End If

Public Enum FontType
    ShxFont = 0
    BigFont = 1
    TrueTypeFont = 2
End Enum

Public Function EnumFontFamProc(lpNLF As LOGFONT, lpNTM As NEWTEXTMETRIC, _
    ByVal FontType As Long, fonts As Collection) As Long
    
    Dim FaceName As String
    Dim FullName As String
    FaceName = StrConv(lpNLF.lfFaceName, vbUnicode)
    fonts.Add left$(FaceName, InStr(FaceName, vbNullChar) - 1)
    EnumFontFamProc = 1
End Function

'自定義兩個函數：
'獲取系統字體
Public Sub FillListWithFonts(ByVal hWnd As Long, ByRef fonts As Collection)
    Dim hDC As Long
    hDC = GetDC(hWnd)
    EnumFontFamilies hDC, vbNullString, AddressOf EnumFontFamProc, fonts
    ReleaseDC hWnd, hDC
End Sub

Public Function GetShxFont(ByVal bBigFont As Boolean) As Variant
    Dim strFontFileName() As String     ' 所有字體名稱的數組
    Dim strFontPath() As String     ' AutoCAD的字體文件路徑
    
    ' 獲得所有的支持文件路徑
    strFontPath = Split(ThisDrawing.Application.preferences.Files, " ")
    
    ' 遍歷所有的支持文件路徑
    Dim i As Integer
    Dim bFirst As Boolean       ' 是否是第一次查找該文件夾
    Dim strFont As String       ' 字體文件名稱
    Dim strTemp As String       ' 讀取到的字體文件的一行
    Dim intCount As Integer     ' 字體數組的維數
    Dim strFontFile As String   ' 字體文件的位置
    intCount = -1
    For i = 0 To UBound(strFontPath)
        bFirst = True
        ' 確保最後一個字符是"\"
        strFontPath(i) = IIf(right(strFontPath(i), 1) = "\", strFontPath(i), strFontPath(i) & "\")
        
        Do
            If bFirst Then
                strFont = dir(strFontPath(i) & "*.shx")
                bFirst = False
            Else
                strFont = dir
            End If
            
            If Len(strFont) <> 0 Then
                ' 打開字體文件
                strFontFile = strFontPath(i) & strFont
                Open strFontFile For Input As #1
                Line Input #1, strTemp
                Close #1
                
                ' 判斷字體的類型
                If bBigFont Then
                    If Mid(strTemp, 12, 7) = "bigfont" Then
                        intCount = intCount + 1
                        ReDim Preserve strFontFileName(intCount)
                        strFontFileName(intCount) = strFont
                    End If
                Else
                    If Mid(strTemp, 12, 7) = "unifont" Or Mid(strTemp, 12, 6) = "shapes" Then
                        intCount = intCount + 1
                        ReDim Preserve strFontFileName(intCount)
                        strFontFileName(intCount) = strFont
                    End If
                End If
            Else
                Exit Do
            End If
        Loop
    Next i
    
    GetShxFont = strFontFileName
End Function
 '在程序中調用

Public Function GetWindowsFonts() As Variant
    Dim bBigFont As Boolean
    Dim WindowsDirectory As String, SystemDirectory As String, x As Long
    WindowsDirectory = space(255)       'Windows的安裝目錄
    SystemDirectory = space(255)        '系統目錄是
    x = GetWindowsDirectory(WindowsDirectory, 255)
    x = GetSystemDirectory(SystemDirectory, 255)
    
    
    Dim strFontFileName() As String     ' 所有字體名稱的數組
    Dim WinFontPath As String     ' Windows 的字體文件路徑
    
    ' 獲得所有的支持文件路徑
    WinFontPath = left(WindowsDirectory, InStr(WindowsDirectory, Chr(0)) - 1)
    WinFontPath = Trim(WinFontPath) & "\Fonts\"
    
    ' 遍歷所有的支持文件路徑
    Dim i As Integer
    Dim bFirst As Boolean       ' 是否是第一次查找該文件夾
    Dim strFont As String       ' 字體文件名稱
    Dim strTemp As String       ' 讀取到的字體文件的一行
    Dim intCount As Integer     ' 字體數組的維數
    Dim strFontFile As String   ' 字體文件的位置
    intCount = -1
    For i = 0 To 0
        bFirst = True
        ' 確保最後一個字符是"\"
        WinFontPath = IIf(right(WinFontPath, 1) = "\", WinFontPath, WinFontPath & "\")
        
        Do
            If bFirst Then
                strFont = dir(WinFontPath & "*")
                bFirst = False
            Else
                strFont = dir
            End If
            
            If Len(strFont) <> 0 Then
                ' 打開字體文件
                strFontFile = WinFontPath & strFont
                
                
                
                ' 判斷字體的類型
                If InStr(1, UCase(strFontFile), "TTF") <> 0 Then
                        intCount = intCount + 1
                        ReDim Preserve strFontFileName(intCount)
                        strFontFileName(intCount) = strFontFile
                        
                ElseIf InStr(1, UCase(strFontFile), "TTE") <> 0 Then
                        intCount = intCount + 1
                        ReDim Preserve strFontFileName(intCount)
                        strFontFileName(intCount) = strFontFile
                ElseIf InStr(1, UCase(strFontFile), "TTC") <> 0 Then
                        intCount = intCount + 1
                        ReDim Preserve strFontFileName(intCount)
                        strFontFileName(intCount) = strFontFile
                End If
            Else
                Exit Do
            End If
        Loop
    Next i
    
    GetWindowsFonts = strFontFileName
    
    
End Function

Public Function CreateTextStyle(ByVal fontName As String, ByVal styleName As String, ByVal font As FontType) As AcadTextStyle
    Dim objTextStyle As AcadTextStyle
    Set objTextStyle = ThisDrawing.TextStyles.Add(styleName)
    
    Dim WindowsDirectory As String, SystemDirectory As String, x As Long
    Dim fontTemp As String
    
    If font = ShxFont Then
        objTextStyle.fontFile = fontName
    ElseIf font = BigFont Then
    
        WindowsDirectory = space(255)       'Windows的安裝目錄
        x = GetWindowsDirectory(WindowsDirectory, 255)
        
        
        Dim strFontFileName() As String     ' 所有字體名稱的數組
        Dim WinFontPath As String     ' Windows 的字體文件路徑
        
        ' 獲得所有的支持文件路徑
        WinFontPath = left(WindowsDirectory, InStr(WindowsDirectory, Chr(0)) - 1)
        WinFontPath = Trim(WinFontPath) & "\Fonts\"
        ' 判斷字體的類型
        If InStr(1, UCase(fontName), "TTF") <> 0 Then
            fontTemp = """" & WinFontPath & fontName & """"
            objTextStyle.BigFontFile = fontTemp
            
        ElseIf InStr(1, UCase(fontName), "TTE") <> 0 Then
            fontTemp = """" & WinFontPath & fontName & """"
            objTextStyle.BigFontFile = fontTemp
        End If
    ElseIf font = TrueTypeFont Then
        ' 獲得當前字體的樣式
        Dim typeFace As String
        Dim Bold As Boolean
        Dim Italic As Boolean
        Dim charSet As Long
        Dim PitchandFamily As Long
        ThisDrawing.ActiveTextStyle.GetFont typeFace, Bold, Italic, charSet, PitchandFamily
        
        objTextStyle.SetFont fontName, Bold, Italic, charSet, PitchandFamily
    End If
    
    objTextStyle.width = 1#
    objTextStyle.ObliqueAngle = 0#
    
    Set CreateTextStyle = objTextStyle
End Function

Attribute VB_Name = "Module_sort"
Option Explicit
Option Compare Binary


Option Base 1
'陣列排序----大
Dim MaxVal As Variant
    
Function SelectionSortMaxTow(TempArray As Variant, TempArrayEnt As Variant)
    Dim MaxIndex As Double
    Dim MaxObj As Object
    Dim i, j As Integer

    ' Step through the elements in the array starting with the
    ' last element in the array.
    For i = UBound(TempArray) To 0 Step -1

        ' Set MaxVal to the element in the array and save the
        ' index of this element as MaxIndex.
        MaxVal = TempArray(i)
        MaxIndex = i

        ' Loop through the remaining elements to see if any is
        ' larger than MaxVal. If it is then set this element
        ' to be the new MaxVal.
        For j = 0 To i
            If TempArray(j) > MaxVal Then
                MaxVal = TempArray(j)
                Set MaxObj = TempArrayEnt(j)
                MaxIndex = j
            End If
        Next j

        ' If the index of the largest element is not i, then
        ' exchange this element with element i.
        If MaxIndex < i Then
            TempArray(MaxIndex) = TempArray(i)
            TempArray(i) = MaxVal
            
            Set TempArrayEnt(MaxIndex) = TempArrayEnt(i)
            Set TempArrayEnt(i) = MaxObj
            
        End If
    Next i
End Function
    
    
    
    
    
    
    
Function SelectionSortMax(TempArray As Variant)
    Dim MaxIndex As Integer
    Dim i, j As Integer

    ' Step through the elements in the array starting with the
    ' last element in the array.
    For i = UBound(TempArray) To 1 Step -1

        ' Set MaxVal to the element in the array and save the
        ' index of this element as MaxIndex.
        MaxVal = TempArray(i)
        MaxIndex = i

        ' Loop through the remaining elements to see if any is
        ' larger than MaxVal. If it is then set this element
        ' to be the new MaxVal.
        For j = 1 To i
            If TempArray(j) > MaxVal Then
                MaxVal = TempArray(j)
                MaxIndex = j
            End If
        Next j

        ' If the index of the largest element is not i, then
        ' exchange this element with element i.
        If MaxIndex < i Then
            TempArray(MaxIndex) = TempArray(i)
            TempArray(i) = MaxVal
        End If
    Next i

End Function

'陣列排序----小
Function SelectionSortMin(TempArray As Variant)
    Dim MinVal As Variant
    Dim MinIndex As Integer
    Dim i, j As Integer

    ' Step through the elements in the array starting with the
    ' last element in the array.
    For i = 1 To UBound(TempArray)
    
        ' Set MaxVal to the element in the array and save the
        ' index of this element as MaxIndex.
        MinVal = TempArray(i)
        MinIndex = i

        ' Loop through the remaining elements to see if any is
        ' larger than MaxVal. If it is then set this element
        ' to be the new MaxVal.
        For j = 1 To UBound(TempArray)
            If TempArray(i) = "" Then
            
            ElseIf TempArray(j) > TempArray(i) Then
                    MinVal = TempArray(j)
                    TempArray(j) = TempArray(i)
                    TempArray(i) = MinVal
                
            ElseIf TempArray(i) = "" Then
                    MinVal = TempArray(j)
                    TempArray(j) = TempArray(i)
                    TempArray(i) = MinVal
            End If
        Next j

    Next
End Function

Function SelectionSort(TempArray As Variant)
    Dim MaxVal As Variant
    Dim MaxIndex As Integer
    Dim i, j As Integer

    ' Step through the elements in the array starting with the
    ' last element in the array.
    For i = UBound(TempArray) To 1 Step -1

        ' Set MaxVal to the element in the array and save the
        ' index of this element as MaxIndex.
        MaxVal = TempArray(i)
        MaxIndex = i

        ' Loop through the remaining elements to see if any is
        ' larger than MaxVal. If it is then set this element
        ' to be the new MaxVal.
        For j = 1 To i
            If TempArray(j) > MaxVal Then
                MaxVal = TempArray(j)
                MaxIndex = j
            End If
        Next j

        ' If the index of the largest element is not i, then
        ' exchange this element with element i.
        If MaxIndex < i Then
            TempArray(MaxIndex) = TempArray(i)
            TempArray(i) = MaxVal
        End If
    Next i

End Function

Sub SelectionSortMyArray()
    Dim TheArray As Variant
    Dim SSS As String
    Dim i As Integer
    ' Create the array.
    TheArray = Array("one", "two", "three", "four", "five", "six", _
        "seven", "eight", "nine", "ten")

    ' Sort the Array and display the values in order.
    SelectionSort TheArray
    For i = 1 To UBound(TheArray)
        SSS = SSS & TheArray(i) & vbCrLf
    Next i
MsgBox SSS
End Sub

Attribute VB_Name = "MusicBlockGraphics"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
    

Const MAINLAYER As String = "main"     '主要的圖層
'    '音附的駐點位置
'Private Type GripPoints
'    osnPtMid(0 To 2) As Double       '在正中間
'    osnPtNode1(0 To 2) As Double     '在左下
'    osnPtNode2(0 To 2) As Double     '在中上
'    osnPtEnd1(0 To 2) As Double      '在左中
'    osnPtEnd2(0 To 2) As Double      '在右中
'    atPt(0 To 2) As Double           '備注點
'End Type
Dim gTextSize As Double
Dim gAtPt As New point
Dim MData As MusicItem
Public nowPartLayer As String


Dim MFS() As MusicFing

Dim Grippt As GripPoints  '音附指法 狀態


Dim kFing(30 To 255) As String
Dim posFing(0 To 255) As point
Dim kTowFing(30 To 255) As String
Dim posTowFing(0 To 255) As point
    
Const MAX200 As Integer = 200

Function Grip() As GripPoints
      Grip = Grippt
End Function

Property Let TextSize(TSize As Double)
    gTextSize = TSize
End Property

Property Get TextSize() As Double
    TextSize = gTextSize
End Property

Property Let DataTest(dtest As MusicItem)
    MData = dtest
End Property
Property Get DataTest() As MusicItem
    DataTest = MData
End Property
Property Get copy() As MusicBlockGraphics
    Dim copy_mbg As New MusicBlockGraphics
    copy_mbg.setDataText gAtPt, MData, gTextSize
    Set copy = copy_mbg
End Property
Function checkBlockName(Name As String) As Boolean
    Dim ck As Boolean
    Dim i As Integer
    ck = False
    For i = 0 To ThisDrawing.Blocks.Count - 1
        If ThisDrawing.Blocks.item(i).Name = Name Then
            ck = True
            Exit For
        End If
    Next
    checkBlockName = ck
End Function

Static Function getGlyphs()

End Function


Sub setDataText(position As point, musItem As MusicItem, TextSize As Double)

    'position 插入的位置
    'cst  文字資料=指法1 八度音 主音 拍子 指法2
    '          共5筆 每筆一個字元 所以共5個字元
    'textSize  字形大小
    
    Set MData = musItem
    
    gAtPt.x = position.x
    gAtPt.y = position.y
    gAtPt.Z = position.Z
    
    gTextSize = TextSize
    setGripPoints gAtPt
    
    
    
'Public Type MusicFing
'    sTONE As String        ' 升降記號 行
'    sFinge As String   '這是指法行     _+)(*&
'    sScale As String   '這是高低音行   .:! , ?
'    sNote As String   '這為主行       1234567.|l
'    sTempo As String   '這是拍子       -=368acefz
'    sTowFinge As String   '這是指法行第二行  _+)(*&
'    sSlur As String
'End Type
    Dim currenCount As Integer
    Dim sarr() As String
    Dim reg As New RegExp
    Dim cc As String
    Dim sNote As String
    Dim iTempo As Integer
    Dim sTempo As Integer
    Dim iScale As Integer
    Dim sScale As Integer
    Dim i As Integer
    
    cc = ""
    
    '取得關鍵字  主音 AMT.iNote
    Dim noteListCode As New iArray
    Dim noteListType As iArray
  
            
    noteListCode.PushArray Array("0 M-NOTE0", _
        "1 M-NOTE1", _
        "2 M-NOTE2", _
        "3 M-NOTE3", _
        "4 M-NOTE4", _
        "5 M-NOTE5", _
        "6 M-NOTE6", _
        "7 M-NOTE7", _
        ". M-NOTE.", _
        "- M-NOTE-", _
        "o M-NOTEo", _
        "x M-NOTEx", _
        "X M-NOTEX2", _
        "e M-NOTEe", _
        "E M-NOTEE2")
            
    Dim iLe As Integer
    Dim cn As String
    Dim tempoListCode As New iArray

    tempoListCode.PushArray Array( _
            "1 M-TEMPO1", _
            "2 M-TEMPO2", _
            "3 M-TEMPO3", _
            "4 M-TEMPO4")
            
    
    Dim scaleListCode As New iArray
    scaleListCode.PushArray Array( _
            ". M-OCTAVE1 1", _
            ": M-OCTAVE2 2", _
            "! M-OCTAVE3 3", _
            ", M-OCTAVEa -1", _
            "; M-OCTAVEb -2", _
            "? M-OCTAVEc -3")
            
    '取得升降字 -特疏字法
    Dim toneListCode As New iArray
    toneListCode.PushArray Array( _
            "# MT-SHARP", _
            "b MT-FLAT", _
            "o MT-NATURAL")
    If MData.typs = Cg.rest Then
        Exit Sub
    End If
    
    ReDim MFS(MData.notes.Count - 1)
    For currenCount = 0 To MData.notes.Count - 1
        
        cc = MData.notes(currenCount).mnote
        For i = 0 To noteListCode.Count - 1
            sarr = Split(noteListCode(i), " ")
            If cc = sarr(0) Then
                If G.isVirtualChar Then
                    MFS(currenCount).sNote = sarr(1) & "_o"
                Else
                    MFS(currenCount).sNote = sarr(1)
                End If
                Exit For
            Else
                MFS(currenCount).sNote = ""
            End If
        Next
    
        
        '取得關鍵字 拍子  -=368acefz amt.iTempo
        iLe = Tempo_c2line(MData.notes(currenCount).mtempo)
        cc = MData.notes(currenCount).mtempo
        For i = 0 To tempoListCode.Count - 1
            sarr = Split(tempoListCode(i), " ")
            If iLe = sarr(0) Then
                MFS(currenCount).sTempo = sarr(1)
                MFS(currenCount).iTempo = iLe
                Exit For
            Else
                MFS(currenCount).sTempo = cc
                MFS(currenCount).iTempo = iLe
            End If
        Next
        
        
        '取得關鍵字高低音行   .:! , ?
        cc = MData.notes(currenCount).mscale
        For i = 0 To scaleListCode.Count - 1
            sarr = Split(scaleListCode(i), " ")
            If cc = sarr(0) Then
                MFS(currenCount).sScale = sarr(1)
                MFS(currenCount).iScale = sarr(2)
                Exit For
            Else
                MFS(currenCount).sScale = ""
                MFS(currenCount).iScale = 0
            End If
        Next
    
    
        '取得關鍵字 -指法1
        MFS(currenCount).sFinge = ""
        cc = MData.notes(currenCount).mfingering
        Select Case cc
            Case "a" To "z", "A" To "Z", "-", "=", "@"
                MFS(currenCount).sFinge = kFing(Asc(cc))
                Set MFS(currenCount).mfPosition = posFing(Asc(cc)).clone
            Case Else
            MFS(currenCount).sFinge = ""
            Set MFS(currenCount).mfPosition = New point
        End Select
    
    
    
    '    '取得關鍵字 -指法2
        cc = MData.notes(currenCount).mtow_fingering
        MFS(currenCount).sTowFinge = ""
        Select Case cc
            Case "a" To "z", "A" To "Z", "-", "=", "@"
                MFS(currenCount).sTowFinge = kTowFing(Asc(cc))
                Set MFS(currenCount).mfTowPosition = posTowFing(Asc(cc)).clone
            Case Else
            MFS(currenCount).sTowFinge = ""
            Set MFS(currenCount).mfTowPosition = New point
        End Select
    
        '取得升降字 -特疏字法
        cc = MData.notes(currenCount).mtone
        For i = 0 To toneListCode.Count - 1
            sarr = Split(toneListCode(i), " ")
            If cc = sarr(0) Then
                MFS(currenCount).sTONE = sarr(1)
                Exit For
            Else
                MFS(currenCount).sTONE = cc
            End If
        Next
    Next

End Sub

Private Sub setGripPoints(ths_aPt As point)
'駐點轉換
    'Dim Grippt As New GripPoints
    Set Grippt.atPt = ths_aPt
    Set Grippt.gptLeft = New point
    Set Grippt.gptLeftDown = New point
    Set Grippt.gptMid = New point
    Set Grippt.gptMidUp = New point
    Set Grippt.gptRight = New point
    
    
    
    '在正中間
    Grippt.gptMid.x = ths_aPt.x + (amt.A_TEXT_WIDTH * gTextSize) / 2
    Grippt.gptMid.y = ths_aPt.y + (amt.bkMidHight * gTextSize)
    
    '在中上
    Grippt.gptMidUp.x = ths_aPt.x + (amt.A_TEXT_WIDTH * gTextSize) / 2
    Grippt.gptMidUp.y = ths_aPt.y + (amt.bkMidUpHight * gTextSize)
    
    '在左下
    Set Grippt.gptLeftDown = ths_aPt
    
    '在左中
    Grippt.gptLeft.x = ths_aPt.x
    Grippt.gptLeft.y = ths_aPt.y + (amt.bkMidHight * gTextSize)
    '在右中
    Grippt.gptRight.x = ths_aPt.x + (amt.A_TEXT_WIDTH * gTextSize)
    Grippt.gptRight.y = ths_aPt.y + (amt.bkMidHight * gTextSize)
    
End Sub
Public Function drawSlur(mt_slur_left As MusicBlockGraphics, mt_slur_right As MusicBlockGraphics)
    '繪圓滑線
        Dim plineSlur As AcadLWPolyline
        Dim points(0 To 7) As Double
        Dim points_s(0 To 5) As Double
        Dim lenght As Double
        ' Find the bulge of the third segment
        Dim color As New AcadAcCmColor
        
        
        Dim islurAddX As Double
        Dim islurAddY As Double
        Dim islurBx As Double
        Dim islurBy As Double
        
        islurAddX = 0.45 * gTextSize
        islurAddY = 0.45 * gTextSize
        
        islurBy = 0.45 * gTextSize
        
        '看是否弧線的距離太近
        
        lenght = Abs(mt_slur_left.Grip.gptMid.x - mt_slur_right.Grip.gptMid.x)
        If lenght >= islurAddX * 2 Then
        
            points(0) = mt_slur_left.Grip.gptMid.x
            points(1) = mt_slur_left.Grip.gptMidUp.y + islurBy
            points(2) = points(0) + islurAddX
            points(3) = points(1) + islurAddY
            points(4) = points(2) + lenght - (islurAddX * 2)
            points(5) = points(3)
            points(6) = points(4) + islurAddX
            points(7) = points(1)
            ' Create a lightweight Polyline object in model space
           Set plineSlur = ThisDrawing.ModelSpace.AddLightWeightPolyline(points)
    
           
           ' Change the bulge of the third segment
           plineSlur.SetBulge 0, (-0.5858 / 1.4142)
           plineSlur.SetBulge 2, (-0.5858 / 1.4142)
           plineSlur.setWidth 0, 0, 0.15
           plineSlur.setWidth 1, 0.15, 0.15
           plineSlur.setWidth 2, 0.15, 0
                           
        Else
        '距離太近的畫線
            points_s(0) = mt_slur_left.Grip.gptMid.x
            points_s(1) = mt_slur_left.Grip.gptMidUp.y + islurBy
            points_s(2) = points_s(0) + (lenght / 2)
            points_s(3) = points_s(1) + islurAddY
            points_s(4) = points_s(2) + (lenght / 2)
            points_s(5) = points_s(1)
            ' Create a lightweight Polyline object in model space
           Set plineSlur = ThisDrawing.ModelSpace.AddLightWeightPolyline(points_s)
           ' Change the bulge of the third segment
           plineSlur.SetBulge 0, (-0.5858 / 1.4142)
           plineSlur.SetBulge 1, (-0.5858 / 1.4142)
           
           plineSlur.setWidth 0, 0, 0.15
           plineSlur.setWidth 1, 0.15, 0
        End If
    plineSlur.Layer = "fige"
    
    color.ColorIndex = 3
    plineSlur.TrueColor = color
    plineSlur.Update
                        
    Set drawSlur = plineSlur
End Function
Public Function drawSlurToEnd(mt_slur_left As MusicBlockGraphics, endX As Double)
    '繪圓滑線 到尾部
        Dim plineSlur As AcadLWPolyline
        Dim points(0 To 5) As Double
        Dim sLenght As Double
        ' Find the bulge of the third segment
        Dim color As New AcadAcCmColor
        
        
        Dim islurAddX As Double
        Dim islurAddY As Double
        Dim islurBx As Double
        Dim islurBy As Double
        
        islurAddX = 0.5 * gTextSize
        islurAddY = 0.45 * gTextSize
        
        islurBy = 0.45 * gTextSize
        
        '看是否弧線的距離太近
        
        sLenght = Abs(mt_slur_left.Grip.gptMid.x - endX) - islurAddX
        If sLenght < 1 Then
            sLenght = 1
        End If
        
        points(0) = mt_slur_left.Grip.gptMid.x
        points(1) = mt_slur_left.Grip.gptMidUp.y + islurBy
        points(2) = points(0) + islurAddX
        points(3) = points(1) + islurAddY
        points(4) = points(0) + sLenght + islurAddX
        points(5) = points(3)
        ' Create a lightweight Polyline object in model space
        Set plineSlur = ThisDrawing.ModelSpace.AddLightWeightPolyline(points)
        
        
        ' Change the bulge of the third segment
        plineSlur.SetBulge 0, (-0.5858 / 1.4142)
        plineSlur.setWidth 0, 0, 0.15
        plineSlur.setWidth 1, 0.15, 0.15
                           
        plineSlur.Layer = "fige"
        
        color.ColorIndex = 3
        plineSlur.TrueColor = color
        plineSlur.Update
                        
        Set drawSlurToEnd = plineSlur
End Function

Public Function drawSlurStarTo(starX As Double, mt_slur_right As MusicBlockGraphics)
    '繪圓滑線 從頭 到 元素
        Dim plineSlur As AcadLWPolyline
        Dim points(0 To 5) As Double
        Dim sLenght As Double
        ' Find the bulge of the third segment
        Dim color As New AcadAcCmColor
        
        
        Dim islurAddX As Double
        Dim islurAddY As Double
        Dim islurBx As Double
        Dim islurBy As Double
        Dim sX As Double
        Dim sY As Double
        
        islurAddX = 0.45 * gTextSize
        islurAddY = 0.45 * gTextSize
        
        islurBy = 0.45 * gTextSize
        
        '看是否弧線的距離太近
        
        sLenght = Abs(starX - mt_slur_right.Grip.gptMid.x) - islurAddX
        If sLenght < 1 Then
            sLenght = 1
        End If
            sX = mt_slur_right.Grip.gptMid.x - islurAddX - sLenght
            sY = mt_slur_right.Grip.gptMidUp.y + islurBy + islurAddY
        
            points(0) = sX
            points(1) = sY
            points(2) = points(0) + sLenght
            points(3) = points(1)
            points(4) = points(2) + islurAddX
            points(5) = points(3) - islurAddY
        ' Create a lightweight Polyline object in model space
        Set plineSlur = ThisDrawing.ModelSpace.AddLightWeightPolyline(points)
        
        
        ' Change the bulge of the third segment
        plineSlur.SetBulge 1, (-0.5858 / 1.4142)
        plineSlur.setWidth 0, 0.15, 0.15
        plineSlur.setWidth 1, 0.15, 0
                           
        plineSlur.Layer = "fige"
        
        color.ColorIndex = 3
        plineSlur.TrueColor = color
        plineSlur.Update
                        
        Set drawSlurStarTo = plineSlur
End Function



Public Function drawTuplet(mt_tuplet_left As MusicBlockGraphics, mt_tuplet_right As MusicBlockGraphics, count_tuplet As Integer)
    '繪 3 5 6 7 連音線
    Dim plineTuplet As AcadLWPolyline
    Dim points(0 To 7) As Double
    Dim points_s(0 To 5) As Double
    'Dim lenght As Double
    ' Find the bulge of the third segment
    Dim color As New AcadAcCmColor
        
    Dim islurAddX As Double
    Dim islurAddY As Double
    Dim islurBx As Double
    Dim islurBy As Double
    
    islurAddX = 0.3 * gTextSize
    islurAddY = 0.3 * gTextSize
    
    islurBy = 0.5 * gTextSize
        
    '總長度
    'lenght = Abs(mt_tuplet_left.Grip.gptLeft.x - mt_tuplet_right.Grip.gptRight.x)
    
    
    '畫線段
    points(0) = mt_tuplet_left.Grip.gptLeft.x + gTextSize * 0.1
    points(1) = mt_tuplet_left.Grip.gptMidUp.y + islurBy
    points(2) = points(0)
    points(3) = points(1) + islurAddY
    points(4) = mt_tuplet_right.Grip.gptRight.x - gTextSize * 0.1
    points(5) = points(3)
    points(6) = points(4)
    points(7) = points(1)
    ' Create a lightweight Polyline object in model space
    Set plineTuplet = ThisDrawing.ModelSpace.AddLightWeightPolyline(points)

    '畫圓取交點
    Dim circleObj As AcadCircle
    Dim centerPt(0 To 2) As Double
    Dim radius As Double
    centerPt(0) = points(0) + (points(4) - points(0)) / 2
    centerPt(1) = points(3)
    centerPt(2) = 0
    radius = gTextSize / 3
    Set circleObj = ThisDrawing.ModelSpace.AddCircle(centerPt, radius)
    
      
    ' 找尋線與圓的交點
    Dim intPoints As Variant
    Dim intPtLeft(0 To 2) As Double
    Dim intPtRight(0 To 2) As Double
    intPoints = plineTuplet.IntersectWith(circleObj, acExtendNone)


    Dim Pts As New PointList
    Dim ip As point
'    ' Print all the intersection points
    Dim i As Integer, j As Integer, k As Integer
'    Dim str As String
    If VarType(intPoints) <> vbEmpty Then
        For i = LBound(intPoints) To UBound(intPoints)
            Set ip = New point
            ip.x = intPoints(j)
            ip.y = intPoints(j + 1)
            ip.Z = intPoints(j + 2)
            Pts.Push ip
            i = i + 2
            j = j + 3
            k = k + 1
        Next
    End If
    
    Dim tmpPt As New point
    
    '取得2個交點才是對的
    If (Pts.Count = 2) Then
        '排序
        If (Pts(0).x > Pts(1).x) Then
            Set tmpPt = Pts(0)
             Pts(0) = Pts(1)
             Pts(1) = tmpPt
        End If
        
        plineTuplet.Delete
        circleObj.Delete
    
        Dim lo_Tuplet As AcadLWPolyline
        Dim ro_Tuplet As AcadLWPolyline
        Dim pt_list(0 To 5) As Double
        pt_list(0) = points(0): pt_list(1) = points(1)
        pt_list(2) = points(2): pt_list(3) = points(3)
        pt_list(4) = Pts(0).x
        pt_list(5) = Pts(0).y
        Set lo_Tuplet = ThisDrawing.ModelSpace.AddLightWeightPolyline(pt_list)
        
        pt_list(0) = Pts(1).x
        pt_list(1) = Pts(1).y
        pt_list(2) = points(4): pt_list(3) = points(5)
        pt_list(4) = points(6): pt_list(5) = points(7)
        Set ro_Tuplet = ThisDrawing.ModelSpace.AddLightWeightPolyline(pt_list)
        
        lo_Tuplet.ConstantWidth = 0.15
        lo_Tuplet.Layer = "fige"
        ro_Tuplet.ConstantWidth = 0.15
        ro_Tuplet.Layer = "fige"
        
        '寫上數字
        Dim textObj As AcadText
        Dim textString As String
        Dim insertionPoint(0 To 2) As Double
        Dim height As Double
        
        ' Define the text object
        textString = count_tuplet
        insertionPoint(0) = 0: insertionPoint(1) = 0: insertionPoint(2) = 0
        height = 0.63 * gTextSize
        
        ' Create the text object in model space
        Set textObj = ThisDrawing.ModelSpace.AddText(textString, insertionPoint, height)
        textObj.Alignment = acAlignmentMiddleCenter
        textObj.Move insertionPoint, centerPt
        textObj.styleName = "音符_數字"
        textObj.Layer = "TEXT"
        
        
        Set drawTuplet = lo_Tuplet
    Else
        circleObj.Delete
        
        plineTuplet.setWidth 0, 0.15, 0.15
        plineTuplet.setWidth 1, 0.15, 0.15
        plineTuplet.setWidth 2, 0.15, 0.15
        
        plineTuplet.Layer = "fige"
        
        color.ColorIndex = 3
        plineTuplet.TrueColor = color
        plineTuplet.Update
                        
        Set drawTuplet = plineTuplet
    End If
       
    
       
       
End Function
Public Function drawBlockItem(blockName As String, x As Double, y As Double, Optional size As Double = 1, _
    Optional dx As Double = 0, Optional dy As Double = 0, _
    Optional scX As Double = 1, Optional scY As Double = 1, Optional scZ As Double = 1)
    '繪 圖塊
    Dim textObj As AcadText
    Dim blockRefObj  As AcadBlockReference
    Dim textString As String
    Dim aligPoint(0 To 2) As Double
    
    aligPoint(0) = x + (size * dx)
    aligPoint(1) = y + (size * dy)
    aligPoint(2) = 0
    
    If checkBlockName(blockName) Then
        Set drawBlockItem = ThisDrawing.ModelSpace.InsertBlock(aligPoint, blockName, size * scX, size * scY, size * scZ, 0)
        drawBlockItem.Layer = nowPartLayer
    Else
        If blockName = "" Then blockName = " "
        Set drawBlockItem = ThisDrawing.ModelSpace.AddText(blockName, aligPoint, size)
    End If
End Function

Public Function draw_Scale(isOneItem As Boolean, iScale As Integer, iTempo As Integer, x As Double, y As Double, Optional fontsize As Double = 1, Optional scY As Double = 1) As Double
    '繪 高低音
    'isOneItem 是否是第一個元素
    'iScale
    '
    '
    '
    Dim mX As Double
    Dim mY As Double
    Dim txtScale As String
    Dim topAdd As Double
    Dim sbottmAdd As Double
    If iScale = 0 Then
        draw_Scale = y + fontsize * scY + 0.2
        Exit Function
    End If
    
    If iScale < 0 Then
        Select Case iScale           ' Evaluate Number.
            Case -1
                txtScale = "M-OCTAVEa"
                sbottmAdd = 0.1
                topAdd = 0.1 + 0.2
            Case -2
                txtScale = "M-OCTAVEb"
                sbottmAdd = 0.4
                topAdd = 0.4 + 0.2
            Case -3
                txtScale = "M-OCTAVEc"
                sbottmAdd = 0.4
                topAdd = 0.4 + 0.2
            Case Else
                txtScale = "M-OCTAVEa"
                sbottmAdd = 0.1
                topAdd = 0.1 + 0.2
        End Select
        
        If isOneItem = True Then
            '有線時 iTempo >1 要下去的距離
            
            mY = -(amt.DROP_ADD_LINE_INTERVAL * iTempo)
            mY = mY - 0.2
            
            Call drawBlockItem(txtScale, x, y, gTextSize, 0, mY)
            draw_Scale = y + fontsize * scY + 0.2 * gTextSize
            
        Else
        '不是第一個
            mY = sbottmAdd
            Call drawBlockItem(txtScale, x, y, gTextSize, 0, mY)
            
            draw_Scale = y + topAdd * gTextSize
            
        End If
    

    
    ElseIf iScale > 0 Then
    'M-OCTAVE1
    'M-OCTAVE2
    'M-OCTAVE3
        mY = fontsize * scY + 0.2 * gTextSize
        Select Case iScale    ' Evaluate Number.
            Case 1
                txtScale = "M-OCTAVE1"
                topAdd = 0.2
            Case 2
                txtScale = "M-OCTAVE2"
                topAdd = 0.5
            Case 3
                txtScale = "M-OCTAVE3"
                topAdd = 0.5
            Case Else
                txtScale = "M-OCTAVE1"
                topAdd = 0.2
        End Select
        Call drawBlockItem(txtScale, x, y + mY, gTextSize)
        
        mY = y + mY + topAdd * gTextSize
        draw_Scale = mY
    End If
    
End Function
Public Function InsterRest() As AcadBlockReference '插入 Rest
    Dim x As Double, y As Double, Z As Double
    Dim lastOctave As Integer
    Dim scY As Double
    Dim bottomY As Double
    
    x = Grippt.gptMid.x
    y = Grippt.gptMid.y
    Z = Grippt.gptMid.Z
        '寫上數字
    Dim textObj As AcadText
    Dim textString As String
    Dim insertionPoint(0 To 2) As Double
    Dim centerPt(0 To 2) As Double
    Dim height As Double
    

    insertionPoint(0) = 0: insertionPoint(1) = 0: insertionPoint(2) = 0
    height = 0.63 * gTextSize
    centerPt(0) = x: centerPt(1) = y: centerPt(2) = 0
    ' Create the text object in model space
    Set textObj = ThisDrawing.ModelSpace.AddText(MData.rest.text, insertionPoint, height)
    textObj.Alignment = acAlignmentMiddleCenter
    textObj.Move insertionPoint, centerPt   'bug 還要移動 1 次
    textObj.styleName = "音符_數字"
    textObj.Layer = "TEXT"
    
    
End Function


Public Function InsterEnt() As AcadBlockReference '插入音附
    Dim textObj As AcadText
    Dim blockRefObj  As AcadBlockReference
    Dim textString As String
    Dim aligPoint(0 To 2) As Double
    Dim height As Double
    Dim insertionPoint(0 To 2) As Double
    
    
    Dim varAttributes As Variant
    Dim entObj As AcadEntity
    Dim pickPnt As Variant
    Dim blkRefObj As AcadBlockReference
    Dim i As Integer
    Dim TheObj As AcadEntity
    Dim towPos As Double
    Dim cc As String
    Dim mX As Double
    Dim mY As Double
    Dim mItem As MusicFing
    Dim ItemCount As Integer
    Dim currentY As Double
    Dim x As Double, y As Double, Z As Double
    Dim lastOctave As Integer
    Dim scY As Double
    Dim bottomY As Double
    
    x = Grippt.gptMid.x
    y = Grippt.gptMid.y
    Z = Grippt.gptMid.Z
    currentY = 0
    For ItemCount = 0 To UBound(MFS)
        mItem = MFS(ItemCount)
        If mItem.sNote <> "" Then
        If UBound(MFS) > 1 Then
         cc = cc
         End If
        
        '設訂疊音的 y 軸比例
        
        If UBound(MFS) >= 3 Then
            scY = 0.6
        ElseIf UBound(MFS) >= 2 Then
            scY = 0.7
        ElseIf UBound(MFS) >= 1 Then
            scY = 1
        Else
            scY = 1
        End If
        

        
'            mX = 0: mY = 0
'                If mItem.iScale <= 0 Then
'                    If ItemCount >= 1 Then
'                        lastOctave = lastOctave + Abs(mItem.iScale)
'                        mY = -0.2
'                    ElseIf mItem.iTempo >= 1 Then    '下點音附 要移下去一些
'                        '有線時 要下去的距離
'                        mX = 0
'                        mY = -(amt.DROP_ADD_LINE_INTERVAL * mItem.iTempo)
'                        mY = mY - 0.2
'                    Else
'                        mY = -0.2 * scY
'                    End If
'                Else
'                    mY = (mY + 1 + 0.2)
'                End If
'
'                If ItemCount > 0 Then
'                    If lastOctave > 0 Then
'                        y = y + (lastOctave * 0.3) * gTextSize - (lastOctave * 0.3) * gTextSize * (1 - scY)
'                    End If
'                    y = y + 1.1 * gTextSize - gTextSize * (1 - scY)
'                End If
'            If mItem.sScale <> "" Then
'                '  x  y 是音符的位置
'                ' mX mY 是高低音位移的位置
'                Call drawBlockItem(mItem.sScale, x, y, gTextSize, mX, mY)
'            End If
            
            '計算多音符的 y 軸移動
            If ItemCount = 0 Then lastOctave = 0
        
        
            '繪主音
            'Y = Y + (gTextSize * itemCount) + totalOctave
        mX = 0: mY = 0
'        If ItemCount = 0 Then
'            '只取得合音的第一個
'            Set TheObj = drawBlockItem(mItem.sNote, x, y, gTextSize, 0, 0, 1, scY, 1)
'        Else
'             Set TheObj = drawBlockItem(mItem.sNote, x, bottomY, gTextSize, 0, 0, 1, scY, 1)
'        End If
'
        
        
        If mItem.iScale < 0 Then
            If ItemCount = 0 Then
                bottomY = Me.draw_Scale(True, mItem.iScale, mItem.iTempo, x, y, gTextSize, scY)
                Set TheObj = drawBlockItem(mItem.sNote, x, y, gTextSize, 0, 0, 1, scY, 1)
                bottomY = Me.draw_Scale(True, 0, mItem.iTempo, x, y, gTextSize, scY)
            Else
                '計算高低音點後的 文字 y 位置
                bottomY = Me.draw_Scale(False, mItem.iScale, mItem.iTempo, x, bottomY, gTextSize, scY)
                Set TheObj = drawBlockItem(mItem.sNote, x, bottomY, gTextSize, 0, 0, 1, scY, 1)
                bottomY = Me.draw_Scale(False, 0, mItem.iTempo, x, bottomY, gTextSize, scY)
            End If
        Else
            If ItemCount = 0 Then
                Set TheObj = drawBlockItem(mItem.sNote, x, y, gTextSize, 0, 0, 1, scY, 1)
                bottomY = Me.draw_Scale(True, mItem.iScale, mItem.iTempo, x, y, gTextSize, scY)
            Else
                Set TheObj = drawBlockItem(mItem.sNote, x, bottomY, gTextSize, 0, 0, 1, scY, 1)
                '計算高低音點後的 文字 y 位置
                bottomY = Me.draw_Scale(False, mItem.iScale, mItem.iTempo, x, bottomY, gTextSize, scY)
            End If
        
        End If
            
            '繪負點音符
            If (MData.dots > 0) Then
                Call drawBlockItem("M-NOTE.", x + (amt.wNote * gTextSize), y, gTextSize, mX, mY)
            End If
            
            If mItem.iScale > 0 Then   '低八度的點
                lastOctave = mItem.iScale
            Else
                lastOctave = 0
            End If
            
            
            '升降記號
            Dim objPT As Variant
            Dim ptY As Double
            objPT = TheObj.insertionPoint
            ptY = objPT(1)
            Call drawBlockItem(mItem.sTONE, x, ptY, gTextSize, 0, 0)
        
            
            If frmEDIT.chkOption1.value = True Then
                '古箏指法 1
                mX = mItem.mfPosition.x
                mY = mItem.mfPosition.y
                Call drawBlockItem(mItem.sFinge, x, y, gTextSize, mX, mY)
                
                '古箏指法 2
                towPos = 0
                If mItem.sTowFinge <> "" Then
                    
                    mX = mItem.mfTowPosition.x
                    mY = mItem.mfTowPosition.y
                    
                    '減 拍線
                    towPos = (amt.DROP_ADD_LINE_INTERVAL * mItem.iTempo)
                    If mItem.iScale < 0 Then
                        '減 下點音附
                        towPos = towPos + (amt.DROP_INTERVAL * (-mItem.iScale))
                    End If
                    If towPos > 0.3 Then
                        mY = mY - towPos
                    Else
                        mY = mY - 0.3
                    End If
                    
                    Call drawBlockItem(mItem.sTowFinge, x, y, gTextSize, mX, mY)
                    
                End If
                
                
            '*****畫特疏指法*******************************************
                If mItem.sTONE = "*" Then
                    InsertMusicStar insertionPoint, gTextSize
                End If
    
                
            ElseIf frmEDIT.chkOption2.value = True Then
                '二胡指法用
                
                
            End If
            
            '寫入屬性
            '本段代碼從選中的圖塊中獲取屬性值，並對其修改
    
            
            BlockReferenceSetMusicData TheObj, MData.notes(ItemCount)
            Set InsterEnt = TheObj
            
                
            
        End If
    Next
    '繪前綴元素
    Dim extMBG As New MusicBlockGraphics
    Dim extra As New MusicItem
    Dim startPt As New point
    
    Dim beamMIList As New MusicItemList
    
    If Not MData.extraObjs Is Nothing Then
        For i = 0 To MData.extraObjs.Count - 1
            startPt.x = gAtPt.x - (Me.TextSize * amt.extraScale * amt.wNote * (MData.extraObjs.Count - i))
            startPt.y = gAtPt.y + Me.TextSize * 1.2
'            Set extra = New MusicItem
'            Set extra.notes = New MusicNoteItemList
'            extra.notes.Push MData.extraObjs(i)
            Set extra = MData.extraObjs(i).ToOneMusicItem
            extra.oX = startPt.x
            extra.oY = startPt.y
            extMBG.setDataText startPt, extra, Me.TextSize * amt.extraScale
            extMBG.nowPartLayer = nowPartLayer
            extMBG.InsterEnt '插入音符及指法
            beamMIList.Push extra
        Next
        extMBG.draw_dur beamMIList
        beamMIList.Clear
    End If
    '繪後綴元素
    If Not MData.rightObjs Is Nothing Then
        For i = 0 To MData.rightObjs.Count - 1
            startPt.x = Grippt.gptRight.x + (Me.TextSize * amt.extraScale * amt.wNote * (i))
            startPt.y = gAtPt.y + Me.TextSize * 1.2
'            Set extra = New MusicItem
'            Set extra.notes = New MusicNoteItemList
'            extra.notes.Push MData.rightObjs(i)
            Set extra = MData.rightObjs(i).ToOneMusicItem
            extra.oX = startPt.x
            extra.oY = startPt.y
            extMBG.setDataText startPt, extra, Me.TextSize * amt.extraScale
            extMBG.nowPartLayer = nowPartLayer
            extMBG.InsterEnt '插入音符及指法
            beamMIList.Push extra
        Next
        extMBG.draw_dur beamMIList
        beamMIList.Clear
    
    End If
    
End Function

Private Sub BlockReferenceSetMusicData(TheObj, note1 As MusicNoteItem)
    Dim blkRefObj As AcadBlockReference
    Dim attVars As Variant
    Dim i As Integer
    If TheObj.objectName = "AcDbBlockReference" Then
        '如果選擇的是塊引用，將其賦給塊引用對象
        Set blkRefObj = TheObj
        '判斷該塊引用是否含有屬性值
        If blkRefObj.HasAttributes Then
            'MsgBox "你選擇的圖塊沒有塊屬性，程序將退出！"
            '如果不含由屬性值退出
    
        '獲取塊引用中的塊屬性對象
        attVars = blkRefObj.GetAttributes
        '對塊屬性對象進行遍歷
            For i = LBound(attVars) To UBound(attVars)
        '       MsgBox "第" & I + 1 & "屬性對象的屬性值分別如下：" & Chr(13) & Chr(13) & _
        '               "屬性標籤為：" & attVars(I).TagString & Chr(13) & _
        '               "屬性值為：" & attVars(I).textString
                '將塊屬性的標籤和值進行修改
                Select Case attVars(i).TagString
                    Case "ITONE"
                        attVars(i).textString = IIf(IsEmpty(note1.mtone), "", note1.mtone)
                    Case "IFINGE"
                        attVars(i).textString = IIf(IsEmpty(note1.mfingering), "", note1.mfingering)
                    Case "ISCALE"
                        attVars(i).textString = IIf(IsEmpty(note1.mscale), "", note1.mscale)
                    Case "INOTE"
                        attVars(i).textString = IIf(IsEmpty(note1.mnote), "", note1.mnote)
                    Case "ITEMPO"
                        '取得關鍵字 拍子  -=368acefz amt.iTempo
                        attVars(i).textString = IIf(IsEmpty(note1.mtempo), "", note1.mtempo)
                    Case "ITOWFINGE"
                        attVars(i).textString = IIf(IsEmpty(note1.mtow_fingering), "", note1.mtow_fingering)
                    Case "ISLUR"
                        attVars(i).textString = IIf(IsEmpty(MData.slurStart), "", MData.slurStart)
                    Case "IRE1"
                    Case Else
                End Select
            Next
            
        End If
    End If
End Sub

Private Function Tempo_c2line(theC As String) As Integer
'拍子的 字元 轉 成幾條線

    
    Dim tempo_hj As String
    Dim tempo_val As Variant
    Dim tempo_ll As Variant
    
    tempo_hj = " -2=45368aAcCfFgGzZ"
    tempo_ll = Array(1, 2, 2, 4, 4, 5, 3, 6, 8, 10, 10, 12, 12, 15, 15, 16, 32, 32)
    tempo_val = Array(0, 1, 1, 2, 2, 2, 2, 2, 3, 3, 3, 4, 4, 4, 4, 4, 4, 4, 4)
    

    Dim ii As Integer
    Dim cn As String
    If theC <> "" Then
    
    For ii = 0 To Len(tempo_hj) - 1
        cn = Mid(tempo_hj, ii + 1, 1)
        If cn = Mid(theC, 1, 1) Then
            Tempo_c2line = tempo_val(ii)
            Exit Function

        End If
    Next ii
    
    End If
    Tempo_c2line = 0
End Function

Private Function Tempo_c2number(cc As String) As Double
'拍子的 字元 轉成 時值

    
    Dim tempo_hj As String
    Dim tempo_val As Variant
    Dim tempo_ll As Variant
    
    tempo_hj = " -2=45368aAcCfFgGzZ"
    tempo_ll = Array(1, 2, 2, 4, 4, 5, 3, 6, 8, 10, 10, 12, 12, 15, 15, 16, 16, 32, 32)
    tempo_val = Array(0, 1, 1, 2, 2, 2, 2, 2, 3, 3, 3, 4, 4, 4, 4, 4, 4, 4, 4)
    

    Dim ii As Integer
    Dim cn As String
    For ii = 0 To Len(tempo_hj) - 1
        cn = Mid(tempo_hj, ii + 1, 1)
        If cn = Mid(theC, 1, 1) Then
            Tempo_c2line = tempo_ll(ii)
            Exit Function
        End If
    Next ii
    Tempo_c2line = 0
End Function




Public Function addMusicJoin(ByVal the_Ids As iArray)

'取得物件 MusicText
'用x 軸來鏈結
On Error Resume Next

    Dim ent As Object
    
    '排序陣列
    Dim TheArray As New iArray
    Dim TheArrayEnt As New iArray
    'Dim coI As Integer
    Dim i As Long
    TheArray.Clear
    TheArrayEnt.Clear
    ' Add the dimstyle to the dimstyles collection

  ' 找出圖面中的每一個選集
'    For i = 0 To the_Ids.Count - 1
'        If the_Ids(i).objectName = "AcDbBlockReference" Then
'            coI = coI + 1
'        End If
'    Next

    

    
    'ReDim TheArray(coI - 1)
    'ReDim TheArrayEnt(coI - 1)
    
    
    'Dim MTobj As NnmText
    Dim pt As Variant
    
    For i = 0 To the_Ids.Count - 1
        Set ent = the_Ids(i)
        If (Mid(ent.Name, 1, 6) = "M-NOTE") Then
            pt = ent.insertionPoint()
            TheArray.Push pt(0)
            TheArrayEnt.Push ent
                       
            
            Dim minExt As Variant
            Dim maxExt As Variant
    
            ent.GetBoundingBox minExt, maxExt
            'Set MTobj = ent
            'minExt = MTobj.GripLeft()
            
        End If
    Next
    
    
    '只有一個，不用排序了
    If the_Ids.Count > 1 Then
        SelectionSortMaxTow TheArray.ToList, TheArrayEnt.ToList

    End If
    '排序開始
    
    
    Dim stPt As point
    Dim endPt As point
    Dim tempo_num(0 To 20) As Integer
    Dim ptTheArr(0 To 20) As point
    Dim cIT As String
    Dim insertionPoint As Variant
    Dim entArr As AcadEntity
    
    Set stPt = New point
    Set endPt = New point
    
    '取得拍子的線條數量及 物件位置
    For i = 0 To TheArray.Count - 1
        Set entArr = TheArrayEnt(i)
        cIT = GetAttribTextString(entArr, "ITEMPO")
        
        tempo_num(i) = Tempo_c2line(cIT)
        insertionPoint = TheArrayEnt(i).insertionPoint
        Set ptTheArr(i) = New point
        ptTheArr(i).c insertionPoint(0), insertionPoint(1), insertionPoint(2)
    Next
    
    

    Dim x As Integer
'    for (int x =1  x<=the_lineOne  x++)
    For x = 1 To 4
        For i = 0 To TheArray.Count - 1
            If tempo_num(i) >= x Then
                If stPt.x = 0 Then
                    Set stPt = ptTheArr(i).clone '取得第一個位置
                Else
                    Set endPt = ptTheArr(i).clone '取得第 後面的位置
                End If
                If i = TheArray.Count - 1 Then '如是最後一個就畫出來
                    If endPt.x = 0 Then
                        Set endPt = stPt.clone
                    End If
                    line_link x - 1, stPt, endPt
                    stPt.c 0, 0, 0
                    endPt.c 0, 0, 0
                End If
            Else
                If stPt.x <> 0 Then
                    If endPt.x = 0 Then
                        Set endPt = stPt.clone
                    End If
                    line_link x - 1, stPt, endPt
                    stPt.c 0, 0, 0
                    endPt.c 0, 0, 0
                    
                End If
            
            End If
        Next
    Next
            



EndJoin:
End Function
Public Function draw_dur(musicList As MusicItemList)
    ''繪製下拍線
    Dim N As Integer
    Dim n2 As Integer
    Dim i As Integer
    Dim sst As MusicItem
    Dim sEnd As MusicItem
    Dim stPt As New point
    Dim endPt As New point
    '取得最大的  nflags
    For i = 0 To musicList.Count - 1
        If n2 < musicList(i).nflags Then
            n2 = musicList(i).nflags
        End If
    Next
    
    '開始繪下拍線
    Dim x As Integer
'    for (int x =1  x<=the_lineOne  x++)
    For N = 1 To n2
        For i = 0 To musicList.Count - 1
            If musicList(i).nflags >= N Then
                If sst Is Nothing Then
                    Set sst = musicList(i) '取得第一個位置
                Else
                    Set sEnd = musicList(i) '取得第 後面的位置
                End If
            Else
                If Not sst Is Nothing Then
                    If sEnd Is Nothing Then
                        Set sEnd = sst
                    End If
                    line_link N, sst, sEnd
                    Set sst = Nothing
                    Set sEnd = Nothing
                    
                End If
            
            End If
        Next
        If Not sst Is Nothing Then
            If sEnd Is Nothing Then
                Set sEnd = sst
            End If
            line_link N, sst, sEnd
            Set sst = Nothing
            Set sEnd = Nothing
            
        End If
    Next

End Function

'
'''畫拍子的線
''' num_col   要畫幾個線
''' l_pt, r_pt  左右鏈結的中點

Sub line_link(num_col As Integer, s1 As MusicItem, s2 As MusicItem)

    If num_col <= 0 Then
        Exit Sub
    End If

    Dim xt As Double
    Dim yt As Double

    Dim plineObj As AcadPolyline
    Dim points(0 To 5) As Double

    ' Define the 2D polyline points
    points(0) = s1.oX
    points(1) = s1.oY + (amt.bkMidHight * gTextSize) - (num_col * amt.LINE_JUMP * gTextSize)
    points(2) = 0


    points(3) = s2.oX + amt.A_TEXT_WIDTH * gTextSize
    points(4) = points(1)
    points(5) = 0


    ' Create a lightweight Polyline object in model space
    Set plineObj = ThisDrawing.ModelSpace.AddPolyline(points)
    plineObj.ConstantWidth = gTextSize * amt.LINE_THICKNESS
    plineObj.Layer = nowPartLayer
    'Call ThisDrawing.ModelSpace.AddPolyline .InsertBlock(insertionPoint, MFS.sFinge, gTextSize, gTextSize, gTextSize, 0)

End Sub



'
'''畫拍子的線
''' num_col   要畫幾個線
''' l_pt, r_pt  左右鏈結的中點

'Sub line_link(num_col As Integer, lPt As point, rPt As point)
'
'    If num_col < 0 Then
'        Exit Sub
'    End If
'
'    Dim xt As Double
'    Dim yt As Double
'
'    Dim plineObj As AcadPolyline
'    Dim points(0 To 5) As Double
'
'    ' Define the 2D polyline points
'    points(0) = lPt.x - amt.A_TEXT_WIDTH / 2 * gTextSize
'    points(1) = lPt.y - (amt.bkInster_Line_H * gTextSize) - (num_col * amt.LINE_JUMP * gTextSize)
'    points(2) = lPt.Z
'
'
'    points(3) = rPt.x + amt.A_TEXT_WIDTH / 2 * gTextSize
'    points(4) = points(1)
'    points(5) = rPt.Z
'
'    ' Create a lightweight Polyline object in model space
'    Set plineObj = ThisDrawing.ModelSpace.AddPolyline(points)
'    plineObj.setWidth 0, gTextSize * amt.LINE_THICKNESS, gTextSize * amt.LINE_THICKNESS
'    plineObj.Layer = MAINLAYER
'    'Call ThisDrawing.ModelSpace.AddPolyline .InsertBlock(insertionPoint, MFS.sFinge, gTextSize, gTextSize, gTextSize, 0)
'
'End Sub

Private Function InsertMusicStar(insertionPoint() As Double, size As Double)
'插入古箏 前音 琵音 * 號
'insertionPoint  是本音符的位置

    
    Dim textObj As AcadText
    Dim blockRefObj  As AcadBlockReference
    Dim textString As String
    Dim alignmentPoint(0 To 2) As Double
    Dim midDownPt(0 To 2) As Double
    Dim height As Double
        
    
    
    Dim xStar As Double
    Dim yStar As Double
    Dim ssize As Double
    xStar = -1.06 '星指法的 X 上增量
    yStar = 1.3 '星指法的 Y 上增量
    ssize = 0.65 '小字的比例
    

    alignmentPoint(0) = insertionPoint(0) + (size * xStar)
    alignmentPoint(1) = insertionPoint(1) + (size * yStar)
    alignmentPoint(2) = insertionPoint(2)

    
    midDownPt(0) = alignmentPoint(0) + (amt.A_TEXT_WIDTH / 2 * size * ssize)
    midDownPt(1) = alignmentPoint(1)
    midDownPt(2) = alignmentPoint(2)


'*******畫星字*****************
    
    Set blockRefObj = ThisDrawing.ModelSpace.InsertBlock(midDownPt, "M-NOTESTAR", size, size, size, 0)
    blockRefObj.Layer = "裝飾符號"
    
'*******畫拍線*****************
    Dim sMGB As New MusicBlockGraphics
    Dim ppt As New point
    Dim lPt As New point
    Dim rPt As New point
    
    sMGB.setDataText ppt, "", size * ssize
    
        
    lPt.x = midDownPt(0)
    lPt.y = midDownPt(1) + (0.15 * size * ssize)
    lPt.Z = midDownPt(2)
    
    rPt.x = lPt.x
    rPt.y = lPt.y
    rPt.Z = lPt.Z

    sMGB.line_link 1, lPt, rPt
    sMGB.line_link 2, lPt, rPt
    
'*******畫弧*****************
      
    Dim arcObj As AcadArc
    Dim centerPoint(0 To 2) As Double
    Dim radius As Double
    Dim startAngleInDegree As Double
    Dim endAngleInDegree As Double
    
    ' Define the circle
    
    radius = 0.38 * size * ssize
    centerPoint(0) = midDownPt(0) + radius
    centerPoint(1) = midDownPt(1) - 0.3 * size * ssize
    centerPoint(2) = midDownPt(2)
    startAngleInDegree = 180#
    endAngleInDegree = 275#
    
    ' Convert the angles in degrees to angles in radians
    Dim startAngleInRadian As Double
    Dim endAngleInRadian As Double
    startAngleInRadian = startAngleInDegree * 3.141592 / 180#
    endAngleInRadian = endAngleInDegree * 3.141592 / 180#
    
    ' Create the arc object in model space
    Set arcObj = ThisDrawing.ModelSpace.AddArc(centerPoint, radius, startAngleInRadian, endAngleInRadian)
    arcObj.Layer = "裝飾符號"
    
End Function


Private Sub linkGrapTempoMaray(the_lineOne As Integer)
    '畫拍子聯結
    'pW
    'lineOne 是要看，現在是第幾條線
    
'    MusicData tmp_md = this->m_MusicData
'
'    string cst
'    cst += "MT::linkGrapTempoMaray"
'    cst += tmp_md.strNnmTextData
'
'    LOG1W(cst.c_str(),(long )__LINE__)
'
'
'    AcGePoint3d stPt, endPt
'    stPt = AcGePoint3d(0,0,0)
'    endPt = AcGePoint3d(0,0,0)
'
'    MusicText *tmp_objMTXT
'
'    deque<structMT> sDeque
'    deque<structMT>::iterator  tmp_iterSDeque
'
'    ''mapData::iterator pos
'
'    structMT tmp_sMT
'    ''Acad::ErrorStatus es
'
'    tmp_sMT.pt = tmp_md.point_
'    tmp_sMT.m_tempo = tmp_md.tempo
'
'    sDeque.push_back(tmp_sMT)
'
'
'    if (tmp_md.LlinkobjId != NULL)
'    {
'        return
'    }
'    else if (tmp_md.RlinkobjId != NULL)
'    {
'        while(tmp_md.RlinkobjId != NULL )
'        {
'
'            if (acdbOpenObject((AcDbObject*&)tmp_objMTXT, tmp_md.RlinkobjId,
'                AcDb::kForWrite) == Acad::eOk)
'            {
'
'                tmp_md = tmp_objMTXT->m_MusicData
'
'                tmp_sMT.pt = tmp_md.point_
'                tmp_sMT.m_tempo = tmp_md.tempo
'
'                sDeque.push_back(tmp_sMT)
'                tmp_objMTXT->close()
'            }
'            Else
'            {
'
'                cst = ""
'                cst += "未取得 id- pu438"
'                LOG1W(cst.c_str(),(long )__LINE__)
'
'                acutPrintf( "\n 未取得 id- pu438" )
'                tmp_md.RlinkobjId = NULL
'
'            }
'        }
'    }
'
'    LOG1W(cst.c_str(),(long )__LINE__)
'
'    for (int x =1  x<=the_lineOne  x++)
'    {
'        for( tmp_iterSDeque = sDeque.begin()  tmp_iterSDeque != sDeque.end()  tmp_iterSDeque++)
'        {
'            if(((*tmp_iterSDeque).m_tempo) >= x)
'            {
'                if(stPt.x == 0)
'                {
'                    stPt = (*tmp_iterSDeque).pt     ''取得第一個位置
'                }
'                Else
'                {
'                    endPt = (*tmp_iterSDeque).pt    ''取得第後面的位置
'                }
'                if(tmp_iterSDeque == (sDeque.end()-1))''如是最後一個就畫出來
'                {
'                    if (endPt.x == 0)
'                    {
'                        endPt = stPt
'                    }
'                    m_pGObject->line_link(pW, x-1, stPt, endPt)
'                    stPt = AcGePoint3d(0,0,0)
'                    endPt = AcGePoint3d(0,0,0)
'                }
'
'            }
'            Else
'            {
'                if(stPt.x != 0)
'                {
'                    if (endPt.x == 0)
'                    {
'                        endPt = stPt
'                    }
'                    m_pGObject->line_link(pW, x-1, stPt, endPt)
'                    stPt = AcGePoint3d(0,0,0)
'                    endPt = AcGePoint3d(0,0,0)
'                }
'            }
'        }
'    }
'
'
'}

End Sub
Public Function insterPositionBox(insterPt As point, G As Glode, Optional layerName As String = "Defpoints")
'插入定位框
    Dim plineObj As AcadPolyline
    Dim Pnt As New PointList
    Dim ip As New point
    ip = insterPt
    Pnt.Push ip.c(insterPt.x, insterPt.y - 200, 0).clone
    Pnt.Push ip.c(insterPt.x, insterPt.y + G.fontsize * 9, 0).clone
    Pnt.Push ip.c(insterPt.x + G.pagewidth, insterPt.y + G.fontsize * 9, 0).clone
    Pnt.Push ip.c(insterPt.x + G.pagewidth, insterPt.y - 200, 0).clone
    
'    Call Pnt.Push(.Add(insterPt.X, insterPt.Y - 200, 0)
'    Call Pnt.Add(insterPt.X, insterPt.Y + G.FontSize * 9, 0)
'    Call Pnt.Add(insterPt.X + G.PageWidth, insterPt.Y + G.FontSize * 9, 0)
'    Call Pnt.Add(insterPt.X + G.PageWidth, insterPt.Y - 200, 0)

    Set plineObj = ThisDrawing.ModelSpace.AddPolyline(Pnt.ToXYZList)
    plineObj.Layer = "Defpoints"
    Set insterPositionBox = plineObj
End Function

   
Public Sub setVirtualChar(isVirtualChar As Boolean)

    Dim kNUM1 As String, kNUM2 As String, kNUM3 As String, kNUM4 As String
    Dim kNUM5 As String, kNUM6 As String, kNUM7 As String, kNUM0 As String
    Dim k延長一拍 As String
    Dim kLIN1 As String: Dim kLIN2 As String: Dim kLIN3 As String
    Dim kUP1 As String
    Dim kUP2 As String
    Dim kDOW1 As String
    Dim kDOW2 As String
    Dim kAdot As String
    Dim kBarLine As String
    'Dim kFing(30 To 255) As String
    'Dim posFing(0 To 255) As point
    Dim posLinDown As Variant
    
    
    posLinDown = Array(0, 12, 26, 40)   '這是看低音下點要移多少下去，是當200字型時計算
    
    kNUM1 = ChrW(&H4E52)
    kNUM2 = ChrW(&H4E53)
    kNUM3 = ChrW(&H4E56)
    kNUM4 = ChrW(&H4E58)
    kNUM5 = ChrW(&H4E59)
    kNUM6 = ChrW(&H4E5C)
    kNUM7 = ChrW(&H4E5D)
    kNUM0 = ChrW(&H5D4C)
    k延長一拍 = ChrW(&H5D1F)
    kLIN1 = ChrW(&H5D39): kLIN2 = ChrW(&H5D3A): kLIN3 = ChrW(&H5D3C)
    kUP1 = ChrW(&H66E0): kUP2 = ChrW(&H66E3): kDOW1 = ChrW(&H66E6): kDOW2 = ChrW(&H66E8)
    kAdot = ChrW(&H5D3D)            '符點音符
    kBarLine = ChrW(&H601D)

    
    '要上下移多少
    Dim ip As Integer
    For ip = 0 To 255
        Set posFing(ip) = New point
        Set posTowFing(ip) = New point
    Next
    Dim posFingListCode As New iArray
    Dim posTowFingListCode As New iArray

            
    posFingListCode.Push ("z , -0.363, 1.57, 0") ' z 大指
    posFingListCode.Push ("x , -0.363, 1.65, 0") ' x 食指
    posFingListCode.Push ("c , -0.363, 1.57, 0") ' c 中指
    posFingListCode.Push ("v , -0.363, 1.57, 0") ' v 無名指
    posFingListCode.Push ("a , -0.363, 1.57, 0") ' a 八度
    posFingListCode.Push ("s , -0.363, 1.57, 0") ' s 王字指法
    posFingListCode.Push ("d , -0.363, -0.85,0") ' d 搖指
    posFingListCode.Push ("p , -0.363, -0.01,0") ' p 卜指法
    posFingListCode.Push ("Z , -0.363, 1.57, 0") ' 大寫Z 反大指法
    posFingListCode.Push ("A , -0.363, 1.57, 0") ' 大寫A 反八度
    posFingListCode.Push ("- , -0.363, 1.57, 0") ' - 間一旋
    posFingListCode.Push ("= , -0.363, 1.57, 0") ' = 間二旋
    posFingListCode.Push ("t , -0.363, 1.6, 0 ") ' t 打圓 托勾
    posFingListCode.Push ("@ , -0.363, 1.57, 0") ' w
        
        
    posTowFingListCode.Push ("z, -0.363, -0.7, 0") ' z 大指
    posTowFingListCode.Push ("x, -0.363, -0.7, 0") ' x 食指
    posTowFingListCode.Push ("c, -0.363, -0.7, 0") ' c 中指
    posTowFingListCode.Push ("v, -0.363, -0.7, 0") ' v 無名指
    posTowFingListCode.Push ("a, -0.363, -0.7, 0") ' a 八度
    posTowFingListCode.Push ("s, -0.363, -0.7, 0") ' s 王字指法
    posTowFingListCode.Push ("d, -0.363, -0.85,0") ' d 搖指
    posTowFingListCode.Push ("p, -0.363, -0.01,0") ' p 卜指法
    posTowFingListCode.Push ("Z, -0.363, -0.7, 0") ' 大寫Z 反大指法
    posTowFingListCode.Push ("A, -0.363, -0.7, 0") ' 大寫A 反八度
    posTowFingListCode.Push ("-, -0.363, -0.7, 0") ' - 間一旋
    posTowFingListCode.Push ("=, -0.363, -0.7, 0") ' = 間二旋
    posTowFingListCode.Push ("t, -0.363, -0.7, 0") ' t 打圓 托勾
    posTowFingListCode.Push ("w, -0.363, -0.7, 0") ' m
    posTowFingListCode.Push ("m, -0.363, -0.7, 0") ' w
    posTowFingListCode.Push ("e, -0.363, -0.7, 0") ' w
    posTowFingListCode.Push ("r, -0.363, -0.7, 0") ' w
    posTowFingListCode.Push ("k, -0.363, -0.7, 0") ' w
    posTowFingListCode.Push ("n, -0.363, -0.7, 0") ' w
    posTowFingListCode.Push ("f, -0.363, -0.7, 0") ' w
    posTowFingListCode.Push ("b, -0.363, -0.7, 0") ' w
                       

    Dim sarr As Variant
    Dim i As Integer
    Dim cc As String
    Dim k As Integer
    For i = 0 To posFingListCode.Count - 1
        sarr = Split(posFingListCode(i), ",")
        cc = Mid(Trim(sarr(0)), 1, 1)
        k = Asc(cc)
        '設定空心字符
        If (isVirtualChar) Then
            kFing(k) = "MT" & Format(k, "0000") & "_o"
        Else
            kFing(k) = "MT" & Format(k, "0000")
        End If
        posFing(k).c Trim(sarr(1)), Trim(sarr(2)), Trim(sarr(3))
    Next
        
            
    For i = 0 To posFingListCode.Count - 1
        sarr = Split(posFingListCode(i), ",")
        cc = Mid(Trim(sarr(0)), 1, 1)
        k = Asc(cc)
        '設定空心字符
        If (G.isVirtualChar) Then
            kTowFing(k) = "MT" & Format(k, "0000") & "_o"
        Else
            kTowFing(k) = "MT" & Format(k, "0000")
        End If
        posTowFing(k).c Trim(sarr(1)), Trim(sarr(2)), Trim(sarr(3))
    Next
            
       
    'xnote.0': { d: [['M', 7.16, 0], ['C', 8.98, 0, 10.39, 0.91, 11.41, 2.74], ['C', 12, 3.9, 12.3, 5.37, 12.3, 7.15], ['L', 12.3, 9.42], ['C', 12.3, 10.72, 11.93, 12.13, 11.18, 13.64], ['C', 10.47, 15.19, 9.15, 15.98, 7.21, 16], ['C', 5.61, 15.99, 4.5, 15.61, 3.88, 14.87], ['C', 3.26, 14.13, 2.84, 13.42, 2.62, 12.75], ['C', 2.4, 12.07, 2.24, 11.33, 2.14, 10.51], ['C', 2.05, 9.69, 2, 8.61, 2, 7.26], ['C', 2.05, 5.31, 2.34, 3.85, 2.87, 2.88], ['C', 3.7, 0.99, 5.13, 0.03, 7.16, 0], ['Z']], w: 14, h: 16 },
    'xnote.1': { d: [['M', 6.46, 0], ['L', 8.66, 0], ['L', 8.84, 0.19], ['L', 8.84, 15.8], ['L', 8.66, 16], ['L', 5.37, 16], ['L', 5.17, 15.8], ['L', 5.17, 3.82], ['L', 3.22, 3.82], ['L', 3, 3.65], ['L', 3, 2], ['L', 3.03, 1.97], ['L', 3.25, 1.78], ['C', 4.17, 1.81, 4.85, 1.73, 5.29, 1.56], ['C', 5.72, 1.38, 6.04, 0.91, 6.24, 0.16], ['L', 6.46, 0], ['Z']], w: 14, h: 16 },
  
    

End Sub
   

Private Sub Class_Initialize()
    
    setVirtualChar (G.isVirtualChar)    '設字空心字
    
End Sub

Attribute VB_Name = "MusicItem"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

 Public typs As Cg
 
 Public notes As MusicNoteItemList
 Public rest As aRestItem
    'mfingering As String  '指法
    'mnote As String           '高低音
    'mscale As String          '音階
 Public mtempo As String             '拍子
 Public duration As Double      '拍子的延遲長度
    'mtow_fingering As String  '指法 第二個
 Public accidental As String    '升降記號
 Public a_deco As iArray        '動態指法
 Public slurStart As Boolean           '連音符
 Public slurEnd As Boolean             '連音符
 Public tupletStart As Boolean           '3 連音開始
 Public tupletEnd As Boolean             '3 連音結束
 Public tupletCount As Integer           '是幾連音
 
 Public mand As Boolean                  '記錄合音 true為跟後面一音合音 ,false為沒有
 Public what As Integer                 '記錄一些不一樣的指法
 Public nflags As Integer    '下拍線個數
 Public dots   As Integer    '負點音符個數
 
 
 Public mete As Integer     '拍號設定改變
 Public mete2 As Integer     '拍號設定改變
 Public barsperstaff  As Integer    '設定每行幾小節
 Public setbarstaffid   As Integer   '設定每行幾小節  setbarstaffid 是要第幾小節
 Public setbarstaff   As Integer   '設定每行幾小節  setbarstaff 是設定每行幾小節
 Public barNumber As Integer    '這小節號碼
 Public barlinebreak As Integer '設定第 x 小節強制換行
 Public barpagebreak As Integer '設定第 x 小節強制換頁，小節數重 1 開始
  
 Public ln As Integer       '要記錄讀進來的資料是在文件裡的第幾 "行"
 Public WD As Integer      '要記錄貢進來的資料是在文件要的第幾 "字"
 
 Public x As Double
 Public y As Double
 Public w As Double     '正位的寬度
 Public extce As Double '這是前置的位置
 Public oX As Double   '最終的位置
 Public oY As Double   '最終的位置
 


Public children As RelativeElementList
Public heads As RelativeElementList
Public abcelem As VoiceABC
Public tuneNumber As Integer
Public durationClass As Double

Public minspacing As Double
Public extra As RelativeElementList
Public extraw As Double    '前綴元素的寬度 是負值
Public extraObjs As MusicNoteItemList  '前綴元素
Public rightObjs As MusicNoteItemList  '後綴元素
Public right As RelativeElementList
Public invisible As Boolean
Public bottom As Double
Public top As Double
Public fixed  As vFixedCoords  ' FixedCoords
Public specialY As Dictionary  'SpecialYProperties
Public elemset As iArray  'SVGElement[]
'    counters as  {
'        line as  number
'        measure as  number
'        measureTotal as  number
'        voice as  number
'        note as  number
'    }
Public notePositions As New PointList
Public isClef As Boolean
Public isKeySig As Boolean
Public Beam As BeamElem
Public startChar As Double
Public endChar As Double

Public hint As Boolean
Public startTie As Boolean
Public klass As String
Public remark As String


'/**
' * get head type, dots, flags of note/rest for a duration
' * 取得一段時間內的頭類型、點、音符 / 休息標誌
' */
Public Function identify_Duration(dur_o As Double)
    
    If dur_o <= 0 Then Exit Function
    Dim flags As Integer
    Dim dots As Long
    Dim dur As Long
        dots = 0
        dur = dur_o

    If (dur Mod 12 <> 0) Then
       Debug.Print Me.typs, "Invalid note duration $1", dur
    End If
    
    dur = dur / 12         ''/* see C.BLEN for values */
    If (dur <= 1) Then Debug.Print 1, Me.typs, "Note too short"
    
'    For flags = 5 To 0 Step -1
'        dur = Math.BitMoveRight(dur, 1)
'        If dur And 1 Then Exit For ''找出奇數
'    Next
    flags = 5
    Do While Not dur And 1
        ''找出奇數
        dur = Math.BitMoveRight(dur, 1)
        flags = flags - 1
        ''If dur And 1 Then Exit Do
    Loop
    
    dur = Math.BitMoveRight(dur, 1)
'    If ((dur + 1) And dur) Then
'        if (s.type != C.REST || dur_o != s.p_v.wmeasure)
'            error(0, s, "Non standard note duration $1", dur_o)
'    End If
    While dur > 0
        dots = dots + 1
        dur = Math.BitMoveRight(dur, dots)
    Wend

    flags = flags - dots
    Me.duration = dur_o
    Me.nflags = CInt(flags)
    Me.dots = dots
End Function

Public Function getFixedCoords() As vFixedCoords
    Set getFixedCoords = vFixedCoords
    getFixedCoords.x = Me.x
    getFixedCoords.w = Me.fixed.w
    getFixedCoords.t = Me.fixed.t
    getFixedCoords.B = Me.fixed.B
    
End Function

Public Sub addExtra(extra As RelativeElement)
    '' used for accidentals, multi-measure rest text,
    '' left-side decorations, gracenote heads,
    '' left annotations, gracenote stems.


    Me.fixed.w = Math.max(Me.fixed.w, extra.dx + extra.w)

    Me.fixed.t = Math.max(Me.fixed.t, extra.top)
    
    Me.fixed.B = Math.min(Me.fixed.B, extra.bottom)
    If (extra.dx < Me.extraw) Then Me.extraw = extra.dx
    Me.extra(Me.extra.Count) = extra
    Me.addChild_ extra
End Sub

Public Sub addHead(head As RelativeElement)

    If (head.dx < Me.extraw) Then Me.extraw = head.dx
    Me.heads.Push head
    Me.addRight head
End Sub

Public Sub addRight(right As RelativeElement)


    '' These are the elements that are the fixed part.
    
    Me.fixed.w = Math.max(Me.fixed.w, right.dx + right.w)
    Me.fixed.t = Math.max(Me.fixed.t, right.top)
    Me.fixed.B = Math.min(Me.fixed.B, right.bottom)
    
    '' if (isNaN(me.fixed.t) || isNaN(me.fixed.b))
    ''  debugger
    If (right.dx + right.w > Me.w) Then Me.w = right.dx + right.w
    Me.right.Push right
    Me.addChild_ right

End Sub

Public Sub addFixed(elem As RelativeElement)
    '' used for elements that can't move relative to other elements after they have been placed.
    '' used for ledger lines, bar numbers, debug msgs, clef, key sigs, time sigs
    Me.addChild_ elem

End Sub

Public Sub addFixedX(elem As RelativeElement)
    '' used for elements that can't move horizontally relative to other elements after they have been placed.
    '' used for parts, tempo, decorations
    Me.addChild_ elem

End Sub

Public Sub addCentered(elem As RelativeElement)
    Dim half As Double
    half = elem.w / 2
    If (-half < Me.extraw) Then Me.extraw = -half
    Set Me.extra(Me.extra.Count) = elem
    If (elem.dx + half > Me.w) Then Me.w = elem.dx + half
    Set Me.right(Me.right.Count) = elem
    Me.addChild_ (elem)
End Sub

'Public Sub setLimit(member, child)
'
'
'    if (!child[member]) return
'    if (!me.specialY[member])
'        me.specialY[member] = child[member]
'    Else
'        me.specialY[member] = Math.max(me.specialY[member], child[member])
'End Sub

Public Sub addChild_(child As RelativeElement)
    ''  console.log("Relative:",child)
    Set child.parent = Me
    Me.children.Push child
    Me.pushTop child.top
    Me.pushBottom child.bottom
'    Me.setLimit "tempoHeightAbove", child
'    Me.setLimit "partHeightAbove", child
'    Me.setLimit "volumeHeightAbove", child
'    Me.setLimit "dynamicHeightAbove", child
'    Me.setLimit "endingHeightAbove", child
'    Me.setLimit "chordHeightAbove", child
'    Me.setLimit "lyricHeightAbove", child
'    Me.setLimit "lyricHeightBelow", child
'    Me.setLimit "chordHeightBelow", child
'    Me.setLimit "volumeHeightBelow", child
'    Me.setLimit "dynamicHeightBelow", child
End Sub

Public Sub pushTop(top As Double)

            Me.top = Math.max(top, Me.top)

End Sub
Public Sub pushBottom(bottom As Double)
            Me.bottom = Math.min(Array(bottom, Me.bottom))
End Sub


Public Sub setX(x As Double)
    Dim i As Integer
    Me.x = x
'    For i = 0 To Me.children.Count - 1
'        Me.children(i).setX (x)
'    Next i
End Sub

Public Sub center(before As AbsoluteElement, after As AbsoluteElement)
    '' Used to center whole rests
    Dim Midpoint As Double
    Midpoint = (after.x - before.x) / 2 + before.x
    Me.x = Midpoint - Me.w / 2
    Dim k As Integer
    For k = 0 To Me.children.Length - 1
        Me.children(k).setX (Me.x)
    Next
End Sub

Public Sub setHint()
    Me.hint = True
End Sub

Public Sub highlight(klass, color)
    'highlight.bind(this)(klass, color)
End Sub

Public Sub unhighlight(klass, color)
    'unhighlight.bind(this)(klass, color)
End Sub

Public Sub calMeWidth()

        Select Case Me.typs
           Case Cg.bar:
                Me.w = amt.wBar * G.fontsize
           Case Cg.meter:
                Me.w = amt.wMete * G.fontsize
           Case Cg.rest, Cg.note:
                If Me.dots > 0 Then
                    Me.w = 3 * amt.wNote * G.fontsize
                Else
                    Me.w = amt.wNote * G.fontsize
                End If
           Case Else
        End Select
        '計算後綴寬度
        If Not Me.rightObjs Is Nothing Then
            Me.w = Me.w + Me.rightObjs.Count * G.fontsize * amt.extraScale
        End If

End Sub

Attribute VB_Name = "MusicItemList"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
'MIT License
'
'Copyright (c) 2019-2021 Petr Katerinak
'
'Permission is hereby granted, free of charge, to any person obtaining a copy
'of this software and associated documentation files (the "Software"), to deal
'in the Software without restriction, including without limitation the rights
'to use, copy, modify, merge, publish, distribute, sublicense, and/or sell
'copies of the Software, and to permit persons to whom the Software is
'furnished to do so, subject to the following conditions:
'
'The above copyright notice and this permission notice shall be included in all
'copies or substantial portions of the Software.
'
'THE SOFTWARE IS PROVIDED "AS IS", WITHOUT WARRANTY OF ANY KIND, EXPRESS OR
'IMPLIED, INCLUDING BUT NOT LIMITED TO THE WARRANTIES OF MERCHANTABILITY,
'FITNESS FOR A PARTICULAR PURPOSE AND NONINFRINGEMENT. IN NO EVENT SHALL THE
'AUTHORS OR COPYRIGHT HOLDERS BE LIABLE FOR ANY CLAIM, DAMAGES OR OTHER
'LIABILITY, WHETHER IN AN ACTION OF CONTRACT, TORT OR OTHERWISE, ARISING FROM,
'OUT OF OR IN CONNECTION WITH THE SOFTWARE OR THE USE OR OTHER DEALINGS IN THE
'SOFTWARE.
'
' Version of iArray: 1.0
''修正 元素從 0 開始

Private mainArray As New Collection
Private i As Long ' Counter

' #####################
' #    CONSTRUCTOR    #
' #####################
'Private Sub Class_Initialize()
'  Set mainArray = New Collection
'End Sub

' #####################
' #  Getter / Setter  #
' #####################
'Attribute Element.VB_UserMemId = 0 saved in both procedures

'@DefaultMember
Public Property Get element(ByVal index As Long) As MusicItem
Attribute element.VB_UserMemId = 0
    If index + 1 < 1 Or index + 1 > mainArray.Count Then
        Set element = Nothing
        Exit Property
    End If
    If IsObject(mainArray(index + 1)) = True Then
        Set element = mainArray(index + 1)
    Else
        element = mainArray(index + 1)
    End If

 
End Property

'@DefaultMember
Public Property Let element(ByVal index As Long, ByVal val As MusicItem)
Attribute element.VB_UserMemId = 0
  If index = 0 And mainArray.Count = 0 Then
    Me.Push val
  If index + 1 > mainArray.Count Then
    Dim eMsg As String
    eMsg = IIf(mainArray.Count > 0, _
               "Index (" & index + 1 & ") out of iArray bounds (1-" & mainArray.Count & ")", _
               "iArray doesn't have any indexes")
    err.Raise Number:=9, Description:=eMsg
    Exit Property
  End If
  mainArray.Add val, after:=index + 1
  mainArray.Remove index + 1
End Property

' #############################
' # COMMON COLLECTION METHODS #
' #############################
Public Function Count() As Long
  Count = mainArray.Count
End Function
Public Sub Add(ByVal val As MusicItem, Optional ByVal bef As Variant = Empty, Optional ByVal aft As Variant = Empty)
  If IsEmpty(bef) And IsEmpty(aft) Then
    mainArray.Add val
  ElseIf IsEmpty(bef) Then
    mainArray.Add val, , , aft
  ElseIf IsEmpty(aft) Then
    mainArray.Add val, , bef
  Else
    mainArray.Add val, , bef, aft
  End If
End Sub
Public Sub Remove(index As Long)
  mainArray.Remove index + 1
End Sub

' ####################
' #  PUBLIC METHODS  #
' ####################

'AddAfter
' Adds element after given index.
' {1,2,3} -> index >= 3 -> Push val
' {1,2,3} -> index < 1 -> Unshift val
' {} -> index = any -> Push val
' @param Long index | Index after which will be added an element
' @param Variant val | One element (String, number, ...) to add into iArray
' @return Long | Count of elements inside iArray
Public Function AddAfter(ByVal index As Long, ByVal val As MusicItem) As Long
  If Me.Count < 1 Or index + 1 >= Me.Count Then
    Me.Push val
  ElseIf index + 1 < 1 Then
    Me.Unshift val
  Else
    Me.Add val, aft:=index + 1
  End If
  AddAfter = Me.Count
End Function

'AddArrayAfter
' Adds elements after given index.
' {1,2,3} -> index >= 3 -> PushArray val
' {1,2,3} -> index < 1 -> UnshiftArray val
' {} -> index = any -> PushArray val
' @param Long index | Index after which will be added an element
' @param Variant val | Array() or iArray of elements to add into iArray
' @return Long | Count of elements inside iArray
Public Function AddArrayAfter(ByVal index As Long, ByVal val As Variant) As Long
  If Me.Count < 1 Or index + 1 >= Me.Count Then
    Me.PushArray val
  ElseIf index + 1 < 1 Then
    Me.UnshiftArray val
  Else
    If TypeOf val Is MusicItemList Then
      For i = 0 To val.Count - 1
        Me.Add val(i), aft:=index + 1
        Inc index
      Next i
    Else
      For i = LBound(val) To UBound(val)
        Me.Add val(i), aft:=index + 1
        Inc index
      Next i
    End If
  End If
  AddArrayAfter = Me.Count
End Function

'AddArrayBefore
' Adds elements before given index.
' {1,2,3} -> index > 3 -> PushArray val
' {1,2,3} -> index <= 1 -> UnshiftArray val
' {} -> index = any -> PushArray val
' @param Long index | Index after which will be added an element
' @param Variant val | Array() or iArray of elements to add into iArray
' @return Long | Count of elements inside iArray
Public Function AddArrayBefore(ByVal index As Long, ByVal val As Variant) As Long
  If Me.Count < 1 Or index + 1 > Me.Count Then
    Me.PushArray val
  ElseIf index <= 0 Then
    Me.UnshiftArray val
  Else
    If TypeOf val Is MusicItemList Then
      For i = val.Count - 1 To 0 Step -1
        Me.Add val(i), bef:=index + 1
      Next i
    Else
      For i = UBound(val) To LBound(val) Step -1
        Me.Add val(i), bef:=index + 1
      Next i
    End If
  End If
  AddArrayBefore = Me.Count
End Function

'AddBefore
' Adds element before given index.
' {1,2,3} -> index > 3 -> Push val
' {1,2,3} -> index <= 1 -> Unshift val
' {} -> index = any -> Push val
' @param Long index | Index before which will be added an element
' @param Variant val | One element (String, number, ...) to add into iArray
' @return Long | Count of elements inside iArray
Public Function AddBefore(ByVal index As Long, ByVal val As MusicItem) As Long
  If Me.Count < 1 Or index + 1 > Me.Count Then
    Me.Push val
  ElseIf index + 1 <= 1 Then
    Me.Unshift val
  Else
    Me.Add val, bef:=index + 1
  End If
  AddBefore = Me.Count
End Function



'Clear
' Empties iArray
Public Function Clear() As Boolean
  For i = mainArray.Count - 1 To 0 Step -1
    mainArray.Remove i + 1
  Next i
  Clear = IIf(mainArray.Count = 0, True, False)
End Function

'Clone
' Makes a hard copy of the mainArray
' @return mainArray | Return exact copy of itself
Public Function clone() As MusicItemList
  Set clone = New MusicItemList
  For i = 0 To Me.Count - 1
    clone.Push Me(i)
  Next i
End Function

'Contains
' Checks if given value is used inside mainArray.
' @param Variant val | One element (String, number, ...) to by checked if it exists in iArray
' $return Boolean | True = exists, False = doesn't exists
Public Function Contains(ByVal val As MusicItem) As Boolean
  Contains = False
  Dim el As Variant
  For Each el In mainArray
    If IsObject(val) = True Or VarType(val) And 8192 Then
        If (VarType(el) And 8192) And (VarType(val) And 8192) Then
            If ArrayDifference(el, val) Then
                Contains = True: Exit Function
            End If
        ElseIf IsObject(el) = True And IsObject(val) = True Then
            If el Is val Then
                Contains = True: Exit Function
            End If
        End If
    Else
        If IsObject(el) = False And (VarType(el) And 8192) <> 8192 Then
            If el = val Then
            Contains = True: Exit Function
            End If
        End If
    End If
  Next el
End Function

'ContainsAll
' Checks if all given values are used inside mainArray.
' @param Variant val | values to by checked if it exists in iArray
' $return Boolean | True = all exists, False = one ore more values doesn't exists
Public Function ContainsAll(ByVal val As MusicItemList) As Boolean
  ContainsAll = False
  Dim foundOccurrences As Integer: foundOccurrences = 0
  Dim values As New MusicItemList
  If Not TypeOf val Is MusicItemList Then
    If IsArray(val) Then
      values.PushArray (val)
    Else
      values.Push (val)
    End If
  Else
    Set values = val
  End If
  For i = 0 To values.Count - 1
    If Me.Contains(values(i)) Then Inc foundOccurrences
  Next i
  If foundOccurrences = values.Count Then ContainsAll = True
End Function


'Dequeue
' Removes an element from the begining of the mainArray.
' @return Variant | Removed element or Empty, if iArray is empty
'刪除開頭一個元素。
Public Function Dequeue() As MusicItem
  Dequeue = Empty
  If mainArray.Count > 0 Then
    If VarType(Me(0)) = vbString Then
        Dequeue = Me(0)
    ElseIf TypeOf Me(0) Is MusicItemList Then
        Set Dequeue = Me(0)
    ElseIf VarType(Me(0)) = vbArray Then
        Set Dequeue = Me(0)
    ElseIf VarType(Me(0)) = vbObject Then
        Set Dequeue = Me(0)
    Else
        Dequeue = Me(0)
    End If
    
    mainArray.Remove 1
  End If
End Function

'Difference
' Checks for number of differences between two arrays, what was added/deleted or combination.
' @param iArray oldArray | Old iArray to be compared with current iArray
' @param String retType | �dd= deleted from old iArray, �aa= added in current iArray, �cc= combination of both (default)
' @return iArray | iArray with differences found
Public Function Difference(ByRef oldArray As MusicItemList, Optional ByVal retType As String = "c") As MusicItemList
  Set Difference = New MusicItemList
  Select Case LCase(retType)
    Case "d"
      For i = 0 To oldArray.Count - 1
        If Me.Contains(oldArray(i)) = False Then Difference.Push oldArray(i)
      Next i
    Case "a"
      For i = 0 To Count - 1
        If oldArray.Contains(Me(i)) = False Then Difference.Push Me(i)
      Next i
    Case "c"
      For i = 0 To oldArray.Count - 1
        If Me.Contains(oldArray(i)) = False Then Difference.Push oldArray(i)
      Next i
      For i = 0 To Count - 1
        If oldArray.Contains(Me(i)) = False Then Difference.Push Me(i)
      Next i
    Case Else
      err.Raise Number:=5, Description:="Unknown Difference return type attribute:" & vbCrLf & _
                                        "Allowed are 'A'dded/'D'eleted/'C'ombination of both"
  End Select
End Function


'First
' Returns value of the first element of the mainArray.
' @return Variant | Value of the first element or Empty if iArray is Empty
Public Function First() As MusicItem
  Set First = IIf(Me.Count > 0, Me(0), Empty)
End Function

'Head
' Returns all elements of iArray, except last one.
' @return iArray | Copy of original array, without last element
Public Function head() As MusicItemList
  Set head = Me.clone
  head.Pop
End Function

'Intersect
' Search for element that exists in both iArrays.
' @param iArray intArray | iArray to be intersected with current iArray
' @return iArray | Intersected values
Public Function Intersect(ByRef intersectedArr As MusicItemList) As MusicItemList
  Set Intersect = New MusicItemList
  Dim el As Variant
  For Each el In mainArray
    If intersectedArr.Contains(el) Then
      If Not Intersect.Contains(el) Then Intersect.Push (el)
    End If
  Next el
End Function

'ContainsOnlyNumeric
' Verify that all elements are numbers or convertable to numbers
' $return Boolean | True = contains only numeric values, False = contains inconvertible values
Public Function ContainsOnlyNumeric() As Boolean
  ContainsOnlyNumeric = True
  Dim el As Variant
  For Each el In mainArray
    If Not IsNumeric(el) Then ContainsOnlyNumeric = False: Exit Function
  Next el
End Function

'Join
' Joins two iArrays.
' @param iArray jArray | iArray to be joined with current iArray
' @return iArray | Joined iArray
Public Function Join(ByRef joinArr As MusicItemList) As MusicItemList
  Set Join = New MusicItemList
  Join.PushArray Me
  Join.PushArray joinArr
End Function

'Last
' Returns value of the last element of the mainArray.
' @return Variant | Value of the last element or Empty if iArray is Empty
Public Function Last() As MusicItem
  Set Last = IIf(Me.Count > 0, Me(Me.Count - 1), Empty)
End Function


'Pop
' Removes an element from the end of the mainArray.
' @return Variant | Removed element or Empty, if iArray is empty
Public Function Pop() As MusicItem
  If mainArray.Count > 0 Then
    If VarType(Me(mainArray.Count - 1)) = vbObject Then
       Set Pop = Me(mainArray.Count - 1)
    Else
        Pop = Me(mainArray.Count - 1)
    End If
    mainArray.Remove mainArray.Count
  End If
End Function
  
  

'Push
' Adds an element at the end of the mainArray.
' @param Variant val | One element (String, number, ...) to add into iArray
' @return Long | Count of elements inside iArray
Public Function Push(ByVal val As MusicItem) As Long
  mainArray.Add val
  Push = mainArray.Count
End Function

'PushArray
' Adds elements at the end of the mainArray.
' @param Variant val | Array() or iArray of elements to add into iArray
' @return Long | Count of elements inside array
Public Function PushArray(ByVal val As Variant) As Long
  If TypeOf val Is MusicItemList Then
    For i = 0 To val.Count - 1
      Me.Push val(i)
    Next i
  Else
    For i = LBound(val) To UBound(val)
      Me.Push val(i)
    Next i
  End If
  PushArray = Me.Count
End Function


'Reverse
' Reverses the content of the iArray
' @return iArray | Reversed iArray
Public Function Reverse() As MusicItemList
  Set Reverse = New MusicItemList
  For i = 0 To Me.Count - 1
    Reverse.Unshift Me(i)
  Next i
End Function

'Shift
' Removes an element from the begining of the mainArray.
' @return Variant | Removed element or Empty, if iArray is empty
'轉移
' 從 iArray 的開頭刪除一個元素。
' @返回第一個元素 | 如果 iArray 為空，則刪除元素或為空
Public Function shift() As MusicItem
  shift = Empty
  If mainArray.Count > 0 Then
    If VarType(Me(0)) = vbString Then
        shift = Me(0)
    ElseIf TypeOf Me(0) Is MusicItemList Then
        Set shift = Me(0)
    ElseIf VarType(Me(0)) = vbArray Then
        Set shift = Me(0)
    ElseIf VarType(Me(0)) = vbObject Then
        Set shift = Me(0)
    Else
        shift = Me(0)
    End If
    
    mainArray.Remove 1
  End If
End Function

'Shuffle
' Randomly mixes content of the iArray
' @return iArray | Shuffled iArray
' 隨機播放
' 隨機混合 iArray 的內容
'@return iArray | 打亂iArray
Public Function Shuffle() As MusicItemList
  Set Shuffle = New MusicItemList
  Dim keys As New MusicItemList
  For i = 0 To Me.Count - 1
    keys.Push (i)
  Next i
  Dim rndNo As Long
  Do While keys.Count > 0
    rndNo = randomFromTo(0, keys.Count - 1)
    Shuffle.Push Me(keys(rndNo))
    keys.Remove (rndNo)
  Loop
End Function



'Tail
' Returns all elements of iArray, except first one.
' @return iArray | Copy of original array, without first element
'返回陣列中除了第一個元素的剩余元素陣列
Public Function Tail() As MusicItemList
  Set Tail = Me.clone
  Tail.Dequeue
End Function

Public Function ToList()
  If Me.Count = 0 Then ToList = Null: Exit Function
  Dim tarr()
  ReDim tarr(Me.Count - 1)
  For i = 0 To Me.Count - 1
    If VarType(Me(i)) = vbString Then
        tarr(i) = Me(i)
    ElseIf TypeOf Me(i) Is MusicItemList Then
        Set tarr(i) = Me(i)
    ElseIf VarType(Me(i)) = vbObject Then
        Set tarr(i) = Me(i)
    Else
        tarr(i) = Me(i)
    End If
  Next i
  ToList = tarr
End Function

'ToString
' Creates string representation of the mainArray.
' @param String delimiter | Optional character to separate the iArray's elements (default = " ")
' @return String | Formated representation of tha iArray
Public Function ToString(Optional ByVal delimiter As String = " ") As String
  If Me.Count = 0 Then ToString = "{}": Exit Function
  ToString = vbNullString
  For i = 0 To Me.Count - 1
    If i = 0 Then ToString = ToString + "{"
    If i > 0 Then ToString = ToString + delimiter
    If VarType(Me(i)) = vbString Then
        ToString = ToString + Chr$(34)
        ToString = ToString + CStr(Me(i))
        ToString = ToString + Chr$(34)
    ElseIf TypeOf Me(i) Is MusicItemList Then
        ToString = ToString + Me(i).ToString(delimiter)
    ElseIf (VarType(Me(i)) And vbArray) = vbArray Then
        ToString = ToString + "[Array]"
    ElseIf VarType(Me(i)) = vbObject Then
        ToString = ToString + "[Object]"
    Else
        ToString = ToString + CStr(Me(i))
    End If
    
    If i = mainArray.Count - 1 Then ToString = ToString + "}"
  Next i
End Function

'Union
' Combines both iArrays and removes duplicities
' @param iArray uArray | iArray to be unioned with current iArray
' @return iArray | Combined values without duplicities
Public Function Union(ByRef uArr As MusicItemList) As MusicItemList
  Set Union = Me.clone
  Union.PushArray uArr
  Union.RemoveDuplicates
End Function

'Unique
' Returns copy of iArray without duplicated values. Original array is not affected
' @return iArray | iArray with unique values
Public Function Unique() As MusicItemList
  Set Unique = New MusicItemList
  Dim el As Variant
  For Each el In mainArray
    If Not Unique.Contains(el) Then Unique.Push (el)
  Next el
End Function

'Unshift
' Add an element at the begining of the mainArray.
' @param Variant val | One element (String, number, ...) to add into iArray
' @return Long | Count of elements inside iArray
Public Function Unshift(ByVal val As Variant) As Long
  If mainArray.Count = 0 Then
    Unshift = Push(val)
  Else
    mainArray.Add val, before:=1
    Unshift = mainArray.Count
  End If
End Function




' #####################
' # PRIVATE FUNCTIONS #
' #####################
Sub Inc(ByRef i)
   i = i + 1
End Sub



'比對 兩個陣列是否一樣
Private Function ArrayDifference(arr1 As Variant, arr2 As Variant) As Boolean

    Dim i As Integer
    If UBound(arr1) = UBound(arr2) Then
        For i = 0 To UBound(arr1)
            If arr1(i) = arr2(i) Then
                ArrayDifference = True
            Else
                ArrayDifference = False
                Exit Function
            End If
        Next
    Else
        ArrayDifference = False
    End If

End Function

'@Description("changes the contents of the array by removing or replacing existing elements and/or adding new elements in place.")
Public Function Splice( _
        ByVal StartIndex As Long, _
        ParamArray Args() As Variant _
    ) As Variant()
    'Dim LocalItems() As Variant
    Dim ActualStart As Long
    Dim ActualDeleteCount As Long
    Dim ArgsCount As Long
    Dim LocalLength As Long
    Dim LocalArgs() As Variant
    Dim result() As Variant
    Dim i As Long
    Dim TempArray() As Variant
    Dim ItemCount As Long
    Dim TempItems() As Variant
    
    LocalArgs = Args
    'LocalItems = mainArray
    LocalLength = Me.Count
    If StartIndex < LocalLength Then
        ActualStart = StartIndex
    Else
        ActualStart = min(StartIndex, LocalLength)
    End If
    
    ArgsCount = UBound(LocalArgs) + 1
    If ArgsCount = 0 Then
        ' only a start index has been supplied
        ' we're gonna delete everything
        ' 僅提供了起始索引
         '我們要刪除所有內容
        ItemCount = 0
        ActualDeleteCount = LocalLength - ActualStart
    Else
        ' first arg in args is delete count, second onwards are insertion items
        ' args 中的第一個參數是刪除計數，第二個之後是插入項
        ItemCount = ArgsCount - 1
        'deleteCount is first element in args.
        'deleteCount 是 args 中的第一個元素。
        ActualDeleteCount = min(max(Args(LBound(Args)), 0), LocalLength - ActualStart)
    End If
    

    ' get items to be deleted for return val
    ' 取得和刪除
    If ActualDeleteCount > 0 Then
        ReDim result(0 To ActualDeleteCount - 1)
        i = 0
        Do While i < ActualDeleteCount
            If IsObject(Me(ActualStart)) Then
                Set result(i) = Me(ActualStart)
                Me.Remove ActualStart
            Else
                result(i) = Me(ActualStart)
                Me.Remove ActualStart
            End If
            Inc i
        Loop
    Else
        ' return empty array if nothing to be deleted
        ReDim result(0)
    End If
    
    '取得要插入的陣列資料
    If ItemCount > 0 Then
        ReDim TempItems(0 To ItemCount - 1)
        For i = 0 To ItemCount - 1
            If IsObject(LocalArgs(i + 1)) Then
                Set TempItems(i) = LocalArgs(i + 1)
            Else
                TempItems(i) = LocalArgs(i + 1)
            End If
        Next
    Me.AddArrayBefore ActualStart, TempItems
    End If
    
    
    Splice = result
End Function

Attribute VB_Name = "MusicNoteItem"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

 Public typs As Cg
 Public configText As String
 Public mtone As String               '升降記號
 Public mfingering As String          '指法
 Public mnote As String               '高低音
 Public mscale As String              '音階
 Public mtempo As String              '拍子
 Public duration As Integer           '拍子的延遲長度
 Public mtow_fingering As String      '指法 第二個
 Public mslur As String               '連音符
 Public mand As String
 Public isAnd As Boolean              '記錄合音 true為跟後面一音合音 ,false為沒有
 Public what As Integer               '記錄一些不一樣的指法


Public Function ToOneMusicItem() As MusicItem
    
    Dim MuseIt As New MusicItem
    Dim lastDuration As Double
    Set MuseIt = New MusicItem
    Set MuseIt.notes = New MusicNoteItemList
    MuseIt.notes.Push Me
    
    lastDuration = calDuration(MuseIt, lastDuration)
    MuseIt.identify_Duration lastDuration
    calExtraw MuseIt
    
    Set ToOneMusicItem = MuseIt
End Function

Attribute VB_Name = "MusicNoteItemList"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
'MIT License
'
'Copyright (c) 2019-2021 Petr Katerinak
'
'Permission is hereby granted, free of charge, to any person obtaining a copy
'of this software and associated documentation files (the "Software"), to deal
'in the Software without restriction, including without limitation the rights
'to use, copy, modify, merge, publish, distribute, sublicense, and/or sell
'copies of the Software, and to permit persons to whom the Software is
'furnished to do so, subject to the following conditions:
'
'The above copyright notice and this permission notice shall be included in all
'copies or substantial portions of the Software.
'
'THE SOFTWARE IS PROVIDED "AS IS", WITHOUT WARRANTY OF ANY KIND, EXPRESS OR
'IMPLIED, INCLUDING BUT NOT LIMITED TO THE WARRANTIES OF MERCHANTABILITY,
'FITNESS FOR A PARTICULAR PURPOSE AND NONINFRINGEMENT. IN NO EVENT SHALL THE
'AUTHORS OR COPYRIGHT HOLDERS BE LIABLE FOR ANY CLAIM, DAMAGES OR OTHER
'LIABILITY, WHETHER IN AN ACTION OF CONTRACT, TORT OR OTHERWISE, ARISING FROM,
'OUT OF OR IN CONNECTION WITH THE SOFTWARE OR THE USE OR OTHER DEALINGS IN THE
'SOFTWARE.
'
' Version of iArray: 1.0
''修正 元素從 0 開始

Private mainArray As New Collection
Private i As Long ' Counter

' #####################
' #    CONSTRUCTOR    #
' #####################
'Private Sub Class_Initialize()
'  Set mainArray = New Collection
'End Sub

' #####################
' #  Getter / Setter  #
' #####################
'Attribute Element.VB_UserMemId = 0 saved in both procedures

'@DefaultMember
Public Property Get element(ByVal index As Long) As MusicNoteItem
Attribute element.VB_UserMemId = 0
    If index + 1 < 1 Or index + 1 > mainArray.Count Then
        Set element = Nothing
        Exit Property
    End If
    If IsObject(mainArray(index + 1)) = True Then
        Set element = mainArray(index + 1)
    Else
        element = mainArray(index + 1)
    End If

 
End Property

'@DefaultMember
Public Property Let element(ByVal index As Long, ByVal val As MusicNoteItem)
Attribute element.VB_UserMemId = 0
  If index = 0 And mainArray.Count = 0 Then
    Me.Push val
    Exit Property
  End If
  If index + 1 > mainArray.Count Then
    Dim eMsg As String
    eMsg = IIf(mainArray.Count > 0, _
               "Index (" & index + 1 & ") out of iArray bounds (1-" & mainArray.Count & ")", _
               "iArray doesn't have any indexes")
    err.Raise Number:=9, Description:=eMsg
    Exit Property
  End If
  mainArray.Remove index + 1
  mainArray.Add val, before:=index
End Property

' #############################
' # COMMON COLLECTION METHODS #
' #############################
Public Function Count() As Long
  Count = mainArray.Count
End Function
Public Sub Add(ByVal val As MusicNoteItem, Optional ByVal bef As Variant = Empty, Optional ByVal aft As Variant = Empty)
  If IsEmpty(bef) And IsEmpty(aft) Then
    mainArray.Add val
  ElseIf IsEmpty(bef) Then
    mainArray.Add val, , , aft
  ElseIf IsEmpty(aft) Then
    mainArray.Add val, , bef
  Else
    mainArray.Add val, , bef, aft
  End If
End Sub
Public Sub Remove(index As Long)
  mainArray.Remove index + 1
End Sub

' ####################
' #  PUBLIC METHODS  #
' ####################

'AddAfter
' Adds element after given index.
' {1,2,3} -> index >= 3 -> Push val
' {1,2,3} -> index < 1 -> Unshift val
' {} -> index = any -> Push val
' @param Long index | Index after which will be added an element
' @param Variant val | One element (String, number, ...) to add into iArray
' @return Long | Count of elements inside iArray
Public Function AddAfter(ByVal index As Long, ByVal val As MusicNoteItem) As Long
  If Me.Count < 1 Or index + 1 >= Me.Count Then
    Me.Push val
  ElseIf index + 1 < 1 Then
    Me.Unshift val
  Else
    Me.Add val, aft:=index + 1
  End If
  AddAfter = Me.Count
End Function

'AddArrayAfter
' Adds elements after given index.
' {1,2,3} -> index >= 3 -> PushArray val
' {1,2,3} -> index < 1 -> UnshiftArray val
' {} -> index = any -> PushArray val
' @param Long index | Index after which will be added an element
' @param Variant val | Array() or iArray of elements to add into iArray
' @return Long | Count of elements inside iArray
Public Function AddArrayAfter(ByVal index As Long, ByVal val As Variant) As Long
  If Me.Count < 1 Or index + 1 >= Me.Count Then
    Me.PushArray val
  ElseIf index + 1 < 1 Then
    Me.UnshiftArray val
  Else
    If TypeOf val Is MusicNoteItemList Then
      For i = 0 To val.Count - 1
        Me.Add val(i), aft:=index + 1
        Inc index
      Next i
    Else
      For i = LBound(val) To UBound(val)
        Me.Add val(i), aft:=index + 1
        Inc index
      Next i
    End If
  End If
  AddArrayAfter = Me.Count
End Function

'AddArrayBefore
' Adds elements before given index.
' {1,2,3} -> index > 3 -> PushArray val
' {1,2,3} -> index <= 1 -> UnshiftArray val
' {} -> index = any -> PushArray val
' @param Long index | Index after which will be added an element
' @param Variant val | Array() or iArray of elements to add into iArray
' @return Long | Count of elements inside iArray
Public Function AddArrayBefore(ByVal index As Long, ByVal val As Variant) As Long
  If Me.Count < 1 Or index + 1 > Me.Count Then
    Me.PushArray val
  ElseIf index <= 0 Then
    Me.UnshiftArray val
  Else
    If TypeOf val Is MusicNoteItemList Then
      For i = val.Count - 1 To 0 Step -1
        Me.Add val(i), bef:=index + 1
      Next i
    Else
      For i = UBound(val) To LBound(val) Step -1
        Me.Add val(i), bef:=index + 1
      Next i
    End If
  End If
  AddArrayBefore = Me.Count
End Function

'AddBefore
' Adds element before given index.
' {1,2,3} -> index > 3 -> Push val
' {1,2,3} -> index <= 1 -> Unshift val
' {} -> index = any -> Push val
' @param Long index | Index before which will be added an element
' @param Variant val | One element (String, number, ...) to add into iArray
' @return Long | Count of elements inside iArray
Public Function AddBefore(ByVal index As Long, ByVal val As MusicNoteItem) As Long
  If Me.Count < 1 Or index + 1 > Me.Count Then
    Me.Push val
  ElseIf index + 1 <= 1 Then
    Me.Unshift val
  Else
    Me.Add val, bef:=index + 1
  End If
  AddBefore = Me.Count
End Function



'Clear
' Empties iArray
Public Function Clear() As Boolean
  For i = mainArray.Count - 1 To 0 Step -1
    mainArray.Remove i + 1
  Next i
  Clear = IIf(mainArray.Count = 0, True, False)
End Function

'Clone
' Makes a hard copy of the mainArray
' @return mainArray | Return exact copy of itself
Public Function clone() As MusicNoteItemList
  Set clone = New MusicNoteItemList
  For i = 0 To Me.Count - 1
    clone.Push Me(i)
  Next i
End Function

'Contains
' Checks if given value is used inside mainArray.
' @param Variant val | One element (String, number, ...) to by checked if it exists in iArray
' $return Boolean | True = exists, False = doesn't exists
Public Function Contains(ByVal val As MusicNoteItem) As Boolean
  Contains = False
  Dim el As Variant
  For Each el In mainArray
    If IsObject(val) = True Or VarType(val) And 8192 Then
        If (VarType(el) And 8192) And (VarType(val) And 8192) Then
            If ArrayDifference(el, val) Then
                Contains = True: Exit Function
            End If
        ElseIf IsObject(el) = True And IsObject(val) = True Then
            If el Is val Then
                Contains = True: Exit Function
            End If
        End If
    Else
        If IsObject(el) = False And (VarType(el) And 8192) <> 8192 Then
            If el = val Then
            Contains = True: Exit Function
            End If
        End If
    End If
  Next el
End Function

'ContainsAll
' Checks if all given values are used inside mainArray.
' @param Variant val | values to by checked if it exists in iArray
' $return Boolean | True = all exists, False = one ore more values doesn't exists
Public Function ContainsAll(ByVal val As MusicNoteItemList) As Boolean
  ContainsAll = False
  Dim foundOccurrences As Integer: foundOccurrences = 0
  Dim values As New MusicNoteItemList
  If Not TypeOf val Is MusicNoteItemList Then
    If IsArray(val) Then
      values.PushArray (val)
    Else
      values.Push (val)
    End If
  Else
    Set values = val
  End If
  For i = 0 To values.Count - 1
    If Me.Contains(values(i)) Then Inc foundOccurrences
  Next i
  If foundOccurrences = values.Count Then ContainsAll = True
End Function


'Dequeue
' Removes an element from the begining of the mainArray.
' @return Variant | Removed element or Empty, if iArray is empty
'刪除開頭一個元素。
Public Function Dequeue() As MusicNoteItem
  Dequeue = Empty
  If mainArray.Count > 0 Then
    If VarType(Me(0)) = vbString Then
        Dequeue = Me(0)
    ElseIf TypeOf Me(0) Is MusicNoteItemList Then
        Set Dequeue = Me(0)
    ElseIf VarType(Me(0)) = vbArray Then
        Set Dequeue = Me(0)
    ElseIf VarType(Me(0)) = vbObject Then
        Set Dequeue = Me(0)
    Else
        Dequeue = Me(0)
    End If
    
    mainArray.Remove 1
  End If
End Function

'Difference
' Checks for number of differences between two arrays, what was added/deleted or combination.
' @param iArray oldArray | Old iArray to be compared with current iArray
' @param String retType | �dd= deleted from old iArray, �aa= added in current iArray, �cc= combination of both (default)
' @return iArray | iArray with differences found
Public Function Difference(ByRef oldArray As MusicNoteItemList, Optional ByVal retType As String = "c") As MusicNoteItemList
  Set Difference = New MusicNoteItemList
  Select Case LCase(retType)
    Case "d"
      For i = 0 To oldArray.Count - 1
        If Me.Contains(oldArray(i)) = False Then Difference.Push oldArray(i)
      Next i
    Case "a"
      For i = 0 To Count - 1
        If oldArray.Contains(Me(i)) = False Then Difference.Push Me(i)
      Next i
    Case "c"
      For i = 0 To oldArray.Count - 1
        If Me.Contains(oldArray(i)) = False Then Difference.Push oldArray(i)
      Next i
      For i = 0 To Count - 1
        If oldArray.Contains(Me(i)) = False Then Difference.Push Me(i)
      Next i
    Case Else
      err.Raise Number:=5, Description:="Unknown Difference return type attribute:" & vbCrLf & _
                                        "Allowed are 'A'dded/'D'eleted/'C'ombination of both"
  End Select
End Function


'First
' Returns value of the first element of the mainArray.
' @return Variant | Value of the first element or Empty if iArray is Empty
Public Function First() As MusicNoteItem
  Set First = IIf(Me.Count > 0, Me(0), Empty)
End Function

'Head
' Returns all elements of iArray, except last one.
' @return iArray | Copy of original array, without last element
Public Function head() As MusicNoteItemList
  Set head = Me.clone
  head.Pop
End Function

'Intersect
' Search for element that exists in both iArrays.
' @param iArray intArray | iArray to be intersected with current iArray
' @return iArray | Intersected values
Public Function Intersect(ByRef intersectedArr As MusicNoteItemList) As MusicNoteItemList
  Set Intersect = New MusicNoteItemList
  Dim el As Variant
  For Each el In mainArray
    If intersectedArr.Contains(el) Then
      If Not Intersect.Contains(el) Then Intersect.Push (el)
    End If
  Next el
End Function

'ContainsOnlyNumeric
' Verify that all elements are numbers or convertable to numbers
' $return Boolean | True = contains only numeric values, False = contains inconvertible values
Public Function ContainsOnlyNumeric() As Boolean
  ContainsOnlyNumeric = True
  Dim el As Variant
  For Each el In mainArray
    If Not IsNumeric(el) Then ContainsOnlyNumeric = False: Exit Function
  Next el
End Function

'Join
' Joins two iArrays.
' @param iArray jArray | iArray to be joined with current iArray
' @return iArray | Joined iArray
Public Function Join(ByRef joinArr As MusicNoteItemList) As MusicNoteItemList
  Set Join = New MusicNoteItemList
  Join.PushArray Me
  Join.PushArray joinArr
End Function

'Last
' Returns value of the last element of the mainArray.
' @return Variant | Value of the last element or Empty if iArray is Empty
Public Function Last() As MusicNoteItem
  Set Last = IIf(Me.Count > 0, Me(Me.Count - 1), Empty)
End Function


'Pop
' Removes an element from the end of the mainArray.
' @return Variant | Removed element or Empty, if iArray is empty
Public Function Pop() As MusicNoteItem
  If mainArray.Count > 0 Then
    If VarType(Me(mainArray.Count - 1)) = vbObject Then
       Set Pop = Me(mainArray.Count - 1)
    Else
        Pop = Me(mainArray.Count - 1)
    End If
    mainArray.Remove mainArray.Count
  End If
End Function
  
  

'Push
' Adds an element at the end of the mainArray.
' @param Variant val | One element (String, number, ...) to add into iArray
' @return Long | Count of elements inside iArray
Public Function Push(ByVal val As MusicNoteItem) As Long
  mainArray.Add val
  Push = mainArray.Count
End Function

'PushArray
' Adds elements at the end of the mainArray.
' @param Variant val | Array() or iArray of elements to add into iArray
' @return Long | Count of elements inside array
Public Function PushArray(ByVal val As Variant) As Long
  If TypeOf val Is MusicNoteItemList Then
    For i = 0 To val.Count - 1
      Me.Push val(i)
    Next i
  Else
    For i = LBound(val) To UBound(val)
      Me.Push val(i)
    Next i
  End If
  PushArray = Me.Count
End Function


'Reverse
' Reverses the content of the iArray
' @return iArray | Reversed iArray
Public Function Reverse() As MusicNoteItemList
  Set Reverse = New MusicNoteItemList
  For i = 0 To Me.Count - 1
    Reverse.Unshift Me(i)
  Next i
End Function

'Shift
' Removes an element from the begining of the mainArray.
' @return Variant | Removed element or Empty, if iArray is empty
'轉移
' 從 iArray 的開頭刪除一個元素。
' @返回第一個元素 | 如果 iArray 為空，則刪除元素或為空
Public Function shift() As MusicNoteItem
  shift = Empty
  If mainArray.Count > 0 Then
    If VarType(Me(0)) = vbString Then
        shift = Me(0)
    ElseIf TypeOf Me(0) Is MusicNoteItemList Then
        Set shift = Me(0)
    ElseIf VarType(Me(0)) = vbArray Then
        Set shift = Me(0)
    ElseIf VarType(Me(0)) = vbObject Then
        Set shift = Me(0)
    Else
        shift = Me(0)
    End If
    
    mainArray.Remove 1
  End If
End Function

'Shuffle
' Randomly mixes content of the iArray
' @return iArray | Shuffled iArray
' 隨機播放
' 隨機混合 iArray 的內容
'@return iArray | 打亂iArray
Public Function Shuffle() As MusicNoteItemList
  Set Shuffle = New MusicNoteItemList
  Dim keys As New MusicNoteItemList
  For i = 0 To Me.Count - 1
    keys.Push (i)
  Next i
  Dim rndNo As Long
  Do While keys.Count > 0
    rndNo = randomFromTo(0, keys.Count - 1)
    Shuffle.Push Me(keys(rndNo))
    keys.Remove (rndNo)
  Loop
End Function



'Tail
' Returns all elements of iArray, except first one.
' @return iArray | Copy of original array, without first element
'返回陣列中除了第一個元素的剩余元素陣列
Public Function Tail() As MusicNoteItemList
  Set Tail = Me.clone
  Tail.Dequeue
End Function

Public Function ToList()
  If Me.Count = 0 Then ToList = Null: Exit Function
  Dim tarr()
  ReDim tarr(Me.Count - 1)
  For i = 0 To Me.Count - 1
    If VarType(Me(i)) = vbString Then
        tarr(i) = Me(i)
    ElseIf TypeOf Me(i) Is MusicNoteItemList Then
        Set tarr(i) = Me(i)
    ElseIf VarType(Me(i)) = vbObject Then
        Set tarr(i) = Me(i)
    Else
        tarr(i) = Me(i)
    End If
  Next i
  ToList = tarr
End Function

'ToString
' Creates string representation of the mainArray.
' @param String delimiter | Optional character to separate the iArray's elements (default = " ")
' @return String | Formated representation of tha iArray
Public Function ToString(Optional ByVal delimiter As String = " ") As String
  If Me.Count = 0 Then ToString = "{}": Exit Function
  ToString = vbNullString
  For i = 0 To Me.Count - 1
    If i = 0 Then ToString = ToString + "{"
    If i > 0 Then ToString = ToString + delimiter
    If VarType(Me(i)) = vbString Then
        ToString = ToString + Chr$(34)
        ToString = ToString + CStr(Me(i))
        ToString = ToString + Chr$(34)
    ElseIf TypeOf Me(i) Is MusicNoteItemList Then
        ToString = ToString + Me(i).ToString(delimiter)
    ElseIf (VarType(Me(i)) And vbArray) = vbArray Then
        ToString = ToString + "[Array]"
    ElseIf VarType(Me(i)) = vbObject Then
        ToString = ToString + "[Object]"
    Else
        ToString = ToString + CStr(Me(i))
    End If
    
    If i = mainArray.Count - 1 Then ToString = ToString + "}"
  Next i
End Function

'Union
' Combines both iArrays and removes duplicities
' @param iArray uArray | iArray to be unioned with current iArray
' @return iArray | Combined values without duplicities
Public Function Union(ByRef uArr As MusicNoteItemList) As MusicNoteItemList
  Set Union = Me.clone
  Union.PushArray uArr
  Union.RemoveDuplicates
End Function

'Unique
' Returns copy of iArray without duplicated values. Original array is not affected
' @return iArray | iArray with unique values
Public Function Unique() As MusicNoteItemList
  Set Unique = New MusicNoteItemList
  Dim el As Variant
  For Each el In mainArray
    If Not Unique.Contains(el) Then Unique.Push (el)
  Next el
End Function

'Unshift
' Add an element at the begining of the mainArray.
' @param Variant val | One element (String, number, ...) to add into iArray
' @return Long | Count of elements inside iArray
Public Function Unshift(ByVal val As Variant) As Long
  If mainArray.Count = 0 Then
    Unshift = Push(val)
  Else
    mainArray.Add val, before:=1
    Unshift = mainArray.Count
  End If
End Function




' #####################
' # PRIVATE FUNCTIONS #
' #####################
Sub Inc(ByRef i)
   i = i + 1
End Sub



'比對 兩個陣列是否一樣
Private Function ArrayDifference(arr1 As Variant, arr2 As Variant) As Boolean

    Dim i As Integer
    If UBound(arr1) = UBound(arr2) Then
        For i = 0 To UBound(arr1)
            If arr1(i) = arr2(i) Then
                ArrayDifference = True
            Else
                ArrayDifference = False
                Exit Function
            End If
        Next
    Else
        ArrayDifference = False
    End If

End Function

'@Description("changes the contents of the array by removing or replacing existing elements and/or adding new elements in place.")
Public Function Splice( _
        ByVal StartIndex As Long, _
        ParamArray Args() As Variant _
    ) As Variant()
    'Dim LocalItems() As Variant
    Dim ActualStart As Long
    Dim ActualDeleteCount As Long
    Dim ArgsCount As Long
    Dim LocalLength As Long
    Dim LocalArgs() As Variant
    Dim result() As Variant
    Dim i As Long
    Dim TempArray() As Variant
    Dim ItemCount As Long
    Dim TempItems() As Variant
    
    LocalArgs = Args
    'LocalItems = mainArray
    LocalLength = Me.Count
    If StartIndex < LocalLength Then
        ActualStart = StartIndex
    Else
        ActualStart = min(StartIndex, LocalLength)
    End If
    
    ArgsCount = UBound(LocalArgs) + 1
    If ArgsCount = 0 Then
        ' only a start index has been supplied
        ' we're gonna delete everything
        ' 僅提供了起始索引
         '我們要刪除所有內容
        ItemCount = 0
        ActualDeleteCount = LocalLength - ActualStart
    Else
        ' first arg in args is delete count, second onwards are insertion items
        ' args 中的第一個參數是刪除計數，第二個之後是插入項
        ItemCount = ArgsCount - 1
        'deleteCount is first element in args.
        'deleteCount 是 args 中的第一個元素。
        ActualDeleteCount = min(max(Args(LBound(Args)), 0), LocalLength - ActualStart)
    End If
    

    ' get items to be deleted for return val
    ' 取得和刪除
    If ActualDeleteCount > 0 Then
        ReDim result(0 To ActualDeleteCount - 1)
        i = 0
        Do While i < ActualDeleteCount
            If IsObject(Me(ActualStart)) Then
                Set result(i) = Me(ActualStart)
                Me.Remove ActualStart
            Else
                result(i) = Me(ActualStart)
                Me.Remove ActualStart
            End If
            Inc i
        Loop
    Else
        ' return empty array if nothing to be deleted
        ReDim result(0)
    End If
    
    '取得要插入的陣列資料
    If ItemCount > 0 Then
        ReDim TempItems(0 To ItemCount - 1)
        For i = 0 To ItemCount - 1
            If IsObject(LocalArgs(i + 1)) Then
                Set TempItems(i) = LocalArgs(i + 1)
            Else
                TempItems(i) = LocalArgs(i + 1)
            End If
        Next
    Me.AddArrayBefore ActualStart, TempItems
    End If
    
    
    Splice = result
End Function

Attribute VB_Name = "OpenExcel"
Option Explicit

' Declare necessary API routines:
Private Declare Function FindWindow Lib "user32" Alias _
"FindWindowA" (ByVal lpClassName As String, _
                    ByVal lpWindowName As Long) As Long
Private Declare Function SendMessage Lib "user32" Alias _
"SendMessageA" (ByVal hWnd As Long, ByVal wMsg As Long, _
                    ByVal wParam As Long, _
                    ByVal lParam As Long) As Long
Sub GetExcel()
    Dim MyXL As Object    ' Variable to hold reference
                                ' to Microsoft Excel.
    Dim ExcelWasNotRunning As Boolean    ' Flag for final release.
' Test to see if there is a copy of Microsoft Excel already running.
    On Error Resume Next    ' Defer error trapping.
' GetObject function called without the first argument returns a
' reference to an instance of the application. If the application isn't
' running, an error occurs.
    Set MyXL = GetObject(, "Excel.Application")
    If err.Number <> 0 Then ExcelWasNotRunning = True
    err.Clear    ' Clear Err object in case error occurred.
' Check for Microsoft Excel. If Microsoft Excel is running,
' enter it into the Running Object table.
    DetectExcel
' Set the object variable to reference the file you want to see.
    Set MyXL = GetObject("C:\GitHub\muse\app說明.xls")
' Show Microsoft Excel through its Application property. Then
' show the actual window containing the file using the Windows
' collection of the MyXL object reference.
    MyXL.Application.Visible = True
    MyXL.parent.Windows(1).Visible = True
     'Do manipulations of your  file here.
    ' ...
' If this copy of Microsoft Excel was not running when you
' started, close it using the Application property's Quit method.
' Note that when you try to quit Microsoft Excel, the
' title bar blinks and a message is displayed asking if you
' want to save any loaded files.
    If ExcelWasNotRunning = True Then
        MyXL.Application.Quit
    End If
    Set MyXL = Nothing    ' Release reference to the
                                ' application and spreadsheet.
End Sub
Sub DetectExcel()
' Procedure dectects a running Excel and registers it.
    Const WM_USER = 1024
    Dim hWnd As Long
' If Excel is running this API call returns its handle.
    hWnd = FindWindow("XLMAIN", 0)
    If hWnd = 0 Then    ' 0 means Excel not running.
        Exit Sub
    Else
    ' Excel is running so use the SendMessage API
    ' function to enter it in the Running Object Table.
        SendMessage hWnd, WM_USER + 18, 0, 0
    End If
End Sub

Attribute VB_Name = "PointList"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
'MIT License
'
'Copyright (c) 2019-2021 Petr Katerinak
'
'Permission is hereby granted, free of charge, to any person obtaining a copy
'of this software and associated documentation files (the "Software"), to deal
'in the Software without restriction, including without limitation the rights
'to use, copy, modify, merge, publish, distribute, sublicense, and/or sell
'copies of the Software, and to permit persons to whom the Software is
'furnished to do so, subject to the following conditions:
'
'The above copyright notice and this permission notice shall be included in all
'copies or substantial portions of the Software.
'
'THE SOFTWARE IS PROVIDED "AS IS", WITHOUT WARRANTY OF ANY KIND, EXPRESS OR
'IMPLIED, INCLUDING BUT NOT LIMITED TO THE WARRANTIES OF MERCHANTABILITY,
'FITNESS FOR A PARTICULAR PURPOSE AND NONINFRINGEMENT. IN NO EVENT SHALL THE
'AUTHORS OR COPYRIGHT HOLDERS BE LIABLE FOR ANY CLAIM, DAMAGES OR OTHER
'LIABILITY, WHETHER IN AN ACTION OF CONTRACT, TORT OR OTHERWISE, ARISING FROM,
'OUT OF OR IN CONNECTION WITH THE SOFTWARE OR THE USE OR OTHER DEALINGS IN THE
'SOFTWARE.
'
' Version of iArray: 1.0
''修正 元素從 0 開始

Private iArray As Collection
Private i As Long ' Counter

' #####################
' #    CONSTRUCTOR    #
' #####################
Private Sub Class_Initialize()
  Set iArray = New Collection
End Sub

' #####################
' #  Getter / Setter  #
' #####################
'Attribute Element.VB_UserMemId = 0 saved in both procedures

'@DefaultMember
Public Property Get element(ByVal index As Long) As point
Attribute element.VB_UserMemId = 0
    If index + 1 < 1 Or index + 1 > iArray.Count Then
        Set element = Nothing
        Exit Property
    End If
    If VarType(iArray(index + 1)) = vbObject Then
       Set element = iArray(index + 1)
    ElseIf VarType(iArray(index + 1)) = vbVariant Then
       Set element = iArray(index + 1)
    ElseIf VarType(iArray(index + 1)) = vbArray Then
       Set element = iArray(index + 1)
    Else
        element = iArray(index + 1)
    End If
 
End Property

'@DefaultMember
Public Property Let element(ByVal index As Long, ByVal val As point)
Attribute element.VB_UserMemId = 0
  If index = 0 And iArray.Count = 0 Then
    Me.Push val
    Exit Property
  End If
  If index + 1 > iArray.Count Then
    Dim eMsg As String
    eMsg = IIf(iArray.Count > 0, _
               "Index (" & index + 1 & ") out of iArray bounds (1-" & iArray.Count & ")", _
               "iArray doesn't have any indexes")
    err.Raise Number:=9, Description:=eMsg
    Exit Property
  End If
  iArray.Remove index + 1
  If index + 1 >= iArray.Count Then
    iArray.Add val
  Else
    iArray.Add val, before:=index + 1
  End If
End Property

' #############################
' # COMMON COLLECTION METHODS #
' #############################
Public Function Count() As Long
  Count = iArray.Count
End Function
Public Sub Add(ByVal val As point, Optional ByVal bef As Variant = Empty, Optional ByVal aft As Variant = Empty)
  If IsEmpty(bef) And IsEmpty(aft) Then
    iArray.Add val
  ElseIf IsEmpty(bef) Then
    iArray.Add val, , , aft
  ElseIf IsEmpty(aft) Then
    iArray.Add val, , bef
  Else
    iArray.Add val, , bef, aft
  End If
End Sub
Public Sub Remove(index As Long)
  iArray.Remove index + 1
End Sub

' ####################
' #  PUBLIC METHODS  #
' ####################

'AddAfter
' Adds element after given index.
' {1,2,3} -> index >= 3 -> Push val
' {1,2,3} -> index < 1 -> Unshift val
' {} -> index = any -> Push val
' @param Long index | Index after which will be added an element
' @param Variant val | One element (String, number, ...) to add into iArray
' @return Long | Count of elements inside iArray
Public Function AddAfter(ByVal index As Long, ByVal val As Variant) As Long
  If Me.Count < 1 Or index + 1 >= Me.Count Then
    Me.Push val
  ElseIf index + 1 < 1 Then
    Me.Unshift val
  Else
    Me.Add val, aft:=index + 1
  End If
  AddAfter = Me.Count
End Function

'AddArrayAfter
' Adds elements after given index.
' {1,2,3} -> index >= 3 -> PushArray val
' {1,2,3} -> index < 1 -> UnshiftArray val
' {} -> index = any -> PushArray val
' @param Long index | Index after which will be added an element
' @param Variant val | Array() or iArray of elements to add into iArray
' @return Long | Count of elements inside iArray
Public Function AddArrayAfter(ByVal index As Long, ByVal val As Variant) As Long
  If Me.Count < 1 Or index + 1 >= Me.Count Then
    Me.PushArray val
  ElseIf index + 1 < 1 Then
    Me.UnshiftArray val
  Else
    If TypeOf val Is PointList Then
      For i = 0 To val.Count - 1
        Me.Add val(i), aft:=index + 1
        Inc index
      Next i
    Else
      For i = LBound(val) To UBound(val)
        Me.Add val(i), aft:=index + 1
        Inc index
      Next i
    End If
  End If
  AddArrayAfter = Me.Count
End Function

'AddArrayBefore
' Adds elements before given index.
' {1,2,3} -> index > 3 -> PushArray val
' {1,2,3} -> index <= 1 -> UnshiftArray val
' {} -> index = any -> PushArray val
' @param Long index | Index after which will be added an element
' @param Variant val | Array() or iArray of elements to add into iArray
' @return Long | Count of elements inside iArray
Public Function AddArrayBefore(ByVal index As Long, ByVal val As Variant) As Long
  If Me.Count < 1 Or index + 1 > Me.Count Then
    Me.PushArray val
  ElseIf index <= 0 Then
    Me.UnshiftArray val
  Else
    If TypeOf val Is iArray Then
      For i = val.Count - 1 To 0 Step -1
        Me.Add val(i), bef:=index + 1
      Next i
    Else
      For i = UBound(val) To LBound(val) Step -1
        Me.Add val(i), bef:=index + 1
      Next i
    End If
  End If
  AddArrayBefore = Me.Count
End Function

'AddBefore
' Adds element before given index.
' {1,2,3} -> index > 3 -> Push val
' {1,2,3} -> index <= 1 -> Unshift val
' {} -> index = any -> Push val
' @param Long index | Index before which will be added an element
' @param Variant val | One element (String, number, ...) to add into iArray
' @return Long | Count of elements inside iArray
Public Function AddBefore(ByVal index As Long, ByVal val As Variant) As Long
  If Me.Count < 1 Or index + 1 > Me.Count Then
    Me.Push val
  ElseIf index + 1 <= 1 Then
    Me.Unshift val
  Else
    Me.Add val, bef:=index + 1
  End If
  AddBefore = Me.Count
End Function

'Avg
' Calculates the average of the numeric iArray.
' @return Variant | Average value / "NaN" if iArray contains non-numeric value(s)
Public Function Avg() As Variant
  If Not Me.ContainsOnlyNumeric Then Avg = "NaN": Exit Function
  Avg = Me.sum / Me.Count
End Function

'Clear
' Empties iArray
Public Function Clear() As Boolean
  For i = iArray.Count - 1 To 0 Step -1
    iArray.Remove i + 1
  Next i
  Clear = IIf(iArray.Count = 0, True, False)
End Function

'Clone
' Makes a hard copy of the iArray
' @return iArray | Return exact copy of itself
Public Function clone() As PointList
  Set clone = New PointList
  For i = 0 To Me.Count - 1
    clone.Push Me(i)
  Next i
End Function

'Contains
' Checks if given value is used inside iArray.
' @param Variant val | One element (String, number, ...) to by checked if it exists in iArray
' $return Boolean | True = exists, False = doesn't exists
Public Function Contains(ByVal val As Variant) As Boolean
  Contains = False
  Dim el As Variant
  For Each el In iArray
    If el = val Then Contains = True: Exit Function
  Next el
End Function

'ContainsAll
' Checks if all given values are used inside iArray.
' @param Variant val | values to by checked if it exists in iArray
' $return Boolean | True = all exists, False = one ore more values doesn't exists
Public Function ContainsAll(ByVal val As Variant) As Boolean
  ContainsAll = False
  Dim foundOccurrences As Integer: foundOccurrences = 0
  Dim values As New iArray
  If Not TypeOf val Is iArray Then
    If IsArray(val) Then
      values.PushArray (val)
    Else
      values.Push (val)
    End If
  Else
    Set values = val
  End If
  For i = 0 To values.Count - 1
    If Me.Contains(values(i)) Then Inc foundOccurrences
  Next i
  If foundOccurrences = values.Count Then ContainsAll = True
End Function

'CountOccurrences
' Checks how many times is given value used inside iArray.
' @param Variant val | One element (String, number, ...) to by checked
' @return Long | Count of matched occurrences
Public Function CountOccurrences(val As Variant) As Long
  CountOccurrences = 0
  Dim el As Variant
  For Each el In iArray
    If el = val Then Inc CountOccurrences
  Next el
End Function

'Dequeue
' Removes an element from the begining of the iArray.
' @return Variant | Removed element or Empty, if iArray is empty
Public Function Dequeue() As Variant
  Dequeue = shift()
End Function

'Difference
' Checks for number of differences between two arrays, what was added/deleted or combination.
' @param iArray oldArray | Old iArray to be compared with current iArray
' @param String retType | �d� = deleted from old iArray, �a� = added in current iArray, �c� = combination of both (default)
' @return iArray | iArray with differences found
Public Function Difference(ByRef oldArray As iArray, Optional ByVal retType As String = "c") As iArray
  Set Difference = New iArray
  Select Case LCase(retType)
    Case "d"
      For i = 0 To oldArray.Count - 1
        If Me.Contains(oldArray(i)) = False Then Difference.Push oldArray(i)
      Next i
    Case "a"
      For i = 0 To Count - 1
        If oldArray.Contains(Me(i)) = False Then Difference.Push Me(i)
      Next i
    Case "c"
      For i = 0 To oldArray.Count - 1
        If Me.Contains(oldArray(i)) = False Then Difference.Push oldArray(i)
      Next i
      For i = 0 To Count - 1
        If oldArray.Contains(Me(i)) = False Then Difference.Push Me(i)
      Next i
    Case Else
      err.Raise Number:=5, Description:="Unknown Difference return type attribute:" & vbCrLf & _
                                        "Allowed are 'A'dded/'D'eleted/'C'ombination of both"
  End Select
End Function

'DropLeft
' Remove n elements from the beginning of the iArray. If n > count of iArray elements, all elements are removed.
' @param Long n | Number of elements to be removed
' @return iArray | Array of the removed elements
Public Function DropLeft(ByRef N As Long) As iArray
  Set DropLeft = New iArray
  If N > Me.Count Then N = Me.Count
  For i = 0 To N - 1
    DropLeft.Push Me(i)
  Next i
  For i = N - 1 To 0 Step -1
    Me.Remove (i)
  Next i
End Function

'DropRight
' Remove n elements from the end of the iArray. If n > count of iArray elements, all elements are removed.
' @param Long n | Number of elements to be removed
' @return iArray | Array of the removed elements
Public Function DropRight(ByRef N As Long) As iArray
  Set DropRight = New iArray
  If N > Me.Count Then N = Me.Count
  For i = Me.Count - N To Me.Count - 1
    DropRight.Push Me(i)
  Next i
  For i = Me.Count - 1 To Me.Count - N Step -1
    Me.Remove (i)
  Next i
End Function

'Enqueue
' Adds an element at the end of the iArray.
' @param Variant val | One element (String, number, ...) to add into iArray
' @return Long | Count of elements inside iArray
Public Function Enqueue(ByVal val As Variant) As Long
  Enqueue = Push(val)
End Function

'EnqueueArray
' Adds elements at the end of the iArray
' @param Variant val | Array() or iArray of elements to add into iArray
' @return Long | Count of elements inside array
Public Function EnqueueArray(ByVal val As Variant) As Long
  EnqueueArray = PushArray(val)
End Function

'First
' Returns value of the first element of the iArray.
' @return Variant | Value of the first element or Empty if iArray is Empty
Public Function First() As point
  Set First = IIf(Me.Count > 0, Me(1), Empty)
End Function

'Head
' Returns all elements of iArray, except last one.
' @return iArray | Copy of original array, without last element
Public Function head() As PointList
  Set head = Me.clone
  head.Pop
End Function

'Intersect
' Search for element that exists in both iArrays.
' @param iArray intArray | iArray to be intersected with current iArray
' @return iArray | Intersected values
Public Function Intersect(ByRef intersectedArr As PointList) As PointList
  Set Intersect = New PointList
  Dim el As Variant
  For Each el In iArray
    If intersectedArr.Contains(el) Then
      If Not Intersect.Contains(el) Then Intersect.Push (el)
    End If
  Next el
End Function

'ContainsOnlyNumeric
' Verify that all elements are numbers or convertable to numbers
' $return Boolean | True = contains only numeric values, False = contains inconvertible values
Public Function ContainsOnlyNumeric() As Boolean
  ContainsOnlyNumeric = True
  Dim el As Variant
  For Each el In iArray
    If Not IsNumeric(el) Then ContainsOnlyNumeric = False: Exit Function
  Next el
End Function

'Join
' Joins two iArrays.
' @param iArray jArray | iArray to be joined with current iArray
' @return iArray | Joined iArray
Public Function Join(ByRef joinArr As PointList) As PointList
  Set Join = New PointList
  Join.PushArray Me
  Join.PushArray joinArr
End Function

'Last
' Returns value of the last element of the iArray.
' @return Variant | Value of the last element or Empty if iArray is Empty
Public Function Last() As point
  Set Last = IIf(Me.Count > 0, Me(Me.Count), Empty)
End Function

'OccurrenceIndexes
' Returns all indexes of a value in iArray.
' @return iArray | iArray containing indexes of occurrence
Public Function OccurenceIndexes(val As Variant) As PointList
  Set OccurenceIndexes = New PointList
  For i = 0 To Me.Count - 1
    If iArray(i) = val Then OccurenceIndexes.Push (i)
  Next i
End Function

'Pop
' Removes an element from the end of the iArray.
' @return Variant | Removed element or Empty, if iArray is empty
Public Function Pop() As point
  If iArray.Count > 0 Then
    If VarType(Me(iArray.Count - 1)) = vbObject Then
       Set Pop = Me(iArray.Count - 1)
    Else
        Pop = Me(iArray.Count - 1)
    End If
    iArray.Remove iArray.Count
  End If
End Function

'Push
' Adds an element at the end of the iArray.
' @param Variant val | One element (String, number, ...) to add into iArray
' @return Long | Count of elements inside iArray
Public Function Push(ByVal val As point) As Long
  iArray.Add val
  Push = iArray.Count
End Function

'PushArray
' Adds elements at the end of the iArray.
' @param Variant val | Array() or iArray of elements to add into iArray
' @return Long | Count of elements inside array
Public Function PushArray(ByVal val As Variant) As Long
  If TypeOf val Is iArray Then
    For i = 0 To val.Count - 1
      Me.Push val(i)
    Next i
  Else
    For i = LBound(val) To UBound(val)
      Me.Push val(i)
    Next i
  End If
  PushArray = Me.Count
End Function

'RemoveDuplicates
' Keeps only the first occurrence of the value. Affects original array
' @return Long | Count of the removed elements
Public Function RemoveDuplicates() As Long
  RemoveDuplicates = 0
  For i = Me.Count To 1 Step -1
    If Me.CountOccurrences(Me(i)) > 1 Then
      Me.Remove i
      Inc RemoveDuplicates
    End If
  Next i
End Function

'Reverse
' Reverses the content of the iArray
' @return iArray | Reversed iArray
Public Function Reverse() As PointList
  Set Reverse = New PointList
  For i = 0 To Me.Count
    Reverse.Unshift Me(i)
  Next i
End Function

'Shift
' Removes an element from the begining of the iArray.
' @return Variant | Removed element or Empty, if iArray is empty
Public Function shift() As Variant
  shift = Empty
  If iArray.Count > 0 Then
    shift = Me(0)
    iArray.Remove 1
  End If
End Function

'Shuffle
' Randomly mixes content of the iArray
' @return iArray | Shuffled iArray
Public Function Shuffle() As iArray
  Set Shuffle = New iArray
  Dim keys As New iArray
  For i = 1 To Me.Count
    keys.Push (i)
  Next i
  Dim rndNo As Long
  Do While keys.Count > 0
    rndNo = randomFromTo(1, keys.Count)
    Shuffle.Push Me(keys(rndNo))
    keys.Remove (rndNo)
  Loop
End Function

'Sum
' Calculates the sum of the numeric iArray.
' @return Variant | Sum value / "NaN" if iArray contains non-numeric value(s)
Public Function sum() As Variant
  If Not Me.ContainsOnlyNumeric Then sum = "NaN": Exit Function
  sum = 0
  Dim el As Variant
  For Each el In iArray
    sum = sum + el
  Next el
End Function

'Tail
' Returns all elements of iArray, except first one.
' @return iArray | Copy of original array, without first element
Public Function Tail() As iArray
  Set Tail = Me.clone
  Tail.Dequeue
End Function

Public Function ToList()
  If Me.Count = 0 Then ToList = Null: Exit Function
  Dim tarr()
  ReDim tarr(Me.Count - 1)
  For i = 0 To Me.Count - 1
    If VarType(Me(i)) = vbString Then
        tarr(i) = Me(i)
    ElseIf TypeOf Me(i) Is iArray Then
        Set tarr(i) = Me(i)
    ElseIf VarType(Me(i)) = vbObject Then
        Set tarr(i) = Me(i)
    Else
        tarr(i) = Me(i)
    End If
  Next i
  ToList = tarr
End Function


Public Function ToXYZList() As Double()
  If Me.Count = 0 Then ToList = Null: Exit Function

  Dim j As Long
  
    Dim tmplist() As Double
    ReDim tmplist(0 To (Me.Count * 3) - 1)
    
    For j = 0 To Me.Count - 1
        tmplist(j * 3) = Me(j).x
        tmplist(j * 3 + 1) = Me(j).y
        tmplist(j * 3 + 2) = Me(j).Z
    Next
    ToXYZList = tmplist
End Function

'ToString
' Creates string representation of the iArray.
' @param String delimiter | Optional character to separate the iArray's elements (default = " ")
' @return String | Formated representation of tha iArray
Public Function ToString(Optional ByVal delimiter As String = " ") As String
  If Me.Count = 0 Then ToString = "{}": Exit Function
  ToString = vbNullString
  For i = 0 To Me.Count - 1
    If i = 0 Then ToString = ToString + "{"
    If i > 0 Then ToString = ToString + delimiter
    If VarType(Me(i)) = vbString Then
        ToString = ToString + Chr$(34)
        ToString = ToString + CStr(Me(i))
        ToString = ToString + Chr$(34)
    ElseIf TypeOf Me(i) Is iArray Then
        ToString = ToString + Me(i).ToString(delimiter)
    ElseIf VarType(Me(i)) = vbObject Then
        ToString = ToString + "[Object]"
    Else
        ToString = ToString + CStr(Me(i))
    End If
    
    If i = iArray.Count - 1 Then ToString = ToString + "}"
  Next i
End Function

'Union
' Combines both iArrays and removes duplicities
' @param iArray uArray | iArray to be unioned with current iArray
' @return iArray | Combined values without duplicities
Public Function Union(ByRef uArr As iArray) As iArray
  Set Union = Me.clone
  Union.PushArray uArr
  Union.RemoveDuplicates
End Function

'Unique
' Returns copy of iArray without duplicated values. Original array is not affected
' @return iArray | iArray with unique values
Public Function Unique() As iArray
  Set Unique = New iArray
  Dim el As Variant
  For Each el In iArray
    If Not Unique.Contains(el) Then Unique.Push (el)
  Next el
End Function

'Unshift
' Add an element at the begining of the iArray.
' @param Variant val | One element (String, number, ...) to add into iArray
' @return Long | Count of elements inside iArray
Public Function Unshift(ByVal val As Variant) As Long
  If iArray.Count = 0 Then
    Unshift = Push(val)
  Else
    iArray.Add val, before:=1
    Unshift = iArray.Count
  End If
End Function

'UnshiftArray
' Add elements at the begining of the iArray.
' @param Variant val | Array() or iArray of elements to add into iArray
' @return Long | Count of elements inside iArray
Public Function UnshiftArray(ByVal val As Variant) As Long
  If TypeOf val Is iArray Then
    For i = val.Count - 1 To 0 Step -1
      Unshift val(i)
    Next i
  Else
    For i = UBound(val) To LBound(val) Step -1
      Unshift val(i)
    Next i
  End If
  UnshiftArray = iArray.Count
End Function


' #####################
' # PRIVATE FUNCTIONS #
' #####################
Sub Inc(ByRef i)
   i = i + 1
End Sub

'Private Function rangeToArray(ByVal rng As Range) As Variant
'  rangeToArray = rng.Value
'End Function

Private Function randomFromTo(ByVal from As Long, ByVal upTo As Long) As Long
  Randomize
  randomFromTo = Int(from + Rnd() * (upTo - from + 1))
End Function

Attribute VB_Name = "RelativeElement"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public typs As String
Public c As String
Public pitch As Double
Public x As Double
Public w As Double
Public dx As Double
Public scalex As Double
Public scaley As Double
Public pitch2 As Double
Public lineWidth As Double
Public klass As String
Public anchor As String '"start" | "middle" | "end"
Public top As Double
Public bottom As Double
Public height As Double
Public Name As String
Public realWidth As Double
Public centerVertically As Boolean
Public parent As AbsoluteElement
Public graphelem As Dictionary  'SVGPathElement
Public stemdir As String
Public highestVert As Double
Public dim_ As Dictionary
' {
'    fontas {
'        faceas string
'        sizeas double
'        decorationas string
'        styleas string
'        weightas string
'        box?
'        paddingas double
'    }
'    attras {
'        'font-size'as double
'        'font-style'as string
'        'font-family'as string
'        'font-weight'as string
'        'text-decoration'as string
'        classas string
'        'text-anchor'as string
'        x As Double
'        y As Double
'        'data-name'as string
'    }
'}

 Public position As String ' 'below' | 'above' | 'hidden' | 'left' | 'right' | 'relative'
 Public partHeightAbove
 Public chordHeightAbove
 Public chordHeightBelow
 Public lyricHeightAbove
 Public lyricHeightBelow
Public lane As Integer

 Public Sub init(c As String, dx As Double, w As Double, pitch As Double, Optional opt As oRelativeOptions = Nothing)
    If (opt Is Nothing) Then Set opt = New oRelativeOptions
    Me.x = 0
    Me.c = c       '' character or path or string
    Me.dx = dx     '' relative x position
    Me.w = w       '' minimum width taken up by this element (can include gratuitous space)
    Me.pitch = pitch  '' relative y position by pitch
    If opt.scalex = 0 Then Me.scalex = 1
    If opt.scaley = 0 Then Me.scaley = 1
    If opt.typs = "" Then Me.typs = "symbol"
    Me.pitch2 = opt.pitch2
    Me.lineWidth = opt.lineWidth
    Me.klass = opt.klass
    If opt.anchor = "" Then Me.anchor = "middle"
    Me.top = pitch
    Me.bottom = pitch
'    if (me.pitch2 !== undefined && me.pitch2 > me.top) me.top = me.pitch2
'    if (me.pitch2 !== undefined && me.pitch2 < me.bottom) me.bottom = me.pitch2
'    if (opt.thickness) {
'        me.top += opt.thickness / 2
'        me.bottom -= opt.thickness / 2
'    }
'    if (opt.stemHeight) {
'        if (opt.stemHeight > 0)
'            me.top += opt.stemHeight
'        Else
'            me.bottom += opt.stemHeight
'    }
'    if (opt.dim)
'        Me.dim = opt.dim
'    if (opt.position)
'        Me.position = opt.position
'    me.height = opt.height ? opt.height : 4  '' The +1 is to give a little bit of padding.
'    if (opt.top)
'        Me.top = opt.top
'    if (opt.bottom)
'        Me.bottom = opt.bottom
'    if (opt.name)
'        Me.name = opt.name
'    else if (me.c)
'        Me.name = Me.c
'    Else
'        Me.name = Me.typs
'    if (opt.realWidth)
'        Me.realWidth = opt.realWidth
'    Else
'        Me.realWidth = Me.w
    Me.centerVertically = False
'    Select Case Me.typs
'        Case "debug":
'            Me.chordHeightAbove = Me.height
'
'        Case "lyric":
'            if (opt.position && opt.position === 'below')
'                Me.lyricHeightBelow = Me.height
'            Else
'                Me.lyricHeightAbove = Me.height
'
'        Case "chord":
'            if (opt.position && opt.position === 'below')
'                Me.chordHeightBelow = Me.height
'            Else
'                Me.chordHeightAbove = Me.height
'
'        Case "text":
'            if (me.pitch === undefined) {
'                if (opt.position && opt.position === 'below')
'                    Me.chordHeightBelow = Me.height
'                Else
'                    Me.chordHeightAbove = Me.height
'            } else
'                Me.centerVertically = True
'
'        Case "part": Me.partHeightAbove = Me.height
'        Case Else
'            Debug.Print "Not between 1 and 10"
'    End Select
End Sub

Public Function getChordDim() As Rect
    If Me.typs = "debug" Then
        Exit Function
    End If
    If IsEmpty(Me.chordHeightAbove) And IsEmpty(Me.chordHeightBelow) Then
        Exit Function
    End If
    '' Chords are centered, annotations are left justified.
    '' NOTE: the font reports extra space to the left and right anyway, so there is a built in margin.
    '' We add a little margin so that items can't touch - we use half the font size as the margin, so that is 1/4 on each side.
    '' if there is only one character that we're printing, use half of that margin.
    '' var margin = me.dim.font.size/4
    '' if (me.c.length === 1)
    ''  margin = margin / 2
    Dim margin As Double
    margin = 0

    Dim Offset As Double
    If Me.typs = "chord" Then
        Offset = Me.realWidth / 2
    Else
        Offset = 0
    End If
    Dim r As Rect
    
    r.left = Me.x - Offset - margin
    r.right = left + Me.realWidth + margin
    getChordDim = r
End Function

Public Sub invertLane(total As Integer)
    Me.lane = total - Me.lane - 1
End Sub

Public Sub putChordInLane(i As Integer)
    Me.lane = i
    '' Add some extra space to account for the character's descenders.
    If IsEmpty(Me.chordHeightAbove) Then
        Me.chordHeightAbove = (Me.height * 1.25) * Me.lane
    Else
        Me.chordHeightBelow = (Me.height * 1.25) * Me.lane
End Sub

Public Function getLane() As Double
    getLane = Me.lane
End Function

Public Sub setX(x As Double)
    Me.x = x + Me.dx
End Sub


Public Function clone() As RelativeElement
    Dim cope As New RelativeElement
    
                               
    cope.typs = Me.typs
    cope.c = Me.c
    cope.pitch = Me.pitch
    cope.x = Me.x
    cope.w = Me.w
    cope.dx = Me.dx
    cope.scalex = Me.scalex
    cope.scaley = Me.scaley
    cope.pitch2 = Me.pitch2
    cope.lineWidth = Me.lineWidth
    cope.klass = Me.klass
    cope.anchor = Me.anchor
    cope.top = Me.top
    cope.bottom = Me.bottom
    cope.height = Me.height
    cope.Name = Me.Name
    cope.realWidth = Me.realWidth
    cope.centerVertically = Me.centerVertically
Set cope.parent = Me.parent
Set cope.graphelem = Me.graphelem
    cope.stemdir = Me.stemdir
    cope.highestVert = Me.highestVert
Set cope.dim_ = Me.dim_
    cope.position = Me.position
    cope.partHeightAbove = Me.partHeightAbove
    cope.chordHeightAbove = Me.chordHeightAbove
    cope.chordHeightBelow = Me.chordHeightBelow
    cope.lyricHeightAbove = Me.lyricHeightAbove
    cope.lyricHeightBelow = Me.lyricHeightBelow
    cope.lane = Me.lane
    Set clone = cope
End Function

Attribute VB_Name = "RelativeElementList"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
'MIT License
'
'Copyright (c) 2019-2021 Petr Katerinak
'
'Permission is hereby granted, free of charge, to any person obtaining a copy
'of this software and associated documentation files (the "Software"), to deal
'in the Software without restriction, including without limitation the rights
'to use, copy, modify, merge, publish, distribute, sublicense, and/or sell
'copies of the Software, and to permit persons to whom the Software is
'furnished to do so, subject to the following conditions:
'
'The above copyright notice and this permission notice shall be included in all
'copies or substantial portions of the Software.
'
'THE SOFTWARE IS PROVIDED "AS IS", WITHOUT WARRANTY OF ANY KIND, EXPRESS OR
'IMPLIED, INCLUDING BUT NOT LIMITED TO THE WARRANTIES OF MERCHANTABILITY,
'FITNESS FOR A PARTICULAR PURPOSE AND NONINFRINGEMENT. IN NO EVENT SHALL THE
'AUTHORS OR COPYRIGHT HOLDERS BE LIABLE FOR ANY CLAIM, DAMAGES OR OTHER
'LIABILITY, WHETHER IN AN ACTION OF CONTRACT, TORT OR OTHERWISE, ARISING FROM,
'OUT OF OR IN CONNECTION WITH THE SOFTWARE OR THE USE OR OTHER DEALINGS IN THE
'SOFTWARE.
'
' Version of iArray: 1.0
''修正 元素從 0 開始

Private mainArray As New Collection
Private i As Long ' Counter

' #####################
' #    CONSTRUCTOR    #
' #####################
'Private Sub Class_Initialize()
'  Set mainArray = New Collection
'End Sub

' #####################
' #  Getter / Setter  #
' #####################
'Attribute Element.VB_UserMemId = 0 saved in both procedures

'@DefaultMember
Public Property Get element(ByVal index As Long) As RelativeElement
Attribute element.VB_UserMemId = 0
    If index + 1 < 1 Or index + 1 > mainArray.Count Then
        Set element = Nothing
        Exit Property
    End If
    If IsObject(mainArray(index + 1)) = True Then
        Set element = mainArray(index + 1)
    Else
        element = mainArray(index + 1)
    End If

 
End Property

'@DefaultMember
Public Property Let element(ByVal index As Long, ByVal val As RelativeElement)
Attribute element.VB_UserMemId = 0
  If index = 0 And mainArray.Count = 0 Then
    Me.Push val
    Exit Property
  End If
  If index + 1 > mainArray.Count Then
    Dim eMsg As String
    eMsg = IIf(mainArray.Count > 0, _
               "Index (" & index + 1 & ") out of iArray bounds (1-" & mainArray.Count & ")", _
               "iArray doesn't have any indexes")
    err.Raise Number:=9, Description:=eMsg
    Exit Property
  End If
  mainArray.Add val, after:=index + 1
  mainArray.Remove index + 1
End Property

' #############################
' # COMMON COLLECTION METHODS #
' #############################
Public Function Count() As Long
  Count = mainArray.Count
End Function
Public Sub Add(ByVal val As RelativeElement, Optional ByVal bef As Variant = Empty, Optional ByVal aft As Variant = Empty)
  If IsEmpty(bef) And IsEmpty(aft) Then
    mainArray.Add val
  ElseIf IsEmpty(bef) Then
    mainArray.Add val, , , aft
  ElseIf IsEmpty(aft) Then
    mainArray.Add val, , bef
  Else
    mainArray.Add val, , bef, aft
  End If
End Sub
Public Sub Remove(index As Long)
  mainArray.Remove index + 1
End Sub

' ####################
' #  PUBLIC METHODS  #
' ####################

'AddAfter
' Adds element after given index.
' {1,2,3} -> index >= 3 -> Push val
' {1,2,3} -> index < 1 -> Unshift val
' {} -> index = any -> Push val
' @param Long index | Index after which will be added an element
' @param Variant val | One element (String, number, ...) to add into iArray
' @return Long | Count of elements inside iArray
Public Function AddAfter(ByVal index As Long, ByVal val As RelativeElement) As Long
  If Me.Count < 1 Or index + 1 >= Me.Count Then
    Me.Push val
  ElseIf index + 1 < 1 Then
    Me.Unshift val
  Else
    Me.Add val, aft:=index + 1
  End If
  AddAfter = Me.Count
End Function

'AddArrayAfter
' Adds elements after given index.
' {1,2,3} -> index >= 3 -> PushArray val
' {1,2,3} -> index < 1 -> UnshiftArray val
' {} -> index = any -> PushArray val
' @param Long index | Index after which will be added an element
' @param Variant val | Array() or iArray of elements to add into iArray
' @return Long | Count of elements inside iArray
Public Function AddArrayAfter(ByVal index As Long, ByVal val As Variant) As Long
  If Me.Count < 1 Or index + 1 >= Me.Count Then
    Me.PushArray val
  ElseIf index + 1 < 1 Then
    Me.UnshiftArray val
  Else
    If TypeOf val Is RelativeElementList Then
      For i = 0 To val.Count - 1
        Me.Add val(i), aft:=index + 1
        Inc index
      Next i
    Else
      For i = LBound(val) To UBound(val)
        Me.Add val(i), aft:=index + 1
        Inc index
      Next i
    End If
  End If
  AddArrayAfter = Me.Count
End Function

'AddArrayBefore
' Adds elements before given index.
' {1,2,3} -> index > 3 -> PushArray val
' {1,2,3} -> index <= 1 -> UnshiftArray val
' {} -> index = any -> PushArray val
' @param Long index | Index after which will be added an element
' @param Variant val | Array() or iArray of elements to add into iArray
' @return Long | Count of elements inside iArray
Public Function AddArrayBefore(ByVal index As Long, ByVal val As Variant) As Long
  If Me.Count < 1 Or index + 1 > Me.Count Then
    Me.PushArray val
  ElseIf index <= 0 Then
    Me.UnshiftArray val
  Else
    If TypeOf val Is RelativeElementList Then
      For i = val.Count - 1 To 0 Step -1
        Me.Add val(i), bef:=index + 1
      Next i
    Else
      For i = UBound(val) To LBound(val) Step -1
        Me.Add val(i), bef:=index + 1
      Next i
    End If
  End If
  AddArrayBefore = Me.Count
End Function

'AddBefore
' Adds element before given index.
' {1,2,3} -> index > 3 -> Push val
' {1,2,3} -> index <= 1 -> Unshift val
' {} -> index = any -> Push val
' @param Long index | Index before which will be added an element
' @param Variant val | One element (String, number, ...) to add into iArray
' @return Long | Count of elements inside iArray
Public Function AddBefore(ByVal index As Long, ByVal val As RelativeElement) As Long
  If Me.Count < 1 Or index + 1 > Me.Count Then
    Me.Push val
  ElseIf index + 1 <= 1 Then
    Me.Unshift val
  Else
    Me.Add val, bef:=index + 1
  End If
  AddBefore = Me.Count
End Function

'Avg
' Calculates the average of the numeric mainArray.
' @return Variant | Average value / "NaN" if iArray contains non-numeric value(s)
Public Function Avg() As Variant
  If Not Me.ContainsOnlyNumeric Then Avg = "NaN": Exit Function
  Avg = Me.sum / Me.Count
End Function

'Clear
' Empties iArray
Public Function Clear() As Boolean
  For i = mainArray.Count - 1 To 0 Step -1
    mainArray.Remove i + 1
  Next i
  Clear = IIf(mainArray.Count = 0, True, False)
End Function

'Clone
' Makes a hard copy of the mainArray
' @return mainArray | Return exact copy of itself
Public Function clone() As RelativeElementList
  Set clone = New RelativeElementList
  For i = 0 To Me.Count - 1
    clone.Push Me(i)
  Next i
End Function

'Contains
' Checks if given value is used inside mainArray.
' @param Variant val | One element (String, number, ...) to by checked if it exists in iArray
' $return Boolean | True = exists, False = doesn't exists
Public Function Contains(ByVal val As RelativeElement) As Boolean
  Contains = False
  Dim el As Variant
  For Each el In mainArray
    If IsObject(val) = True Or VarType(val) And 8192 Then
        If (VarType(el) And 8192) And (VarType(val) And 8192) Then
            If ArrayDifference(el, val) Then
                Contains = True: Exit Function
            End If
        ElseIf IsObject(el) = True And IsObject(val) = True Then
            If el Is val Then
                Contains = True: Exit Function
            End If
        End If
    Else
        If IsObject(el) = False And (VarType(el) And 8192) <> 8192 Then
            If el = val Then
            Contains = True: Exit Function
            End If
        End If
    End If
  Next el
End Function

'ContainsAll
' Checks if all given values are used inside mainArray.
' @param Variant val | values to by checked if it exists in iArray
' $return Boolean | True = all exists, False = one ore more values doesn't exists
Public Function ContainsAll(ByVal val As RelativeElementList) As Boolean
  ContainsAll = False
  Dim foundOccurrences As Integer: foundOccurrences = 0
  Dim values As New RelativeElementList
  If Not TypeOf val Is RelativeElementList Then
    If IsArray(val) Then
      values.PushArray (val)
    Else
      values.Push (val)
    End If
  Else
    Set values = val
  End If
  For i = 0 To values.Count - 1
    If Me.Contains(values(i)) Then Inc foundOccurrences
  Next i
  If foundOccurrences = values.Count Then ContainsAll = True
End Function

'CountOccurrences
' Checks how many times is given value used inside mainArray.
' @param Variant val | One element (String, number, ...) to by checked
' @return Long | Count of matched occurrences
Public Function CountOccurrences(val As Variant) As Long
  CountOccurrences = 0
  Dim el As Variant
  For Each el In mainArray
  
    If IsObject(val) = True Or VarType(val) And 8192 Then
        If VarType(el) And 8192 And VarType(val) And 8192 Then
            If ArrayDifference(el, val) Then
                Inc CountOccurrences
                Exit Function
            End If
        ElseIf IsObject(el) = True And IsObject(val) = True Then
            If el Is val Then
                Inc CountOccurrences
                Exit Function
            End If
        End If
    Else
        If IsObject(el) = False And Not (VarType(el) And 8192) Then
            If el = val Then
                Inc CountOccurrences
                Exit Function
            End If
        End If
    End If
  
     'If el = val Then Inc CountOccurrences
  Next el
End Function

'Dequeue
' Removes an element from the begining of the mainArray.
' @return Variant | Removed element or Empty, if iArray is empty
'刪除開頭一個元素。
Public Function Dequeue() As RelativeElement
  Dequeue = Empty
  If mainArray.Count > 0 Then
    If VarType(Me(0)) = vbString Then
        Dequeue = Me(0)
    ElseIf TypeOf Me(0) Is RelativeElementList Then
        Set Dequeue = Me(0)
    ElseIf VarType(Me(0)) = vbArray Then
        Set Dequeue = Me(0)
    ElseIf VarType(Me(0)) = vbObject Then
        Set Dequeue = Me(0)
    Else
        Dequeue = Me(0)
    End If
    
    mainArray.Remove 1
  End If
End Function

'Difference
' Checks for number of differences between two arrays, what was added/deleted or combination.
' @param iArray oldArray | Old iArray to be compared with current iArray
' @param String retType | �dd= deleted from old iArray, �aa= added in current iArray, �cc= combination of both (default)
' @return iArray | iArray with differences found
Public Function Difference(ByRef oldArray As RelativeElementList, Optional ByVal retType As String = "c") As RelativeElementList
  Set Difference = New RelativeElementList
  Select Case LCase(retType)
    Case "d"
      For i = 0 To oldArray.Count - 1
        If Me.Contains(oldArray(i)) = False Then Difference.Push oldArray(i)
      Next i
    Case "a"
      For i = 0 To Count - 1
        If oldArray.Contains(Me(i)) = False Then Difference.Push Me(i)
      Next i
    Case "c"
      For i = 0 To oldArray.Count - 1
        If Me.Contains(oldArray(i)) = False Then Difference.Push oldArray(i)
      Next i
      For i = 0 To Count - 1
        If oldArray.Contains(Me(i)) = False Then Difference.Push Me(i)
      Next i
    Case Else
      err.Raise Number:=5, Description:="Unknown Difference return type attribute:" & vbCrLf & _
                                        "Allowed are 'A'dded/'D'eleted/'C'ombination of both"
  End Select
End Function

'DropLeft
' Remove n elements from the beginning of the mainArray. If n > count of iArray elements, all elements are removed.
' @param Long n | Number of elements to be removed
' @return iArray | Array of the removed elements
Public Function DropLeft(ByRef N As Long) As RelativeElementList
  Set DropLeft = New RelativeElementList
  If N > Me.Count Then N = Me.Count
  For i = 0 To N - 1
    DropLeft.Push Me(i)
  Next i
  For i = N - 1 To 0 Step -1
    Me.Remove (i)
  Next i
End Function

'DropRight
' Remove n elements from the end of the mainArray. If n > count of iArray elements, all elements are removed.
' @param Long n | Number of elements to be removed
' @return iArray | Array of the removed elements
Public Function DropRight(ByRef N As Long) As RelativeElementList
  Set DropRight = New RelativeElementList
  If N > Me.Count Then N = Me.Count
  For i = Me.Count - N To Me.Count - 1
    DropRight.Push Me(i)
  Next i
  For i = Me.Count - 1 To Me.Count - N Step -1
    Me.Remove (i)
  Next i
End Function

'Enqueue
' Adds an element at the end of the mainArray.
' @param Variant val | One element (String, number, ...) to add into iArray
' @return Long | Count of elements inside iArray
Public Function Enqueue(ByVal val As Variant) As Long
  Enqueue = Push(val)
End Function

'EnqueueArray
' Adds elements at the end of the iArray
' @param Variant val | Array() or iArray of elements to add into iArray
' @return Long | Count of elements inside array
Public Function EnqueueArray(ByVal val As Variant) As Long
  EnqueueArray = PushArray(val)
End Function

'First
' Returns value of the first element of the mainArray.
' @return Variant | Value of the first element or Empty if iArray is Empty
Public Function First() As RelativeElement
  Set First = IIf(Me.Count > 0, Me(0), Empty)
End Function

'Head
' Returns all elements of iArray, except last one.
' @return iArray | Copy of original array, without last element
Public Function head() As RelativeElementList
  Set head = Me.clone
  head.Pop
End Function

'Intersect
' Search for element that exists in both iArrays.
' @param iArray intArray | iArray to be intersected with current iArray
' @return iArray | Intersected values
Public Function Intersect(ByRef intersectedArr As RelativeElementList) As RelativeElementList
  Set Intersect = New RelativeElementList
  Dim el As Variant
  For Each el In mainArray
    If intersectedArr.Contains(el) Then
      If Not Intersect.Contains(el) Then Intersect.Push (el)
    End If
  Next el
End Function

'ContainsOnlyNumeric
' Verify that all elements are numbers or convertable to numbers
' $return Boolean | True = contains only numeric values, False = contains inconvertible values
Public Function ContainsOnlyNumeric() As Boolean
  ContainsOnlyNumeric = True
  Dim el As Variant
  For Each el In mainArray
    If Not IsNumeric(el) Then ContainsOnlyNumeric = False: Exit Function
  Next el
End Function

'Join
' Joins two iArrays.
' @param iArray jArray | iArray to be joined with current iArray
' @return iArray | Joined iArray
Public Function Join(ByRef joinArr As RelativeElementList) As RelativeElementList
  Set Join = New RelativeElementList
  Join.PushArray Me
  Join.PushArray joinArr
End Function

'Last
' Returns value of the last element of the mainArray.
' @return Variant | Value of the last element or Empty if iArray is Empty
Public Function Last() As RelativeElement
  Set Last = IIf(Me.Count > 0, Me(Me.Count - 1), Empty)
End Function

'OccurrenceIndexes
' Returns all indexes of a value in mainArray.
' @return iArray | iArray containing indexes of occurrence
Public Function OccurenceIndexes(val As Variant) As RelativeElementList
  Set OccurenceIndexes = New RelativeElementList
  For i = 0 To Me.Count - 1
    If Me(i) = val Then
        OccurenceIndexes.Push (i)
    End If
  Next i
End Function

'Pop
' Removes an element from the end of the mainArray.
' @return Variant | Removed element or Empty, if iArray is empty
Public Function Pop() As RelativeElement
  If mainArray.Count > 0 Then
    If VarType(Me(mainArray.Count - 1)) = vbObject Then
       Set Pop = Me(mainArray.Count - 1)
    Else
        Pop = Me(mainArray.Count - 1)
    End If
    mainArray.Remove mainArray.Count
  End If
End Function
  
  

'Push
' Adds an element at the end of the mainArray.
' @param Variant val | One element (String, number, ...) to add into iArray
' @return Long | Count of elements inside iArray
Public Function Push(ByVal val As RelativeElement) As Long
  mainArray.Add val
  Push = mainArray.Count
End Function

'PushArray
' Adds elements at the end of the mainArray.
' @param Variant val | Array() or iArray of elements to add into iArray
' @return Long | Count of elements inside array
Public Function PushArray(ByVal val As Variant) As Long
  If TypeOf val Is RelativeElementList Then
    For i = 0 To val.Count - 1
      Me.Push val(i)
    Next i
  Else
    For i = LBound(val) To UBound(val)
      Me.Push val(i)
    Next i
  End If
  PushArray = Me.Count
End Function

'RemoveDuplicates
' Keeps only the first occurrence of the value. Affects original array
' @return Long | Count of the removed elements
Public Function RemoveDuplicates() As Long
  RemoveDuplicates = 0
  For i = Me.Count - 1 To 0 Step -1
    If Me.CountOccurrences(Me(i)) > 1 Then
      Me.Remove i
      Inc RemoveDuplicates
    End If
  Next i
End Function

'Reverse
' Reverses the content of the iArray
' @return iArray | Reversed iArray
Public Function Reverse() As RelativeElementList
  Set Reverse = New RelativeElementList
  For i = 0 To Me.Count - 1
    Reverse.Unshift Me(i)
  Next i
End Function

'Shift
' Removes an element from the begining of the mainArray.
' @return Variant | Removed element or Empty, if iArray is empty
'轉移
' 從 iArray 的開頭刪除一個元素。
' @返回第一個元素 | 如果 iArray 為空，則刪除元素或為空
Public Function shift() As RelativeElement
  shift = Empty
  If mainArray.Count > 0 Then
    If VarType(Me(0)) = vbString Then
        shift = Me(0)
    ElseIf TypeOf Me(0) Is RelativeElementList Then
        Set shift = Me(0)
    ElseIf VarType(Me(0)) = vbArray Then
        Set shift = Me(0)
    ElseIf VarType(Me(0)) = vbObject Then
        Set shift = Me(0)
    Else
        shift = Me(0)
    End If
    
    mainArray.Remove 1
  End If
End Function

'Shuffle
' Randomly mixes content of the iArray
' @return iArray | Shuffled iArray
' 隨機播放
' 隨機混合 iArray 的內容
'@return iArray | 打亂iArray
Public Function Shuffle() As RelativeElementList
  Set Shuffle = New RelativeElementList
  Dim keys As New RelativeElementList
  For i = 0 To Me.Count - 1
    keys.Push (i)
  Next i
  Dim rndNo As Long
  Do While keys.Count > 0
    rndNo = randomFromTo(0, keys.Count - 1)
    Shuffle.Push Me(keys(rndNo))
    keys.Remove (rndNo)
  Loop
End Function

'Sum
' Calculates the sum of the numeric mainArray.
' @return Variant | Sum value / "NaN" if iArray contains non-numeric value(s)
Public Function sum() As Variant
  If Not Me.ContainsOnlyNumeric Then sum = "NaN": Exit Function
  sum = 0
  Dim el As Variant
  For Each el In mainArray
    sum = sum + el
  Next el
End Function

'Tail
' Returns all elements of iArray, except first one.
' @return iArray | Copy of original array, without first element
'返回陣列中除了第一個元素的剩余元素陣列
Public Function Tail() As RelativeElementList
  Set Tail = Me.clone
  Tail.Dequeue
End Function

Public Function ToList()
  If Me.Count = 0 Then ToList = Null: Exit Function
  Dim tarr()
  ReDim tarr(Me.Count - 1)
  For i = 0 To Me.Count - 1
    If VarType(Me(i)) = vbString Then
        tarr(i) = Me(i)
    ElseIf TypeOf Me(i) Is RelativeElementList Then
        Set tarr(i) = Me(i)
    ElseIf VarType(Me(i)) = vbObject Then
        Set tarr(i) = Me(i)
    Else
        tarr(i) = Me(i)
    End If
  Next i
  ToList = tarr
End Function

'ToString
' Creates string representation of the mainArray.
' @param String delimiter | Optional character to separate the iArray's elements (default = " ")
' @return String | Formated representation of tha iArray
Public Function ToString(Optional ByVal delimiter As String = " ") As String
  If Me.Count = 0 Then ToString = "{}": Exit Function
  ToString = vbNullString
  For i = 0 To Me.Count - 1
    If i = 0 Then ToString = ToString + "{"
    If i > 0 Then ToString = ToString + delimiter
    If VarType(Me(i)) = vbString Then
        ToString = ToString + Chr$(34)
        ToString = ToString + CStr(Me(i))
        ToString = ToString + Chr$(34)
    ElseIf TypeOf Me(i) Is RelativeElementList Then
        ToString = ToString + Me(i).ToString(delimiter)
    ElseIf (VarType(Me(i)) And vbArray) = vbArray Then
        ToString = ToString + "[Array]"
    ElseIf VarType(Me(i)) = vbObject Then
        ToString = ToString + "[Object]"
    Else
        ToString = ToString + CStr(Me(i))
    End If
    
    If i = mainArray.Count - 1 Then ToString = ToString + "}"
  Next i
End Function

'Union
' Combines both iArrays and removes duplicities
' @param iArray uArray | iArray to be unioned with current iArray
' @return iArray | Combined values without duplicities
Public Function Union(ByRef uArr As RelativeElementList) As RelativeElementList
  Set Union = Me.clone
  Union.PushArray uArr
  Union.RemoveDuplicates
End Function

'Unique
' Returns copy of iArray without duplicated values. Original array is not affected
' @return iArray | iArray with unique values
Public Function Unique() As RelativeElementList
  Set Unique = New RelativeElementList
  Dim el As Variant
  For Each el In mainArray
    If Not Unique.Contains(el) Then Unique.Push (el)
  Next el
End Function

'Unshift
' Add an element at the begining of the mainArray.
' @param Variant val | One element (String, number, ...) to add into iArray
' @return Long | Count of elements inside iArray
Public Function Unshift(ByVal val As Variant) As Long
  If mainArray.Count = 0 Then
    Unshift = Push(val)
  Else
    mainArray.Add val, before:=1
    Unshift = mainArray.Count
  End If
End Function

'UnshiftArray
' Add elements at the begining of the mainArray.
' @param Variant val | Array() or iArray of elements to add into iArray
' @return Long | Count of elements inside iArray
Public Function UnshiftArray(ByVal val As Variant) As Long
  If TypeOf val Is RelativeElementList Then
    For i = val.Count - 1 To 0 Step -1
      Unshift val(i)
    Next i
  Else
    For i = UBound(val) To LBound(val) Step -1
      Unshift val(i)
    Next i
  End If
  UnshiftArray = mainArray.Count
End Function


' #####################
' # PRIVATE FUNCTIONS #
' #####################
Sub Inc(ByRef i)
   i = i + 1
End Sub

'Private Function rangeToArray(ByVal rng As Range) As Variant
'  rangeToArray = rng.Value
'End Function

Private Function randomFromTo(ByVal from As Long, ByVal upTo As Long) As Long
  Randomize
  randomFromTo = Int(from + Rnd() * (upTo - from + 1))
End Function

'比對 兩個陣列是否一樣
Private Function ArrayDifference(arr1 As Variant, arr2 As Variant) As Boolean

    Dim i As Integer
    If UBound(arr1) = UBound(arr2) Then
        For i = 0 To UBound(arr1)
            If arr1(i) = arr2(i) Then
                ArrayDifference = True
            Else
                ArrayDifference = False
                Exit Function
            End If
        Next
    Else
        ArrayDifference = False
    End If

End Function

'@Description("changes the contents of the array by removing or replacing existing elements and/or adding new elements in place.")
Public Function Splice( _
        ByVal StartIndex As Long, _
        ParamArray Args() As Variant _
    ) As Variant()
    'Dim LocalItems() As Variant
    Dim ActualStart As Long
    Dim ActualDeleteCount As Long
    Dim ArgsCount As Long
    Dim LocalLength As Long
    Dim LocalArgs() As Variant
    Dim result() As Variant
    Dim i As Long
    Dim TempArray() As Variant
    Dim ItemCount As Long
    Dim TempItems() As Variant
    
    LocalArgs = Args
    'LocalItems = mainArray
    LocalLength = Me.Count
    If StartIndex < LocalLength Then
        ActualStart = StartIndex
    Else
        ActualStart = min(StartIndex, LocalLength)
    End If
    
    ArgsCount = UBound(LocalArgs) + 1
    If ArgsCount = 0 Then
        ' only a start index has been supplied
        ' we're gonna delete everything
        ' 僅提供了起始索引
         '我們要刪除所有內容
        ItemCount = 0
        ActualDeleteCount = LocalLength - ActualStart
    Else
        ' first arg in args is delete count, second onwards are insertion items
        ' args 中的第一個參數是刪除計數，第二個之後是插入項
        ItemCount = ArgsCount - 1
        'deleteCount is first element in args.
        'deleteCount 是 args 中的第一個元素。
        ActualDeleteCount = min(max(Args(LBound(Args)), 0), LocalLength - ActualStart)
    End If
    

    ' get items to be deleted for return val
    ' 取得和刪除
    If ActualDeleteCount > 0 Then
        ReDim result(0 To ActualDeleteCount - 1)
        i = 0
        Do While i < ActualDeleteCount
            If IsObject(Me(ActualStart)) Then
                Set result(i) = Me(ActualStart)
                Me.Remove ActualStart
            Else
                result(i) = Me(ActualStart)
                Me.Remove ActualStart
            End If
            Inc i
        Loop
    Else
        ' return empty array if nothing to be deleted
        ReDim result(0)
    End If
    
    '取得要插入的陣列資料
    If ItemCount > 0 Then
        ReDim TempItems(0 To ItemCount - 1)
        For i = 0 To ItemCount - 1
            If IsObject(LocalArgs(i + 1)) Then
                Set TempItems(i) = LocalArgs(i + 1)
            Else
                TempItems(i) = LocalArgs(i + 1)
            End If
        Next
    Me.AddArrayBefore ActualStart, TempItems
    End If
    
    
    Splice = result
End Function

Attribute VB_Name = "RendererModule"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

 ''    abc_renderer.js: API to render to SVG/Raphael/whatever rendering engine

'/**
' * Implements the API for rendering ABCJS Abstract Rendering Structure to a canvas/paper (e.g. SVG, Raphael, etc)
' * @param {Object} paper
' */
Public paper As SVGmodel      'svg
Public controller As EngraverController
Public space As Double
Public padding As vBox
Public paddingOverride As vBox
Public y As Double
Public abcTune As TuneData

Public path As String
Public isPrint As Boolean
Public lineThickness As Double
Public spacingRenderer As vSpacingRenderer
Public firefox112 As Boolean
Public foregroundColor As String
Public minPadding As Double
Public staffbottom As Double
Public showDebug As Boolean
Public ariaLabel As String


Public Sub init() 'paper As Dictionary)

        Set Me.paper = New SVGmodel  ' new Svg(paper)
        Me.paper.init
        Set Me.controller = Nothing

        Me.space = 3 * spacing.space
        'me.padding = {}   '' renderer's padding is managed by the controller
        Me.reset
        'me.firefox112 = navigator.userAgent.indexOf('Firefox/112.0') >= 0
End Sub


Public Sub reset()

        Me.paper.Clear  'clear()
        Me.y = 0
        Set Me.abcTune = Nothing
        Me.path = ""
        Me.isPrint = False
        Me.lineThickness = 0
        initVerticalSpace
End Sub

Public Sub newTune(abcTune As TuneData)
        Set Me.abcTune = abcTune   '' TODO-PER: this is just to get the font info.
        Me.setVerticalSpace abcTune.formatting
         ''me.measureNumber = null
         ''me.noteNumber = null
        Me.isPrint = (abcTune.media = "print")
        Me.setPadding abcTune
End Sub

 Public Sub setLineThickness(lineThickness As Integer)
        Me.lineThickness = lineThickness
End Sub

Public Sub setPaddingOverride(params As Dictionary)
        Set Me.paddingOverride = New vBox
        With Me.paddingOverride
            .top = params("paddingtop")
            .bottom = params("paddingbottom")
            .right = params("paddingright")
            .left = params("paddingleft")
        End With

End Sub
Public Function getPaddingVariable(self, paddingOverKey, formattingKey, printDefault, screenDefault) As Double
            Dim paddingKey As Double
            If (formattingKey <> 0) Then
                paddingKey = formattingKey
            ElseIf (paddingOverKey <> 0) Then
                paddingKey = paddingOverKey
            ElseIf (self.isPrint) Then
                paddingKey = printDefault
            Else
                paddingKey = screenDefault
            End If
            getPaddingVariable = paddingKey
End Function
Public Sub setPadding(abcTune As TuneData)
         '' If the padding is set in the tune, then use that.
         '' Otherwise, if the padding is set in the override, use that.
         '' Otherwise, use the defaults (there are a different set of defaults for screen and print.)

         '' 1cm x 0.393701in/cm x 72pt/in x 1.33px/pt = 38px
         '' 1.8cm x 0.393701in/cm x 72pt/in x 1.33px/pt = 68px
        Set padding = New vBox
        padding.top = getPaddingVariable(Me, paddingOverride.top, abcTune.formatting.topmargin, 38, 15)
        padding.bottom = getPaddingVariable(Me, paddingOverride.bottom, abcTune.formatting.botmargin, 38, 15)
        padding.left = getPaddingVariable(Me, paddingOverride.left, abcTune.formatting.leftmargin, 68, 15)
        padding.right = getPaddingVariable(Me, paddingOverride.right, abcTune.formatting.rightmargin, 68, 15)
End Sub

'    /**
'     * Some of the items on the page are not scaled, so adjust them in the opposite direction of scaling to cancel out the scaling.
'     * @param {float} scale
'     */
Public Sub adjustNonScaledItems(scale_ As Double)
        Me.padding.top = Me.padding.top / scale_
        Me.padding.bottom = Me.padding.bottom / scale_
        Me.padding.left = Me.padding.left / scale_
        Me.padding.right = Me.padding.right / scale_
        Set Me.abcTune.formatting.headerfont = New vFont        'line 沒有建立 要初始化
        Set Me.abcTune.formatting.footerfont = New vFont        'line 沒有建立 要初始化
        Me.abcTune.formatting.headerfont.size = Me.abcTune.formatting.headerfont.size / scale_
        Me.abcTune.formatting.footerfont.size = Me.abcTune.formatting.footerfont.size / scale_
End Sub

'    /**
'     * Set the the values for all the configurable vertical space options.
'     */
Public Sub initVerticalSpace()
         '' conversion: 37.7953 = conversion factor for cm to px.
         '' All of the following values are in px.
         Set Me.spacingRenderer = New vSpacingRenderer
        With Me.spacingRenderer
            .composer = 7.56   '' Set the vertical space above the composer.
            .graceBefore = 8.67   '' Define the space before, inside and after the grace notes.
            .graceInside = 10.67
            .graceAfter = 16
            .info = 0   '' Set the vertical space above the infoline.
            .lineSkipFactor = 1.1   '' Set the factor for spacing between lines of text. (multiply this by the font size)
            .music = 7.56   '' Set the vertical space above the first staff.
            .paragraphSkipFactor = 0.4   '' Set the factor for spacing between text paragraphs. (multiply this by the font size)
            .parts = 11.33   '' Set the vertical space above a new part.
            .slurHeight = 1#    '' Set the slur height factor.
            .staffSeparation = 61.33   '' Do not put a staff system closer than <unit> from the previous system.
            .stemHeight = 26.67 + 10   '' Set the stem height.
            .subtitle = 3.78   '' Set the vertical space above the subtitle.
            .systemStaffSeparation = 48   '' Do not place the staves closer than <unit> inside a system. * This values applies to all staves when in the tune header. Otherwise, it applies to the next staff
            .text = 18.9   '' Set the vertical space above the history.
            .title = 7.56   '' Set the vertical space above the title.
            .top = 30.24   ''Set the vertical space above the tunes and on the top of the continuation pages.
            .vocal = 0   '' Set the vertical space above the lyrics under the staves.
            .words = 0 '' Set the vertical space above the lyrics at the end of the tune.
        End With
'    /*
'        TODO-PER: Handle the x-coordinate spacing items, too.
'    maxshrink <float>Default: 0.65
'    Set how much to compress horizontally when music line breaks
'    are automatic.
'    <float> must be between 0 (natural spacing)
'    and 1 (max shrinking).
'
'     '' This next value is used to compute the natural spacing of
'     '' the notes. The base spacing of the crotchet is always
'     '' 40 pts. When the duration of a note type is twice the
'     '' duration of an other note type, its spacing is multiplied
'     '' by this factor.
'     '' The default value causes the note spacing to be multiplied
'     '' by 2 when its duration is multiplied by 4, i.e. the
'     '' space of the semibreve is 80 pts and the space of the
'     '' semiquaver is 20 pts.
'     '' Setting this value to 1 sets all note spacing to 40 pts.
'    noteSpacingFactor: 1.414,  '' Set the note spacing factor to <float> (range 1..2).
'
'    scale <float> Default: 0.75 Set the page scale factor. Note that the header and footer are not scaled.
'
'    stretchlast <float>Default: 0.8
'    Stretch the last music line of a tune when it exceeds
'    the <float> fraction of the page width.
'    <float> range is 0.0 to 1.0.
'         */
End Sub

Public Sub setVerticalSpace(formatting As vFormatting)
         '' conversion from pts to px 4/3
        If (formatting.staffsep <> 0) Then Me.spacingRenderer.staffSeparation = formatting.staffsep * 4 / 3
        If (formatting.composerspace <> 0) Then Me.spacingRenderer.composer = formatting.composerspace * 4 / 3
        If (formatting.partsspace <> 0) Then Me.spacingRenderer.parts = formatting.partsspace * 4 / 3
        If (formatting.textspace <> 0) Then Me.spacingRenderer.text = formatting.textspace * 4 / 3
        If (formatting.musicspace <> 0) Then Me.spacingRenderer.music = formatting.musicspace * 4 / 3
        If (formatting.titlespace <> 0) Then Me.spacingRenderer.title = formatting.titlespace * 4 / 3
        If (formatting.sysstaffsep <> 0) Then Me.spacingRenderer.systemStaffSeparation = formatting.sysstaffsep * 4 / 3
        If (formatting.subtitlespace <> 0) Then Me.spacingRenderer.subtitle = formatting.subtitlespace * 4 / 3
        If (formatting.topspace <> 0) Then Me.spacingRenderer.top = formatting.topspace * 4 / 3
        If (formatting.vocalspace <> 0) Then Me.spacingRenderer.vocal = formatting.vocalspace * 4 / 3
        If (formatting.wordsspace <> 0) Then Me.spacingRenderer.words = formatting.wordsspace * 4 / 3
End Sub


'    /**
'     * Calculates the y for a given pitch value (relative to the stave the renderer is currently printing)
'     * @param {number} ofs pitch value (bottom C on a G clef = 0, D=1, etc.)
'     */
Public Function calcY(ofs As Double) As Double
        calcY = Me.y - ofs * spacing.Step
End Function

Public Sub moveY(em As Double, numLines As Integer)
        If (numLines = 0) Then numLines = 1
        Me.y = Me.y + em * numLines
End Sub

Public Sub absolutemoveY(y As Double)
        Me.y = y
End Sub

Attribute VB_Name = "SVGmodel"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit


Const svgNS   As String = "http:''www.w3.org/2000/svg"

Dim sizeCache  As New Dictionary '= {}

Public svg As Dictionary     ' SVGElement
Public currentGroup As iArray      'SVGElement[]
Public dummySvg
Public Sub init() 'wrapper)
        Set Me.svg = createSvg()
        Set Me.currentGroup = New iArray
        'line wrapper.appendChild Me.svg
End Sub

Public Sub Clear()
'        Dim wrapper
'        If Not (Me.svg Is Nothing) Then
'            wrapper = Me.svg.parentNode
'            Me.svg = createSvg()
'            Me.currentGroup = []
'            if (wrapper) {
'                '' TODO-PER: If the wrapper is not present, then the underlying div was pulled out from under this instance. It's possible that is still useful (for creating the music off page?)
'                wrapper.innerHTML = ""
'                wrapper.appendChild (Me.svg)
'            End If
'        End If
End Sub

'    setTitle(title) {
'        var titleEl = document.createElement("title")
'        var titleNode = document.createTextNode(title)
'        titleEl.appendChild(titleNode)
'        me.svg.insertBefore(titleEl, me.svg.firstChild)
'    }
'
'    setResponsiveWidth(w, h) {
'        '' this technique is from: http:''thenewcode.com/744/Make-SVG-Responsive, thx to https:''github.com/iantresman
'        me.svg.setAttribute("viewBox", "0 0 " + w + " " + h)
'        me.svg.setAttribute("preserveAspectRatio", "xMinYMin meet")
'        me.svg.removeAttribute("height")
'        me.svg.removeAttribute("width")
'        me.svg.style['display'] = "inline-block"
'        me.svg.style['position'] = "absolute"
'        me.svg.style['top'] = "0"
'        me.svg.style['left'] = "0"
'
'        if (me.svg.parentNode) {
'            var cls = me.svg.parentNode.getAttribute("class")
'            if (!cls)
'                me.svg.parentNode.setAttribute("class", "abcjs-container")
'            else if (cls.indexOf("abcjs-container") < 0)
'                me.svg.parentNode.setAttribute("class", cls + " abcjs-container")
'            me.svg.parentNode.style['display'] = "inline-block"
'            me.svg.parentNode.style['position'] = "relative"
'            me.svg.parentNode.style['width'] = "100%"
'            '' PER: I changed the padding from 100% to this through trial and error.
'            '' The example was using a square image, but this music might be either wider or taller.
'            var padding = h / w * 100
'            me.svg.parentNode.style['padding-bottom'] = padding + "%"
'            me.svg.parentNode.style['vertical-align'] = "middle"
'            me.svg.parentNode.style['overflow'] = "hidden"
'        }
'    }
'
'    setSize(w, h) {
'        me.svg.setAttribute('width', w)
'        me.svg.setAttribute('height', h)
'    }
'
'    setAttribute(attr, value) {
'        me.svg.setAttribute(attr, value)
'    }
'
'    setScale(scale) {
'        if (scale !== 1) {
'            me.svg.style.transform = "scale(" + scale + "," + scale + ")"
'            me.svg.style['-ms-transform'] = "scale(" + scale + "," + scale + ")"
'            me.svg.style['-webkit-transform'] = "scale(" + scale + "," + scale + ")"
'            me.svg.style['transform-origin'] = "0 0"
'            me.svg.style['-ms-transform-origin-x'] = "0"
'            me.svg.style['-ms-transform-origin-y'] = "0"
'            me.svg.style['-webkit-transform-origin-x'] = "0"
'            me.svg.style['-webkit-transform-origin-y'] = "0"
'        } else {
'            me.svg.style.transform = ""
'            me.svg.style['-ms-transform'] = ""
'            me.svg.style['-webkit-transform'] = ""
'        }
'    }
'
'    insertStyles(styles) {
'        var el = document.createElementNS(svgNS, "style")
'        el.textContent = styles
'        me.svg.insertBefore(el, me.svg.firstChild)  '' prepend is not available on older browsers.
'        ''  me.svg.prepend(el)
'    }
'
'    setParentStyles(attr) {
'        '' This is needed to get the size right when there is scaling involved.
'        for (var key in attr) {
'            if (attr.hasOwnProperty(key)) {
'                if (me.svg.parentNode)
'                    me.svg.parentNode.style[key] = attr[key]
'            }
'        }
'        '' This is the last thing that gets called, so delete the temporary SVG if one was created
'        if (me.dummySvg) {
'            var body = document.querySelector('body')
'            body.removeChild(me.dummySvg)
'            me.dummySvg = null
'        }
'
'    }
'
'
'    rect(attr) {
'        '' This uses path instead of rect so that it can be hollow and the color changes with "fill" instead of "stroke".
'        var lines = []
'        var x1 = attr.x
'        var y1 = attr.y
'        var x2 = attr.x + attr.width
'        var y2 = attr.y + attr.height
'        lines.push(constructHLine(x1, y1, x2))
'        lines.push(constructHLine(x1, y2, x2))
'        lines.push(constructVLine(x2, y1, y2))
'        lines.push(constructVLine(x1, y2, y1))
'
'        return me.path({ path: lines.join(" "), stroke: "none", "data-name": attr["data-name"] })
'    }
'
'    dottedLine(attr) {
'        var el = document.createElementNS(svgNS, 'line')
'        el.setAttribute("x1", attr.x1)
'        el.setAttribute("x2", attr.x2)
'        el.setAttribute("y1", attr.y1)
'        el.setAttribute("y2", attr.y2)
'        el.setAttribute("stroke", attr.stroke)
'        el.setAttribute("stroke-dasharray", "5,5")
'        me.svg.insertBefore(el, me.svg.firstChild)
'    }
'
'    rectBeneath(attr) {
'        var el = document.createElementNS(svgNS, 'rect')
'        el.setAttribute("x", attr.x)
'        el.setAttribute("width", attr.width)
'        el.setAttribute("y", attr.y)
'        el.setAttribute("height", attr.height)
'        if (attr.stroke)
'            el.setAttribute("stroke", attr.stroke)
'        if (attr['stroke-opacity'])
'            el.setAttribute("stroke-opacity", attr['stroke-opacity'])
'        if (attr.fill)
'            el.setAttribute("fill", attr.fill)
'        if (attr['fill-opacity'])
'            el.setAttribute("fill-opacity", attr['fill-opacity'])
'        me.svg.insertBefore(el, me.svg.firstChild)
'    }
'
'    text(text, attr, target?): SVGTextElement {
'        var el = document.createElementNS(svgNS, 'text') as SVGTextElement
'        el.setAttribute("stroke", "none")
'        for (var key in attr) {
'            if (attr.hasOwnProperty(key)) {
'                el.setAttribute(key, attr[key])
'            }
'        }
'        var lines = ("" + text).split("\n")
'        for (var i = 0  i < lines.length  i++) {
'            var line = document.createElementNS(svgNS, 'tspan')
'            line.setAttribute("x", attr.x ? attr.x : 0)
'            if (i !== 0)
'                line.setAttribute("dy", "1.2em")
'            if (lines[i].indexOf("\x03") !== -1) {
'                var parts = lines[i].split('\x03')
'                line.textContent = parts[0]
'                if (parts[1]) {
'                    var ts2 = document.createElementNS(svgNS, 'tspan')
'                    ts2.setAttribute("dy", "-0.3em")
'                    ts2.setAttribute("style", "font-size:0.7em")
'                    ts2.textContent = parts[1]
'                    line.appendChild(ts2)
'                }
'                if (parts[2]) {
'                    var dist = parts[1] ? "0.4em" : "0.1em"
'                    var ts3 = document.createElementNS(svgNS, 'tspan')
'                    ts3.setAttribute("dy", dist)
'                    ts3.setAttribute("style", "font-size:0.7em")
'                    ts3.textContent = parts[2]
'                    line.appendChild(ts3)
'                }
'            } else
'                line.textContent = lines[i]
'            el.appendChild(line)
'        }
'        if (target)
'            target.appendChild(el)
'        Else
'            me.append(el)
'        return el
'    }
'
'    guessWidth(text, attr): { width: number height:number} {
'        var svg = me.createDummySvg()
'        var el = me.text(text, attr, svg)
'        var size: { width: number  height: number }
'        try {
'            size = el.getBBox()
'            if (isNaN(size.height) || !size.height) '' TODO-PER: I don't think this can happen unless there isn't a browser at all.
'                size = { width: attr['font-size'] / 2, height: attr['font-size'] + 2 }  '' Just a wild guess.
'            Else
'                size = { width: size.width, height: size.height }
'        } catch (ex) {
'            size = { width: attr['font-size'] / 2, height: attr['font-size'] + 2 }  '' Just a wild guess.
'        }
'        svg.removeChild(el)
'        return size
'    }
'
'    createDummySvg(): SVGElement {
'        if (!me.dummySvg) {
'            me.dummySvg = createSvg()
'            var styles = [
'                "display: block !important ",
'                "height: 1px ",
'                "width: 1px ",
'                "position: absolute "
'            ]
'            me.dummySvg.setAttribute('style', styles.join(""))
'            var body = document.querySelector('body')
'            body.appendChild(me.dummySvg)
'        }
'
'        return me.dummySvg
'    }
'
'
Public Function getTextSize(text, attr, el As Dictionary)   ': SVGTextElement) {

'        if (typeof text === 'number')
'            text = '' + text
'        if (!text || text.match(/^\s+$/))
'            return { width: 0, height: 0 }
'        var key
'        if (text.length < 20) {
'            '' The short text tends to be repetitive and getBBox is really slow, so lets cache.
'            key = text + JSON.stringify(attr)
'            if (sizeCache[key])
'                return sizeCache[key]
'        }
'        var removeLater = !el
'        if (!el)
'            el = me.text(text, attr)
'        var size
'        try {
'            size = el.getBBox()
'            if (isNaN(size.height) || !size.height)
'                size = me.guessWidth(text, attr)
'            Else
'                size = { width: size.width, height: size.height }
'        } catch (ex) {
'            size = me.guessWidth(text, attr)
'        }
'        if (removeLater) {
'            if (me.currentGroup.length > 0)
'                me.currentGroup[0].removeChild(el)
'            Else
'                me.svg.removeChild(el)
'        }
'        if (key)
'            sizeCache[key] = size
'        return size

End Function
'
'    openGroup(options?) {
'        options = options ? options : {}
'        var el = document.createElementNS(svgNS, "g") as SVGGElement
'        if (options.klass)
'            el.setAttribute("class", options.klass)
'        if (options.fill)
'            el.setAttribute("fill", options.fill)
'        if (options.stroke)
'            el.setAttribute("stroke", options.stroke)
'        if (options['data-name'])
'            el.setAttribute("data-name", options['data-name'])
'
'        if (options.prepend)
'            me.prepend(el)
'        Else
'            me.append(el)
'        me.currentGroup.unshift(el)
'        return el
'    }
'
'    closeGroup() {
'        var g = me.currentGroup.shift()
'        if (g && g.children.length === 0) {
'            '' If nothing was added to the group it is because all the elements were invisible. We don't need the group, then.
'            g.parentElement.removeChild(g)
'            return null
'        }
'        return g
'    }
'
'    path(attr): SVGPathElement {
'        var el = document.createElementNS(svgNS, "path") as SVGPathElement
'        for (var key in attr) {
'            if (attr.hasOwnProperty(key)) {
'                if (key === 'path')
'                    el.setAttributeNS(null, 'd', attr.path)
'                else if (key === 'klass')
'                    el.setAttributeNS(null, "class", attr[key])
'                else if (attr[key] !== undefined)
'                    el.setAttributeNS(null, key, attr[key])
'            }
'        }
'        me.append(el)
'        return el
'    }
'
'    pathToBack(attr): SVGPathElement {
'        var el = document.createElementNS(svgNS, "path") as SVGPathElement
'        for (var key in attr) {
'            if (attr.hasOwnProperty(key)) {
'                if (key === 'path')
'                    el.setAttributeNS(null, 'd', attr.path)
'                else if (key === 'klass')
'                    el.setAttributeNS(null, "class", attr[key])
'                Else
'                    el.setAttributeNS(null, key, attr[key])
'            }
'        }
'        me.prepend(el)
'        return el
'    }
'
'    lineToBack(attr): SVGLineElement {
'        var el = document.createElementNS(svgNS, 'line') as SVGLineElement
'        var Keys = Object.Keys(attr)
'        for (var i = 0  i < keys.length  i++)
'            el.setAttribute(keys[i], attr[keys[i]])
'        me.prepend(el)
'        return el
'    }
'
'
'    append(el: SVGElement) {
'        if (me.currentGroup.length > 0)
'            me.currentGroup[0].appendChild(el)
'        Else
'            me.svg.appendChild(el)
'    }
'
'    prepend(el: SVGElement) {
'        '' The entire group is prepended, so don't prepend the individual elements.
'        if (me.currentGroup.length > 0)
'            me.currentGroup[0].appendChild(el)
'        Else
'            me.svg.insertBefore(el, me.svg.firstChild)
'    }
'
'    setAttributeOnElement(el: SVGElement, attr) {
'        for (var key in attr) {
'            if (attr.hasOwnProperty(key)) {
'                el.setAttributeNS(null, key, attr[key])
'            }
'        }
'    }
'
'    moveElementToChild(parent, child) {
'        parent.appendChild(child)
'    }
'}
'function constructHLine(x1, y1, x2) {
'    var len = x2 - x1
'    return "M " + x1 + " " + y1 +
'        " l " + len + ' ' + 0 +
'        " l " + 0 + " " + 1 + " " +
'        " l " + (-len) + " " + 0 + " " + " z "
'}
'
'function constructVLine(x1, y1, y2) {
'    var len = y2 - y1
'    return "M " + x1 + " " + y1 +
'        " l " + 0 + ' ' + len +
'        " l " + 1 + " " + 0 + " " +
'        " l " + 0 + " " + (-len) + " " + " z "
'}
Public Function createSvg()
'
'    var svg = document.createElementNS(svgNS, "svg")
'    svg.setAttributeNS("http:''www.w3.org/2000/xmlns/", "xmlns:xlink", "http:''www.w3.org/1999/xlink")
'    svg.setAttribute('role', 'img')     '' for accessibility
'    svg.setAttribute('fill', 'currentColor')     '' for automatically picking up dark mode and high contrast
'    svg.setAttribute('stroke', 'currentColor')     '' for automatically picking up dark mode and high contrast
'    return svg as SVGElement
    Set createSvg = Nothing
End Function

Attribute VB_Name = "SetXRecord_test"
Option Explicit
Sub testt()
'測試 setAddXrecord
    Dim arr1(2) As Variant
    Dim a As Variant
    SetXRecord "tlscad", "A", Array(1, 2, "A")
    SetXRecord "tlscad", "B", Array(3, 4, "B")
    a = GetXRecord("tlscad", "A")
    If Not IsNull(a) Then MsgBox a(2)
End Sub


Public Function SetXRecord(ByVal DictName As String, ByVal Keyword As String, ByVal XRecordData)
    Dim pDict As AcadDictionary
    Dim pXRecord As AcadXRecord
    Dim XRecordType() As Integer
    Dim pLen As Integer
    Dim i As Integer
    
    Set pDict = ThisDrawing.Dictionaries.Add(DictName)
    Set pXRecord = pDict.AddXRecord(Keyword)
    
    pLen = UBound(XRecordData)
    ReDim XRecordType(pLen) As Integer
    For i = 0 To pLen
        Select Case VarType(XRecordData(i))
            Case vbInteger, vbLong
                XRecordType(i) = 70
            Case vbSingle, vbDouble
                XRecordType(i) = 40
            Case vbString
                XRecordType(i) = 1
        End Select
    Next i
    
    pXRecord.SetXRecordData XRecordType, XRecordData
End Function
Public Function GetXRecord(ByVal DictName As String, ByVal Keyword As String)
On Error GoTo ErrHandle
    Dim pDict As AcadDictionary
    Dim pXRecord As AcadXRecord
    Dim xt
    Set pDict = ThisDrawing.Dictionaries(DictName)
    Set pXRecord = pDict.GetObject(Keyword)
    pXRecord.GetXRecordData xt, GetXRecord
    Exit Function
ErrHandle:
    GetXRecord = Null
End Function
 
Public Function CreateArray(ByVal TypeName As VbVarType, ParamArray ValArray())
    Dim nCount As Integer
    Dim i
    Dim mArray
    
    nCount = UBound(ValArray)
    
    Select Case TypeName
    Case vbDouble
        Dim dArray() As Double
        ReDim dArray(nCount)
        For i = 0 To nCount
            dArray(i) = ValArray(i)
        Next i
        CreateArray = dArray
    Case vbInteger
        Dim nArray() As Integer
        ReDim nArray(nCount)
        For i = 0 To nCount
            nArray(i) = ValArray(i)
        Next i
        CreateArray = nArray
    Case vbString
        Dim sArray() As String
        ReDim sArray(nCount)
        For i = 0 To nCount
            sArray(i) = ValArray(i)
        Next i
        CreateArray = sArray
    Case vbVariant
        Dim vArray()
        ReDim vArray(nCount)
        For i = 0 To nCount
            vArray(i) = ValArray(i)
        Next i
        CreateArray = vArray
    Case vbObject
        Dim oArray() As Object
        ReDim oArray(nCount)
        For i = 0 To nCount
            Set oArray(i) = ValArray(i)
        Next i
        CreateArray = oArray
    End Select
End Function

Attribute VB_Name = "SpecDefinition"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
''
' SpecDefinition v1.4.0
' (c) Tim Hall - https:''github.com/timhall/Excel-TDD
'
' Provides helpers and acts as workbook proxy
'
' @dependencies
' @author tim.hall.engr@gmail.com
' @license: MIT (http:''www.opensource.org/licenses/mit-license.php)
'
' ~~~~~~~~~~~~~~~~~~~~~~~~~~~~~~~~~~~~~~~~~~~~~~~~~~~~~~~~~~~~~~~~~~~~~~ '

Private pExpectations As Collection
Private pFailedExpectations As Collection

Public Enum SpecResult
    Pass
    Fail
    Pending
End Enum


' ~~~~~~~~~~~~~~~~~~~~~~~~~~~~~~~~~~~~~~ '
' Properties
' ~~~~~~~~~~~~~~~~~~~~~~~~~~~~~~~~~~~~~~ '

Public Description As String
Public ID As String

Public Property Get Expectations() As Collection
    If pExpectations Is Nothing Then
        Set pExpectations = New Collection
    End If
    Set Expectations = pExpectations
End Property
Private Property Let Expectations(value As Collection)
    Set pExpectations = value
End Property

Public Property Get FailedExpectations() As Collection
    If pFailedExpectations Is Nothing Then
        Set pFailedExpectations = New Collection
    End If
    Set FailedExpectations = pFailedExpectations
End Property
Private Property Let FailedExpectations(value As Collection)
    Set pFailedExpectations = value
End Property


' ~~~~~~~~~~~~~~~~~~~~~~~~~~~~~~~~~~~~~~ '
' Public Methods
' ~~~~~~~~~~~~~~~~~~~~~~~~~~~~~~~~~~~~~~ '

''
' Create a new expectation to test the defined value
'
' @param {Variant} value Value to be tested by expectation
' @returns {Expectation}
' --------------------------------------------- '

Public Function Expect(Optional value As Variant) As SpecExpectation
    Dim exp As New SpecExpectation
    
    If VarType(value) = vbObject Then
        Set exp.Actual = value
    Else
        exp.Actual = value
    End If
    Me.Expectations.Add exp
    
    Set Expect = exp
End Function

''
' Run each expectation, store failed expectations, and return result
'
' @returns {SpecResult} Pass/Fail/Pending
' --------------------------------------------- '

Public Function result() As SpecResult
    Dim exp As SpecExpectation
    
    ' Reset failed expectations
    FailedExpectations = New Collection
    
    ' If no expectations have been defined, return pending
    If Me.Expectations.Count < 1 Then
        result = Pending
    Else
        ' Loop through all expectations
        For Each exp In Me.Expectations
            ' If expectation fails, store it
            If exp.result = Fail Then
                FailedExpectations.Add exp
            End If
        Next exp
        
        ' If no expectations failed, spec passes
        If Me.FailedExpectations.Count > 0 Then
            result = Fail
        Else
            result = Pass
        End If
    End If
End Function

''
' Helper to get result name (i.e. "Pass", "Fail", "Pending")
'
' @returns {String}
' --------------------------------------------- '

Public Function ResultName() As String
    Select Case Me.result
        Case Pass: ResultName = "Pass"
        Case Fail: ResultName = "Fail"
        Case Pending: ResultName = "Pending"
    End Select
End Function

Attribute VB_Name = "SpecExpectation"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
''
' SpecExpectation v1.4.0
' (c) Tim Hall - https:''github.com/timhall/Excel-TDD
'
' Provides various tests that can be performed for a provided value
'
' @dependencies
' @author tim.hall.engr@gmail.com
' @license: MIT (http:''www.opensource.org/licenses/mit-license.php)
'
' ~~~~~~~~~~~~~~~~~~~~~~~~~~~~~~~~~~~~~~~~~~~~~~~~~~~~~~~~~~~~~~~~~~~~~~ '

Public Enum ExpectResult
    Pass
    Fail
End Enum

Public Actual As Variant
Public Expected As Variant
Public result As ExpectResult
Public FailureMessage As String


' ~~~~~~~~~~~~~~~~~~~~~~~~~~~~~~~~~~~~~~ '
' Public Methods
' ~~~~~~~~~~~~~~~~~~~~~~~~~~~~~~~~~~~~~~ '

''
' Check if the actual value is equal / not equal to the expected value
'
' @param {Variant} Expected
' --------------------------------------------- '
Public Sub ToEqual(Expected As Variant)
    Check IsEqual(Me.Actual, Expected), "to equal", Expected:=Expected
End Sub
Public Sub ToNotEqual(Expected As Variant)
    Check IsEqual(Me.Actual, Expected), "to not equal", Expected:=Expected, Inverse:=True
End Sub

Private Function IsEqual(Actual As Variant, Expected As Variant) As Variant
    If IsError(Actual) Or IsError(Expected) Then
        IsEqual = False
    ElseIf IsObject(Actual) Or IsObject(Expected) Then
        IsEqual = "Unsupported: Can't compare objects"
    ElseIf VarType(Actual) = vbDouble And VarType(Expected) = vbDouble Then
        ' It is inherently difficult/almost impossible to check equality of Double
        ' http:''support.microsoft.com/kb/78113
        '
        ' Compare up to 15 significant figures
        ' -> Format as scientific notation with 15 significant figures and then compare strings
        IsEqual = IsCloseTo(Actual, Expected, 15)
    Else
        IsEqual = Actual = Expected
    End If
End Function

''
' Check if the actual value is undefined / not undefined
' (Nothing, Empty, Null, or Missing)
' --------------------------------------------- '
Public Sub ToBeDefined()
    Debug.Print "Excel-TDD: DEPRECATED, ToBeDefined() has been deprecated in favor of ToNotBeUndefined and will be removed in Excel-TDD v2.0.0"
    Check IsUndefined(Me.Actual), "to be defined", Inverse:=True
End Sub
Public Sub ToBeUndefined()
    Check IsUndefined(Me.Actual), "to be undefined"
End Sub
Public Sub ToNotBeUndefined()
    Check IsUndefined(Me.Actual), "to not be undefined", Inverse:=True
End Sub

Private Function IsUndefined(Actual As Variant) As Variant
    IsUndefined = IsNothing(Actual) Or IsEmpty(Actual) Or IsNull(Actual) Or IsMissing(Actual)
End Function

''
' Check if the actual value is nothing / not nothing
' --------------------------------------------- '
Public Sub ToBeNothing()
    Check IsNothing(Me.Actual), "to be nothing"
End Sub
Public Sub ToNotBeNothing()
    Check IsNothing(Me.Actual), "to not be nothing", Inverse:=True
End Sub

Private Function IsNothing(Actual As Variant) As Variant
    If IsObject(Actual) Then
        If Actual Is Nothing Then
            IsNothing = True
        Else
            IsNothing = False
        End If
    Else
        IsNothing = False
    End If
End Function

''
' Check if the actual value is empty / not empty
' --------------------------------------------- '
Public Sub ToBeEmpty()
    Check IsEmpty(Me.Actual), "to be empty"
End Sub
Public Sub ToNotBeEmpty()
    Check IsEmpty(Me.Actual), "to not be empty", Inverse:=True
End Sub

''
' Check if the actual value is null / not null
' --------------------------------------------- '
Public Sub ToBeNull()
    Check IsNull(Me.Actual), "to be null"
End Sub
Public Sub ToNotBeNull()
    Check IsNull(Me.Actual), "to not be null", Inverse:=True
End Sub

''
' Check if the actual value is missing / not missing
' --------------------------------------------- '
Public Sub ToBeMissing()
    Check IsMissing(Me.Actual), "to be missing"
End Sub
Public Sub ToNotBeMissing()
    Check IsMissing(Me.Actual), "to not be missing", Inverse:=True
End Sub

''
' Check if the actual value is less than the expected value
'
' @param {Variant} Expected
' --------------------------------------------- '
Public Sub ToBeLessThan(Expected As Variant)
    Check IsLT(Me.Actual, Expected), "to be less than", Expected:=Expected
End Sub
Public Sub ToBeLT(Expected As Variant)
    ToBeLessThan Expected
End Sub

Private Function IsLT(Actual As Variant, Expected As Variant) As Variant
    If IsError(Actual) Or IsError(Expected) Or Actual >= Expected Then
        IsLT = False
    Else
        IsLT = True
    End If
End Function

''
' Check if the actual value is less than or equal to the expected value
'
' @param {Variant} Expected
' --------------------------------------------- '
Public Sub ToBeLessThanOrEqualTo(Expected As Variant)
    Check IsLTE(Me.Actual, Expected), "to be less than or equal to", Expected:=Expected
End Sub
Public Sub ToBeLTE(Expected As Variant)
    ToBeLessThanOrEqualTo Expected
End Sub

Private Function IsLTE(Actual As Variant, Expected As Variant) As Variant
    If IsError(Actual) Or IsError(Expected) Or Actual > Expected Then
        IsLTE = False
    Else
        IsLTE = True
    End If
End Function

''
' Check if the actual value is greater than the expected value
'
' @param {Variant} Expected
' --------------------------------------------- '
Public Sub ToBeGreaterThan(Expected As Variant)
    Check IsGT(Me.Actual, Expected), "to be greater than", Expected:=Expected
End Sub
Public Sub ToBeGT(Expected As Variant)
    ToBeGreaterThan Expected
End Sub

Private Function IsGT(Actual As Variant, Expected As Variant) As Variant
    If IsError(Actual) Or IsError(Expected) Or Actual <= Expected Then
        IsGT = False
    Else
        IsGT = True
    End If
End Function

''
' Check if the actual value is greater than or equal to the expected value
'
' @param {Variant} Expected
' --------------------------------------------- '
Public Sub ToBeGreaterThanOrEqualTo(Expected As Variant)
    Check IsGTE(Me.Actual, Expected), "to be greater than or equal to", Expected:=Expected
End Sub
Public Sub ToBeGTE(Expected As Variant)
    ToBeGreaterThanOrEqualTo Expected
End Sub

Private Function IsGTE(Actual As Variant, Expected As Variant) As Variant
    If IsError(Actual) Or IsError(Expected) Or Actual < Expected Then
        IsGTE = False
    Else
        IsGTE = True
    End If
End Function

''
' Check if the actual value is close to the expected value
'
' @param {Variant} Expected
' @param {Integer} SignificantFigures (1-15)
' --------------------------------------------- '
Public Sub ToBeCloseTo(Expected As Variant, SignificantFigures As Integer)
    Check IsCloseTo(Me.Actual, Expected, SignificantFigures), "to be close to", Expected:=Expected
End Sub
Public Sub ToNotBeCloseTo(Expected As Variant, SignificantFigures As Integer)
    Check IsCloseTo(Me.Actual, Expected, SignificantFigures), "to be close to", Expected:=Expected, Inverse:=True
End Sub

Private Function IsCloseTo(Actual As Variant, Expected As Variant, SignificantFigures As Integer) As Variant
    Dim ActualAsString As String
    Dim ExpectedAsString As String
    
    If SignificantFigures < 1 Or SignificantFigures > 15 Then
        IsCloseTo = "ToBeCloseTo/ToNotBeClose to can only compare from 1 to 15 significant figures"""
    ElseIf Not IsError(Actual) And Not IsError(Expected) Then
        ' Convert values to scientific notation strings and then compare strings
        If Actual > 1 Then
            ActualAsString = VBA.Format$(Actual, VBA.left$("0.00000000000000", SignificantFigures + 1) & "e+0")
        Else
            ActualAsString = VBA.Format$(Actual, VBA.left$("0.00000000000000", SignificantFigures + 1) & "e-0")
        End If
        
        If Expected > 1 Then
            ExpectedAsString = VBA.Format$(Expected, VBA.left$("0.00000000000000", SignificantFigures + 1) & "e+0")
        Else
            ExpectedAsString = VBA.Format$(Expected, VBA.left$("0.00000000000000", SignificantFigures + 1) & "e-0")
        End If
        
        IsCloseTo = ActualAsString = ExpectedAsString
    End If
End Function

''
' Check if the actual value contains the expected value
' Deprecated: Check if the actual value contains the expected value
'
' @param {Variant} Expected
' @param {Boolean} [MatchCase=True] *deprecated
' --------------------------------------------- '
Public Sub ToContain(Expected As Variant, Optional MatchCase As Boolean = True)
    If VarType(Me.Actual) = vbString Then
        Debug.Print "Excel-TDD: DEPRECATED ToContain has been changed to ToMatch in Excel-TDD v2.0.0"
        If MatchCase Then
            Check matches(Me.Actual, Expected), "to match", Expected:=Expected
        Else
            Check matches(VBA.UCase$(Me.Actual), VBA.UCase$(Expected)), "to match", Expected:=Expected
        End If
    Else
        Check Contains(Me.Actual, Expected), "to contain", Expected:=Expected
    End If
End Sub
Public Sub ToNotContain(Expected As Variant, Optional MatchCase As Boolean = True)
    If VarType(Me.Actual) = vbString Then
        Debug.Print "Excel-TDD: DEPRECATED ToNotContain has been changed to ToMatch in Excel-TDD v2.0.0"
        If MatchCase Then
            Check matches(Me.Actual, Expected), "to not match", Expected:=Expected, Inverse:=True
        Else
            Check matches(VBA.UCase$(Me.Actual), VBA.UCase$(Expected)), "to not match", Expected:=Expected, Inverse:=True
        End If
    Else
        Check Contains(Me.Actual, Expected), "to not contain", Expected:=Expected, Inverse:=True
    End If
End Sub

Private Function Contains(Actual As Variant, Expected As Variant) As Variant
    If Not IsArray(Actual) Then
        Contains = "Error: Actual needs to be an Array or Collection for ToContain/ToNotContain"
    Else
        Dim i As Integer
        If TypeOf Actual Is Collection Then
            For i = 1 To Actual.Count
                If Actual.item(i) = Expected Then
                    Contains = True
                    Exit Function
                End If
            Next i
        Else
            For i = LBound(Actual) To UBound(Actual)
                If Actual(i) = Expected Then
                    Contains = True
                    Exit Function
                End If
            Next i
        End If
    End If
End Function

''
' Check if the actual value matches the expected value
' (Only checks if the actual contains the expected string currently)
'
' @param {Variant} Expected
' --------------------------------------------- '
Public Sub ToMatch(Expected As Variant)
    Check matches(Me.Actual, Expected), "to match", Expected:=Expected
End Sub
Public Sub ToNotMatch(Expected As Variant)
    Check matches(Me.Actual, Expected), "to not match", Expected:=Expected, Inverse:=True
End Sub

Private Function matches(Actual As Variant, Expected As Variant) As Variant
    If InStr(Actual, Expected) > 0 Then
        matches = True
    Else
        matches = False
    End If
End Function

''
' Run custom matcher
'
' @example
' .Expect(100).RunMatcher "Module.ToBeWithin", "to be within", 90, 110
'
' Module:
' Public Function ToBeWithin(Actual As Variant, Args As Variant) As Variant
'     If UBound(Args) - LBound(Args) < 1 Then
'         ' Return string for specific failure message
'         ToBeWithin = "Need to pass in upper-bound to ToBeWithin"
'     Else
'         If Actual >= Args(0) And Actual <= Args(1) Then
'             ' Return true for pass
'             ToBeWithin = True
'         Else
'             ' Return false for fail or custom failure message
'             ToBeWithin = False
'         End If
'     End If
' End Function
'
' @param {String} Name of function for matcher
' @param {String} Message
' @param {...} Arguments for custom matcher
' --------------------------------------------- '
Public Sub RunMatcher(Name As String, Message As String, ParamArray Arguments() As Variant)
    Dim Expected As String
    Dim i As Integer
    Dim HasArguments As Boolean
        
    HasArguments = UBound(Arguments) >= 0
    For i = LBound(Arguments) To UBound(Arguments)
        If Expected = "" Then
            Expected = GetStringForValue(Arguments(i))
        ElseIf i = UBound(Arguments) Then
            If (UBound(Arguments) > 1) Then
                Expected = Expected & ", and " & GetStringForValue(Arguments(i))
            Else
                Expected = Expected & " and " & GetStringForValue(Arguments(i))
            End If
        Else
            Expected = Expected & ", " & GetStringForValue(Arguments(i))
        End If
    Next i
    
    If HasArguments Then
        Check Application.Run(Name, Me.Actual, Arguments), Message, Expected:=Expected
    Else
        Check Application.Run(Name, Me.Actual), Message
    End If
End Sub

' ~~~~~~~~~~~~~~~~~~~~~~~~~~~~~~~~~~~~~~ '
' Internal Methods
' ~~~~~~~~~~~~~~~~~~~~~~~~~~~~~~~~~~~~~~ '

Private Sub Check(result As Variant, Message As String, Optional Expected As Variant, Optional Inverse As Boolean = False)
    If Not IsMissing(Expected) Then
        If IsObject(Expected) Then
            Set Me.Expected = Expected
        Else
            Me.Expected = Expected
        End If
    End If
    
    If VarType(result) = vbString Then
        Fails CStr(result)
    Else
        If Inverse Then
            result = Not result
        End If
        
        If result Then
            Passes
        Else
            Fails CreateFailureMessage(Message, Expected)
        End If
    End If
End Sub

Private Sub Passes()
    Me.result = ExpectResult.Pass
End Sub

Private Sub Fails(Message As String)
    Me.result = ExpectResult.Fail
    Me.FailureMessage = Message
End Sub

Private Function CreateFailureMessage(Message As String, Optional Expected As Variant) As String
    CreateFailureMessage = "Expected " & GetStringForValue(Me.Actual) & " " & Message
    If Not IsMissing(Expected) Then
        CreateFailureMessage = CreateFailureMessage & " " & GetStringForValue(Expected)
    End If
End Function

Private Function GetStringForValue(value As Variant) As String
    If IsObject(value) Then
        If value Is Nothing Then
            GetStringForValue = "(Nothing)"
        Else
            GetStringForValue = "(Object)"
        End If
    ElseIf IsArray(value) Then
        GetStringForValue = "(Array)"
    ElseIf IsEmpty(value) Then
        GetStringForValue = "(Empty)"
    ElseIf IsNull(value) Then
        GetStringForValue = "(Null)"
    ElseIf IsMissing(value) Then
        GetStringForValue = "(Missing)"
    Else
        GetStringForValue = CStr(value)
    End If
    
    If GetStringForValue = "" Then
        GetStringForValue = "(Undefined)"
    End If
End Function

Private Function IsArray(value As Variant) As Boolean
    If Not IsEmpty(value) Then
        If IsObject(value) Then
            If TypeOf value Is Collection Then
                IsArray = True
            End If
        ElseIf VarType(value) = vbArray Or VarType(value) = 8204 Then
            ' VarType = 8204 seems to arise from Array(...) constructor
            IsArray = True
        End If
    End If
End Function

Attribute VB_Name = "SpecSuite"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
''
' SpecSuite v1.4.0
' (c) Tim Hall - https:''github.com/timhall/Excel-TDD
'
' A collection of specs with the workbook that they act on
'
' @dependencies
' @author tim.hall.engr@gmail.com
' @license: MIT (http:''www.opensource.org/licenses/mit-license.php)
'
' ~~~~~~~~~~~~~~~~~~~~~~~~~~~~~~~~~~~~~~~~~~~~~~~~~~~~~~~~~~~~~~~~~~~~~~ '

Private pSpecsCol As Collection

' ~~~~~~~~~~~~~~~~~~~~~~~~~~~~~~~~~~~~~~ '
' Properties
' ~~~~~~~~~~~~~~~~~~~~~~~~~~~~~~~~~~~~~~ '

Public Description As String

Public BeforeEachCallback As String
Public BeforeEachCallbackArgs As Variant

Public Property Get SpecsCol() As Collection
    If pSpecsCol Is Nothing Then: Set pSpecsCol = New Collection
    Set SpecsCol = pSpecsCol
End Property
Public Property Let SpecsCol(value As Collection)
    Set pSpecsCol = value
End Property


' ~~~~~~~~~~~~~~~~~~~~~~~~~~~~~~~~~~~~~~ '
' Public Methods
' ~~~~~~~~~~~~~~~~~~~~~~~~~~~~~~~~~~~~~~ '

''
' Create a new spec definition with description
'
' @param {String} Description
' @param {String} [SpecId] Useful for identifying specific specs
' @returns {SpecDefinition} Initialized Spec Definition
' --------------------------------------------- '

Public Function it(Description As String, Optional SpecId As String = "") As SpecDefinition
    Dim Spec As New SpecDefinition
    
    ' Call BeforeEach if defined
    ExecuteBeforeEach
    
    ' Initialize spec
    Spec.Description = Description
    Spec.ID = SpecId
    Me.SpecsCol.Add Spec
    Set it = Spec
End Function

''
' Setup a callback to run before each spec
'
' @param {String} Callback
' @param {...} CallbackArgs any additional arguments to pass as array to callback each time
'
' Example:
' BeforeEach "Cleanup", 100, 200
'
' ' Cleanup is called before each spec with Args = [100, 200]
' Sub Cleanup(Args As Variant)
'   ThisWorkbook.Sheets("Main").Cells(1, 1) = Args(0) ' (100)
'   ThisWorkbook.Sheets("Main").Cells(2, 1) = Args(1) ' (200)
' End Sub
' --------------------------------------------- '

Public Sub BeforeEach(Callback As String, ParamArray CallbackArgs() As Variant)
    Me.BeforeEachCallback = Callback
    Me.BeforeEachCallbackArgs = CallbackArgs
End Sub


' ~~~~~~~~~~~~~~~~~~~~~~~~~~~~~~~~~~~~~~ '
' Internal Methods
' ~~~~~~~~~~~~~~~~~~~~~~~~~~~~~~~~~~~~~~ '

Private Sub ExecuteBeforeEach()
    If Me.BeforeEachCallback <> "" Then
        Dim HasArguments As Boolean
        If VarType(Me.BeforeEachCallbackArgs) = vbObject Then
            If Not Me.BeforeEachCallbackArgs Is Nothing Then
                HasArguments = True
            End If
        ElseIf IsArray(Me.BeforeEachCallbackArgs) Then
            If UBound(Me.BeforeEachCallbackArgs) >= 0 Then
                HasArguments = True
            End If
        End If
    
        If HasArguments Then
            Application.Run Me.BeforeEachCallback, Me.BeforeEachCallbackArgs
        Else
            Application.Run Me.BeforeEachCallback
        End If
    End If
End Sub

Attribute VB_Name = "Specs"
Public Function Specs() As SpecSuite
    Set Specs = New SpecSuite
    Specs.Description = "VBA-JSON"
    
    On Error Resume Next
    
    Dim JsonString As String
    Dim JsonObject As Object
    Dim NestedObject As Object
    Dim EmptyVariant As Variant
    Dim NothingObject As Object
    
    Dim MultiDimensionalArray(1, 1) As Variant
    
    ' ============================================= '
    ' ParseJson
    ' ============================================= '
    
    With Specs.it("should parse object string")
        JsonString = "{""a"":1,""b"":3.14,""c"":""abc"",""d"":false,""e"":[1,3.14,""abc"",false,[1,2,3],{""a"":1}],""f"":{""a"":1},""g"":null}"
        Set JsonObject = JsonConverter.ParseJson(JsonString)
        
        .Expect(JsonObject).ToNotBeUndefined
        .Expect(JsonObject("a")).ToEqual 1
        .Expect(JsonObject("b")).ToEqual 3.14
        .Expect(JsonObject("c")).ToEqual "abc"
        .Expect(JsonObject("d")).ToEqual False
        
        .Expect(JsonObject("e")).ToNotBeUndefined
        .Expect(JsonObject("e")(1)).ToEqual 1
        .Expect(JsonObject("e")(2)).ToEqual 3.14
        .Expect(JsonObject("e")(3)).ToEqual "abc"
        .Expect(JsonObject("e")(4)).ToEqual False
        .Expect(JsonObject("e")(5)).ToNotBeUndefined
        .Expect(JsonObject("e")(5)(1)).ToEqual 1
        .Expect(JsonObject("e")(5)(2)).ToEqual 2
        .Expect(JsonObject("e")(5)(3)).ToEqual 3
        .Expect(JsonObject("e")(6)).ToNotBeUndefined
        .Expect(JsonObject("e")(6)("a")).ToEqual 1
        
        .Expect(JsonObject("f")).ToNotBeUndefined
        .Expect(JsonObject("f")("a")).ToEqual 1
        
        .Expect(JsonObject("g")).ToBeNull
    End With
    
    With Specs.it("should parse array string")
        JsonString = "[1,3.14,""abc"",false,[1,2,3],{""a"":1},null]"
        Set JsonObject = JsonConverter.ParseJson(JsonString)
        
        .Expect(JsonObject).ToNotBeUndefined
        .Expect(JsonObject(1)).ToEqual 1
        .Expect(JsonObject(2)).ToEqual 3.14
        .Expect(JsonObject(3)).ToEqual "abc"
        .Expect(JsonObject(4)).ToEqual False
        .Expect(JsonObject(5)).ToNotBeUndefined
        .Expect(JsonObject(5)(1)).ToEqual 1
        .Expect(JsonObject(5)(2)).ToEqual 2
        .Expect(JsonObject(5)(3)).ToEqual 3
        .Expect(JsonObject(6)).ToNotBeUndefined
        .Expect(JsonObject(6)("a")).ToEqual 1
        .Expect(JsonObject(7)).ToBeNull
    End With
    
    With Specs.it("should parse nested array string")
        JsonString = "[[[1,2,3],4],5]"
        Set JsonObject = JsonConverter.ParseJson(JsonString)
        
        .Expect(JsonObject).ToNotBeUndefined
        .Expect(JsonObject(1)).ToNotBeUndefined
        .Expect(JsonObject(1)(1)).ToNotBeUndefined
        .Expect(JsonObject(1)(1)(1)).ToEqual 1
        .Expect(JsonObject(1)(1)(2)).ToEqual 2
        .Expect(JsonObject(1)(1)(3)).ToEqual 3
        .Expect(JsonObject(1)(2)).ToEqual 4
        .Expect(JsonObject(2)).ToEqual 5
    End With
    
    With Specs.it("should parse escaped single quote in key and value")
        ' Checks https:''code.google.com/p/vba-json/issues/detail?id=2
        JsonString = "{'a\'b':'c\'d'}"
        Set JsonObject = JsonConverter.ParseJson(JsonString)
        
        .Expect(JsonObject).ToNotBeUndefined
        .Expect(JsonObject.Exists("a'b")).ToEqual True
        .Expect(JsonObject("a'b")).ToEqual "c'd"
    End With
    
    With Specs.it("should parse nested objects and arrays")
        ' Checks https:''code.google.com/p/vba-json/issues/detail?id=7
        JsonString = "{""total_rows"":36778,""offset"":26220,""rows"":[" & vbNewLine & _
            "{""id"":""6b80c0b76"",""key"":""a@bbb.net"",""value"":{""entryid"":""81151F241C2500"",""subject"":""test subject"",""senton"":""2009-7-09 22:03:43""}}," & vbNewLine & _
            "{""id"":""b10ed9bee"",""key"":""b@bbb.net"",""value"":{""entryid"":""A7C3CF74EA95C9F"",""subject"":""test subject2"",""senton"":""2009-4-21 10:18:26""}}" & vbNewLine & _
        "]}"
        Set JsonObject = JsonConverter.ParseJson(JsonString)
        
        .Expect(JsonObject).ToNotBeUndefined
        .Expect(JsonObject("offset")).ToEqual 26220
        .Expect(JsonObject("rows")(2)("key")).ToEqual "b@bbb.net"
    End With
    
    With Specs.it("should handle very long numbers as strings (e.g. BIGINT)")
        JsonString = "[123456789012345678901234567890, 1.123456789012345678901234567890, 123456789012345, 1.23456789012345]"
        Set JsonObject = JsonConverter.ParseJson(JsonString)
        
        .Expect(JsonObject).ToNotBeUndefined
        .Expect(JsonObject(1)).ToEqual "123456789012345678901234567890"
        .Expect(JsonObject(2)).ToEqual "1.123456789012345678901234567890"
        .Expect(JsonObject(3)).ToEqual 123456789012345#
        .Expect(JsonObject(4)).ToEqual 1.23456789012345
        
        JsonConverter.JsonOptions.UseDoubleForLargeNumbers = True
        JsonString = "[123456789012345678901234567890]"
        Set JsonObject = JsonConverter.ParseJson(JsonString)
        
        .Expect(JsonObject).ToNotBeUndefined
        .Expect(JsonObject(1)).ToEqual 1.23456789012346E+29
        JsonConverter.JsonOptions.UseDoubleForLargeNumbers = False
    End With
    
    With Specs.it("should parse double-backslash as backslash")
        ' Checks https:''code.google.com/p/vba-json/issues/detail?id=11
        JsonString = "[""C:\\folder\\picture.jpg""]"
        Set JsonObject = JsonConverter.ParseJson(JsonString)
        
        .Expect(JsonObject).ToNotBeUndefined
        .Expect(JsonObject(1)).ToEqual "C:\folder\picture.jpg"
    End With
    
    With Specs.it("should allow keys and values with colons")
        ' Checks https:''code.google.com/p/vba-json/issues/detail?id=14
        JsonString = "{""a:b"":""c:d""}"
        Set JsonObject = JsonConverter.ParseJson(JsonString)
        
        .Expect(JsonObject).ToNotBeUndefined
        .Expect(JsonObject.Exists("a:b")).ToEqual True
        .Expect(JsonObject("a:b")).ToEqual "c:d"
    End With
    
    With Specs.it("should allow spaces in keys")
        ' Checks https:''code.google.com/p/vba-json/issues/detail?id=19
        JsonString = "{""a b  c"":""d e  f""}"
        Set JsonObject = JsonConverter.ParseJson(JsonString)
        
        .Expect(JsonObject).ToNotBeUndefined
        .Expect(JsonObject.Exists("a b  c")).ToEqual True
        .Expect(JsonObject("a b  c")).ToEqual "d e  f"
    End With
    
    With Specs.it("should allow unquoted keys with option")
        JsonConverter.JsonOptions.AllowUnquotedKeys = True
        JsonString = "{a:""a"",b     :""b""}"
        Set JsonObject = JsonConverter.ParseJson(JsonString)

        .Expect(JsonObject).ToNotBeUndefined
        .Expect(JsonObject.Exists("a")).ToEqual True
        .Expect(JsonObject("a")).ToEqual "a"
        .Expect(JsonObject.Exists("b")).ToEqual True
        .Expect(JsonObject("b")).ToEqual "b"
        JsonConverter.JsonOptions.AllowUnquotedKeys = False
    End With
    
    ' ============================================= '
    ' ConvertToJson
    ' ============================================= '
    
    With Specs.it("should convert object to string")
        Set JsonObject = New Dictionary
        JsonObject.Add "a", 1
        JsonObject.Add "b", 3.14
        JsonObject.Add "c", "abc"
        JsonObject.Add "d", False
        JsonObject.Add "e", New Collection
        JsonObject("e").Add 1
        JsonObject("e").Add 3.14
        JsonObject("e").Add "abc"
        JsonObject("e").Add False
        JsonObject("e").Add Array(1, 2, 3)
        JsonObject("e").Add New Dictionary
        JsonObject("e")(6).Add "a", 1
        JsonObject.Add "f", New Dictionary
        JsonObject("f").Add "a", 1
        JsonObject.Add "g", Null
        
        JsonString = JsonConverter.ConvertToJson(JsonObject)
        .Expect(JsonString).ToEqual "{""a"":1,""b"":3.14,""c"":""abc"",""d"":false,""e"":[1,3.14,""abc"",false,[1,2,3],{""a"":1}],""f"":{""a"":1},""g"":null}"
    End With
    
    With Specs.it("should convert collection to string")
        Set JsonObject = New Collection
        JsonObject.Add 1
        JsonObject.Add 3.14
        JsonObject.Add "abc"
        JsonObject.Add False
        JsonObject.Add Array(1, 2, 3)
        JsonObject.Add New Dictionary
        JsonObject(6).Add "a", 1
        JsonObject.Add Null
    
        JsonString = JsonConverter.ConvertToJson(JsonObject)
        .Expect(JsonString).ToEqual "[1,3.14,""abc"",false,[1,2,3],{""a"":1},null]"
    End With
    
    With Specs.it("should convert array to string")
        JsonString = JsonConverter.ConvertToJson(Array(1, 3.14, "abc", False, Array(1, 2, 3)))
        .Expect(JsonString).ToEqual "[1,3.14,""abc"",false,[1,2,3]]"
    End With
    
    With Specs.it("should convert very long numbers as strings (e.g. BIGINT)")
        JsonString = JsonConverter.ConvertToJson(Array("123456789012345678901234567890", "1.123456789012345678901234567890", "1234567890123456F"))
        .Expect(JsonString).ToEqual "[123456789012345678901234567890,1.123456789012345678901234567890,""1234567890123456F""]"
        
        JsonConverter.JsonOptions.UseDoubleForLargeNumbers = True
        JsonString = JsonConverter.ConvertToJson(Array("123456789012345678901234567890"))
        .Expect(JsonString).ToEqual "[""123456789012345678901234567890""]"
        JsonConverter.JsonOptions.UseDoubleForLargeNumbers = False
    End With
    
    With Specs.it("should convert dates to ISO 8601")
        JsonString = JsonConverter.ConvertToJson(DateSerial(2003, 1, 15) + TimeSerial(12, 5, 6))
        
        ' Due to UTC conversion, test shape and year, month, and seconds
        .Expect(JsonString).ToMatch "2003-01-"
        .Expect(JsonString).ToMatch "T"
        .Expect(JsonString).ToMatch ":06.000Z"
    End With
    
    With Specs.it("should convert 2D arrays")
        ' Checks https:''code.google.com/p/vba-json/issues/detail?id=8
        MultiDimensionalArray(0, 0) = 1
        MultiDimensionalArray(0, 1) = 2
        MultiDimensionalArray(1, 0) = 3
        MultiDimensionalArray(1, 1) = 4
        JsonString = JsonConverter.ConvertToJson(MultiDimensionalArray)
        .Expect(JsonString).ToEqual "[[1,2],[3,4]]"
    End With
    
    With Specs.it("should handle strongly typed arrays")
        Dim LongArray(3) As Long
        LongArray(0) = 1
        LongArray(1) = 2
        LongArray(2) = 3
        LongArray(3) = 4
        
        JsonString = JsonConverter.ConvertToJson(LongArray)
        .Expect(JsonString).ToEqual "[1,2,3,4]"
        
        Dim StringArray(3) As String
        StringArray(0) = "A"
        StringArray(1) = "B"
        StringArray(2) = "C"
        StringArray(3) = "D"
        
        JsonString = JsonConverter.ConvertToJson(StringArray)
        .Expect(JsonString).ToEqual "[""A"",""B"",""C"",""D""]"
    End With
    
    With Specs.it("should json-encode strings")
        Dim Strings As Variant
        Strings = Array("""\" & vbCr & vbLf & vbTab & vbBack & vbFormFeed, ChrW(128) & ChrW(32767), "#$%&{|}~")
        
        JsonString = JsonConverter.ConvertToJson(Strings)
        .Expect(JsonString).ToEqual "[""\""\\\r\n\t\b\f"",""\u0080\u7FFF"",""#$%&{|}~""]"
    End With
    
    With Specs.it("should escape solidus with option")
        Strings = Array("a/b")
        
        JsonString = JsonConverter.ConvertToJson(Strings)
        .Expect(JsonString).ToEqual "[""a/b""]"
        
        JsonConverter.JsonOptions.EscapeSolidus = True
        JsonString = JsonConverter.ConvertToJson(Strings)
        .Expect(JsonString).ToEqual "[""a\/b""]"
        JsonConverter.JsonOptions.EscapeSolidus = False
    End With
    
    With Specs.it("should handle Empty and Nothing in arrays as null")
        JsonString = JsonConverter.ConvertToJson(Array("a", EmptyVariant, NothingObject, Empty, Nothing, "z"))
        .Expect(JsonString).ToEqual "[""a"",null,null,null,null,""z""]"

        Set JsonObject = New Collection
        JsonObject.Add "a"
        JsonObject.Add EmptyVariant
        JsonObject.Add NothingObject
        JsonObject.Add Empty
        JsonObject.Add Nothing
        JsonObject.Add ""
        JsonObject.Add "z"
    
        JsonString = JsonConverter.ConvertToJson(JsonObject)
        .Expect(JsonString).ToEqual "[""a"",null,null,null,null,"""",""z""]"
    End With
    
    With Specs.it("should handle Empty and Nothing in objects as undefined")
        Set JsonObject = New Dictionary
        JsonObject.Add "a", "a"
        JsonObject.Add "b", EmptyVariant
        JsonObject.Add "c", NothingObject
        JsonObject.Add "d", Empty
        JsonObject.Add "e", Nothing
        JsonObject.Add "f", ""
        JsonObject.Add "z", "z"
        
        JsonString = JsonConverter.ConvertToJson(JsonObject)
        .Expect(JsonString).ToEqual "{""a"":""a"",""f"":"""",""z"":""z""}"
    End With
    
    With Specs.it("should use whitespace number/string")
        ' Nested, plain array + 2
        JsonString = JsonConverter.ConvertToJson(Array(1, Array(2, Array(3))), 2)
        .Expect(JsonString).ToEqual _
            "[" & vbNewLine & _
            "  1," & vbNewLine & _
            "  [" & vbNewLine & _
            "    2," & vbNewLine & _
            "    [" & vbNewLine & _
            "      3" & vbNewLine & _
            "    ]" & vbNewLine & _
            "  ]" & vbNewLine & _
            "]"
        
        ' Nested Dictionary + Tab
        Set JsonObject = New Dictionary
        JsonObject.Add "a", Array(1, 2, 3)
        JsonObject.Add "b", "c"
        Set NestedObject = New Dictionary
        NestedObject.Add "d", "e"
        JsonObject.Add "nested", NestedObject
        
        JsonString = JsonConverter.ConvertToJson(JsonObject, VBA.vbTab)
        .Expect(JsonString).ToEqual _
            "{" & vbNewLine & _
            vbTab & """a"": [" & vbNewLine & _
            vbTab & vbTab & "1," & vbNewLine & _
            vbTab & vbTab & "2," & vbNewLine & _
            vbTab & vbTab & "3" & vbNewLine & _
            vbTab & "]," & vbNewLine & _
            vbTab & """b"": ""c""," & vbNewLine & _
            vbTab & """nested"": {" & vbNewLine & _
            vbTab & vbTab & """d"": ""e""" & vbNewLine & _
            vbTab & "}" & vbNewLine & _
            "}"
            
        ' Multi-dimensional array + 4
        MultiDimensionalArray(0, 0) = 1
        MultiDimensionalArray(0, 1) = 2
        MultiDimensionalArray(1, 0) = Array(1, 2, 3)
        MultiDimensionalArray(1, 1) = 4
        JsonString = JsonConverter.ConvertToJson(MultiDimensionalArray, 4)
        .Expect(JsonString).ToEqual _
            "[" & vbNewLine & _
            "    [" & vbNewLine & _
            "        1," & vbNewLine & _
            "        2" & vbNewLine & _
            "    ]," & vbNewLine & _
            "    [" & vbNewLine & _
            "        [" & vbNewLine & _
            "            1," & vbNewLine & _
            "            2," & vbNewLine & _
            "            3" & vbNewLine & _
            "        ]," & vbNewLine & _
            "        4" & vbNewLine & _
            "    ]" & vbNewLine & _
            "]"
        
        ' Collection + "-"
        Set JsonObject = New Collection
        JsonObject.Add Array(1, 2, 3)
        
        JsonString = JsonConverter.ConvertToJson(JsonObject, "-")
        .Expect(JsonString).ToEqual _
            "[" & vbNewLine & _
            "-[" & vbNewLine & _
            "--1," & vbNewLine & _
            "--2," & vbNewLine & _
            "--3" & vbNewLine & _
            "-]" & vbNewLine & _
            "]"
    End With
    
    ' ============================================= '
    ' Errors
    ' ============================================= '
    
    With Specs.it("should have descriptive parsing errors")
        err.Clear
        JsonString = "Howdy!"
        Set JsonObject = JsonConverter.ParseJson(JsonString)
        
        .Expect.RunMatcher "ToMatchParseError", "to match parse error", _
            "Howdy!", "^", "Expecting '{' or '['"
        
        err.Clear
        JsonString = "{""abc""}"
        Set JsonObject = JsonConverter.ParseJson(JsonString)
        
        .Expect.RunMatcher "ToMatchParseError", "to match parse error", _
            "{""abc""}", "      ^", "Expecting ':'"
        
        err.Clear
        JsonString = "{""abc"":True}"
        Set JsonObject = JsonConverter.ParseJson(JsonString)
        
        .Expect.RunMatcher "ToMatchParseError", "to match parse error", _
            "{""abc"":True}", "       ^", "Expecting 'STRING', 'NUMBER', null, true, false, '{', or '['"
        
        err.Clear
        JsonString = "{""abc"":undefined}"
        Set JsonObject = JsonConverter.ParseJson(JsonString)
        
        .Expect.RunMatcher "ToMatchParseError", "to match parse error", _
            "{""abc"":undefined}", "       ^", "Expecting 'STRING', 'NUMBER', null, true, false, '{', or '['"
    End With
    
    InlineRunner.RunSuite Specs
End Function

Public Sub RunSpecs()
    DisplayRunner.IdCol = 1
    DisplayRunner.DescCol = 1
    DisplayRunner.ResultCol = 2
    DisplayRunner.OutputStartRow = 4
    
    DisplayRunner.RunSuite Specs
End Sub

Public Function ToMatchParseError(Actual As Variant, Args As Variant) As Variant
    Dim Partial As String
    Dim Arrow As String
    Dim Message As String
    Dim Description As String
    
    If UBound(Args) < 2 Then
        ToMatchParseError = "Need to pass expected partial, arrow, and message"""
    ElseIf err.Number = 10001 Then
        Partial = Args(0)
        Arrow = Args(1)
        Message = Args(2)
        Description = "Error parsing JSON:" & vbNewLine & Partial & vbNewLine & Arrow & vbNewLine & Message
        
        Dim parts As Variant
        parts = Split(err.Description, vbNewLine)
        
        If parts(1) <> Partial Then
            ToMatchParseError = "Expected " & parts(1) & " to equal " & Partial
        ElseIf parts(2) <> Arrow Then
            ToMatchParseError = "Expected " & parts(2) & " to equal " & Arrow
        ElseIf parts(3) <> Message Then
            ToMatchParseError = "Expected " & parts(3) & " to equal " & Message
        ElseIf err.Description <> Description Then
            ToMatchParseError = "Expected " & err.Description & " to equal " & Description
        Else
            ToMatchParseError = True
        End If
    Else
        ToMatchParseError = "Expected error number " & err.Number & " to be 10001"
    End If
End Function

Attribute VB_Name = "Staff"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public barNumber As Integer
Public brace As String     'BracePosition
Public bracket As String     'BracePosition
Public clef As vClefProperties
Public connectBarLines As String    'BracePosition
Public annotationfont As vFont
Public gchordfont As vFont
Public tripletfont As vFont
Public vocalfont As vFont
Public key As vKeySignature
Public meter As vMeter
Public spacingAbove As Double
Public spacingBelow As Double
Public stafflines As Integer
Public isJianpu As Boolean
Public staffscale As Double
Public title As iArray    ' Array<string>
Public voices As MusicItemList  'iArray 'VoiceABCList        'Array<Array<VoiceItem>>

Attribute VB_Name = "StaffGroupElement"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public line As Integer
Public startX As Double
Public w As Double
Public height As Double
Public gTextSize As getTextSize
Public voices As VoiceElementList   ' VoiceElement
Public staffInfos As vStaffInfoList
Public brace As BraceElemList
Public bracket As BraceElemList

Private sa_(100) As size
Private saIs As New Dictionary
Public spacingUnits As Double   '記錄這行的空白單位
Public minSpace As Double       '記錄這行的 最小空白單位

Public Property Get sa(index As Integer) As size
    If saIs(index) = True Then
        sa = sa_(index)
        Exit Property
    ElseIf UBound(sa_) >= index Then
        sa = Empty
    End If
End Property

Public Property Let sa(index As Integer, si As size)
    If UBound(sa_) >= index Then
        sa_(index) = si
        saIs(index) = True
    Else
        'ReDim Me.sa_(index * 2)
        sa_(index) = si
        saIs(index) = True
    End If
    
End Property

Public Sub init(gTextSize As getTextSize)

        Set Me.gTextSize = gTextSize
        Set Me.voices = New VoiceElementList
        Set Me.staffInfos = New vStaffInfoList
        Set Me.brace = New BraceElemList  ''tony
        Set Me.bracket = New BraceElemList

End Sub

Public Sub setLimit(member As String, voice As VoiceElement)
        If (voice.specialY(member) Is Nothing) Then Exit Sub
        If (voice.Staff.specialY(member) Is Nothing) Then
            voice.Staff.specialY(member) = voice.specialY(member)
        Else
            voice.Staff.specialY(member) = Math.max(voice.Staff.specialY(member), voice.specialY(member))
        End If
End Sub

Public Sub addVoice(voice As VoiceElement, staffnumber As Integer, stafflines As Integer)
        Dim voiceNum As Integer
        Dim staffEle As vStaffInfo
        Dim zeor0
        voiceNum = Me.voices.Count
        Me.voices.Push voice
        If Not (Me.staffInfos(staffnumber) Is Nothing) Then
            Me.staffInfos(staffnumber).voices.Push (voiceNum)
        Else
            '' TODO-PER: how does the min/max change when stafflines is not 5?
            Set staffEle = New vStaffInfo
            staffEle.top = 10
            staffEle.bottom = 2
            staffEle.lines = stafflines
            staffEle.voices.Push voiceNum
            zeor0 = 0
            Dim spY As New Dictionary
            spY("tempoHeightAbove") = 0
            spY("partHeightAbove") = 0
            spY("volumeHeightAbove") = 0
            spY("dynamicHeightAbove") = 0
            spY("endingHeightAbove") = 0
            spY("chordHeightAbove") = 0
            spY("lyricHeightAbove") = 0
            spY("lyricHeightBelow") = 0
            spY("chordHeightBelow") = 0
            spY("volumeHeightBelow") = 0
            spY("dynamicHeightBelow") = 0
            Set staffEle.specialY = spY
            
            Me.staffInfos.Push staffEle
        End If
        Set voice.staffInfo = Me.staffInfos(staffnumber)
End Sub

Public Sub setHeight()
        Me.height = calcHeight(Me)
End Sub

Public Sub setWidth(width As Double)
        Dim i As Integer
        Me.w = width
        For i = 0 To Me.voices.Count - 1
            Call Me.voices(i).setWidth(width)
        Next
End Sub

Public Sub setStaffLimits(voice As VoiceElement)
        voice.Staff.top = Math.max(voice.Staff.top, voice.top)
        voice.Staff.bottom = Math.min(voice.Staff.bottom, voice.bottom)
        Me.setLimit "tempoHeightAbove", voice
        Me.setLimit "partHeightAbove", voice
        Me.setLimit "volumeHeightAbove", voice
        Me.setLimit "dynamicHeightAbove", voice
        Me.setLimit "endingHeightAbove", voice
        Me.setLimit "chordHeightAbove", voice
        Me.setLimit "lyricHeightAbove", voice
        Me.setLimit "lyricHeightBelow", voice
        Me.setLimit "chordHeightBelow", voice
        Me.setLimit "volumeHeightBelow", voice
        Me.setLimit "dynamicHeightBelow", voice
    
End Sub

Attribute VB_Name = "StaffList"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
'MIT License
'
'Copyright (c) 2019-2021 Petr Katerinak
'
'Permission is hereby granted, free of charge, to any person obtaining a copy
'of this software and associated documentation files (the "Software"), to deal
'in the Software without restriction, including without limitation the rights
'to use, copy, modify, merge, publish, distribute, sublicense, and/or sell
'copies of the Software, and to permit persons to whom the Software is
'furnished to do so, subject to the following conditions:
'
'The above copyright notice and this permission notice shall be included in all
'copies or substantial portions of the Software.
'
'THE SOFTWARE IS PROVIDED "AS IS", WITHOUT WARRANTY OF ANY KIND, EXPRESS OR
'IMPLIED, INCLUDING BUT NOT LIMITED TO THE WARRANTIES OF MERCHANTABILITY,
'FITNESS FOR A PARTICULAR PURPOSE AND NONINFRINGEMENT. IN NO EVENT SHALL THE
'AUTHORS OR COPYRIGHT HOLDERS BE LIABLE FOR ANY CLAIM, DAMAGES OR OTHER
'LIABILITY, WHETHER IN AN ACTION OF CONTRACT, TORT OR OTHERWISE, ARISING FROM,
'OUT OF OR IN CONNECTION WITH THE SOFTWARE OR THE USE OR OTHER DEALINGS IN THE
'SOFTWARE.
'
' Version of iArray: 1.0
''修正 元素從 0 開始

Private mainArray As New Collection
Private i As Long ' Counter

' #####################
' #    CONSTRUCTOR    #
' #####################
'Private Sub Class_Initialize()
'  Set mainArray = New Collection
'End Sub

' #####################
' #  Getter / Setter  #
' #####################
'Attribute Element.VB_UserMemId = 0 saved in both procedures

'@DefaultMember
Public Property Get element(ByVal index As Long) As Staff
Attribute element.VB_UserMemId = 0
    If index + 1 < 1 Or index + 1 > mainArray.Count Then
        Set element = Nothing
        Exit Property
    End If
    If IsObject(mainArray(index + 1)) = True Then
        Set element = mainArray(index + 1)
    Else
        element = mainArray(index + 1)
    End If

 
End Property

'@DefaultMember
Public Property Let element(ByVal index As Long, ByVal val As Staff)
Attribute element.VB_UserMemId = 0
  If index = 0 And mainArray.Count = 0 Then
    Me.Push val
  If index + 1 > mainArray.Count Then
    Dim eMsg As String
    eMsg = IIf(mainArray.Count > 0, _
               "Index (" & index + 1 & ") out of iArray bounds (1-" & mainArray.Count & ")", _
               "iArray doesn't have any indexes")
    err.Raise Number:=9, Description:=eMsg
    Exit Property
  End If
  mainArray.Remove index + 1
  mainArray.Add val, before:=index
End Property

' #############################
' # COMMON COLLECTION METHODS #
' #############################
Public Function Count() As Long
  Count = mainArray.Count
End Function
Public Sub Add(ByVal val As Staff, Optional ByVal bef As Variant = Empty, Optional ByVal aft As Variant = Empty)
  If IsEmpty(bef) And IsEmpty(aft) Then
    mainArray.Add val
  ElseIf IsEmpty(bef) Then
    mainArray.Add val, , , aft
  ElseIf IsEmpty(aft) Then
    mainArray.Add val, , bef
  Else
    mainArray.Add val, , bef, aft
  End If
End Sub
Public Sub Remove(index As Long)
  mainArray.Remove index + 1
End Sub

' ####################
' #  PUBLIC METHODS  #
' ####################

'AddAfter
' Adds element after given index.
' {1,2,3} -> index >= 3 -> Push val
' {1,2,3} -> index < 1 -> Unshift val
' {} -> index = any -> Push val
' @param Long index | Index after which will be added an element
' @param Variant val | One element (String, number, ...) to add into iArray
' @return Long | Count of elements inside iArray
Public Function AddAfter(ByVal index As Long, ByVal val As Staff) As Long
  If Me.Count < 1 Or index + 1 >= Me.Count Then
    Me.Push val
  ElseIf index + 1 < 1 Then
    Me.Unshift val
  Else
    Me.Add val, aft:=index + 1
  End If
  AddAfter = Me.Count
End Function

'AddArrayAfter
' Adds elements after given index.
' {1,2,3} -> index >= 3 -> PushArray val
' {1,2,3} -> index < 1 -> UnshiftArray val
' {} -> index = any -> PushArray val
' @param Long index | Index after which will be added an element
' @param Variant val | Array() or iArray of elements to add into iArray
' @return Long | Count of elements inside iArray
Public Function AddArrayAfter(ByVal index As Long, ByVal val As Variant) As Long
  If Me.Count < 1 Or index + 1 >= Me.Count Then
    Me.PushArray val
  ElseIf index + 1 < 1 Then
    Me.UnshiftArray val
  Else
    If TypeOf val Is StaffList Then
      For i = 0 To val.Count - 1
        Me.Add val(i), aft:=index + 1
        Inc index
      Next i
    Else
      For i = LBound(val) To UBound(val)
        Me.Add val(i), aft:=index + 1
        Inc index
      Next i
    End If
  End If
  AddArrayAfter = Me.Count
End Function

'AddArrayBefore
' Adds elements before given index.
' {1,2,3} -> index > 3 -> PushArray val
' {1,2,3} -> index <= 1 -> UnshiftArray val
' {} -> index = any -> PushArray val
' @param Long index | Index after which will be added an element
' @param Variant val | Array() or iArray of elements to add into iArray
' @return Long | Count of elements inside iArray
Public Function AddArrayBefore(ByVal index As Long, ByVal val As Variant) As Long
  If Me.Count < 1 Or index + 1 > Me.Count Then
    Me.PushArray val
  ElseIf index <= 0 Then
    Me.UnshiftArray val
  Else
    If TypeOf val Is StaffList Then
      For i = val.Count - 1 To 0 Step -1
        Me.Add val(i), bef:=index + 1
      Next i
    Else
      For i = UBound(val) To LBound(val) Step -1
        Me.Add val(i), bef:=index + 1
      Next i
    End If
  End If
  AddArrayBefore = Me.Count
End Function

'AddBefore
' Adds element before given index.
' {1,2,3} -> index > 3 -> Push val
' {1,2,3} -> index <= 1 -> Unshift val
' {} -> index = any -> Push val
' @param Long index | Index before which will be added an element
' @param Variant val | One element (String, number, ...) to add into iArray
' @return Long | Count of elements inside iArray
Public Function AddBefore(ByVal index As Long, ByVal val As Staff) As Long
  If Me.Count < 1 Or index + 1 > Me.Count Then
    Me.Push val
  ElseIf index + 1 <= 1 Then
    Me.Unshift val
  Else
    Me.Add val, bef:=index + 1
  End If
  AddBefore = Me.Count
End Function

'Avg
' Calculates the average of the numeric mainArray.
' @return Variant | Average value / "NaN" if iArray contains non-numeric value(s)
Public Function Avg() As Variant
  If Not Me.ContainsOnlyNumeric Then Avg = "NaN": Exit Function
  Avg = Me.sum / Me.Count
End Function

'Clear
' Empties iArray
Public Function Clear() As Boolean
  For i = mainArray.Count - 1 To 0 Step -1
    mainArray.Remove i + 1
  Next i
  Clear = IIf(mainArray.Count = 0, True, False)
End Function

'Clone
' Makes a hard copy of the mainArray
' @return mainArray | Return exact copy of itself
Public Function clone() As StaffList
  Set clone = New StaffList
  For i = 0 To Me.Count - 1
    clone.Push Me(i)
  Next i
End Function

'Contains
' Checks if given value is used inside mainArray.
' @param Variant val | One element (String, number, ...) to by checked if it exists in iArray
' $return Boolean | True = exists, False = doesn't exists
Public Function Contains(ByVal val As Staff) As Boolean
  Contains = False
  Dim el As Variant
  For Each el In mainArray
    If IsObject(val) = True Or VarType(val) And 8192 Then
        If (VarType(el) And 8192) And (VarType(val) And 8192) Then
            If ArrayDifference(el, val) Then
                Contains = True: Exit Function
            End If
        ElseIf IsObject(el) = True And IsObject(val) = True Then
            If el Is val Then
                Contains = True: Exit Function
            End If
        End If
    Else
        If IsObject(el) = False And (VarType(el) And 8192) <> 8192 Then
            If el = val Then
            Contains = True: Exit Function
            End If
        End If
    End If
  Next el
End Function

'ContainsAll
' Checks if all given values are used inside mainArray.
' @param Variant val | values to by checked if it exists in iArray
' $return Boolean | True = all exists, False = one ore more values doesn't exists
Public Function ContainsAll(ByVal val As StaffList) As Boolean
  ContainsAll = False
  Dim foundOccurrences As Integer: foundOccurrences = 0
  Dim values As New StaffList
  If Not TypeOf val Is StaffList Then
    If IsArray(val) Then
      values.PushArray (val)
    Else
      values.Push (val)
    End If
  Else
    Set values = val
  End If
  For i = 0 To values.Count - 1
    If Me.Contains(values(i)) Then Inc foundOccurrences
  Next i
  If foundOccurrences = values.Count Then ContainsAll = True
End Function

'CountOccurrences
' Checks how many times is given value used inside mainArray.
' @param Variant val | One element (String, number, ...) to by checked
' @return Long | Count of matched occurrences
Public Function CountOccurrences(val As Variant) As Long
  CountOccurrences = 0
  Dim el As Variant
  For Each el In mainArray
  
    If IsObject(val) = True Or VarType(val) And 8192 Then
        If VarType(el) And 8192 And VarType(val) And 8192 Then
            If ArrayDifference(el, val) Then
                Inc CountOccurrences
                Exit Function
            End If
        ElseIf IsObject(el) = True And IsObject(val) = True Then
            If el Is val Then
                Inc CountOccurrences
                Exit Function
            End If
        End If
    Else
        If IsObject(el) = False And Not (VarType(el) And 8192) Then
            If el = val Then
                Inc CountOccurrences
                Exit Function
            End If
        End If
    End If
  
     'If el = val Then Inc CountOccurrences
  Next el
End Function

'Dequeue
' Removes an element from the begining of the mainArray.
' @return Variant | Removed element or Empty, if iArray is empty
'刪除開頭一個元素。
Public Function Dequeue() As Staff
  Dequeue = Empty
  If mainArray.Count > 0 Then
    If VarType(Me(0)) = vbString Then
        Dequeue = Me(0)
    ElseIf TypeOf Me(0) Is StaffList Then
        Set Dequeue = Me(0)
    ElseIf VarType(Me(0)) = vbArray Then
        Set Dequeue = Me(0)
    ElseIf VarType(Me(0)) = vbObject Then
        Set Dequeue = Me(0)
    Else
        Dequeue = Me(0)
    End If
    
    mainArray.Remove 1
  End If
End Function

'Difference
' Checks for number of differences between two arrays, what was added/deleted or combination.
' @param iArray oldArray | Old iArray to be compared with current iArray
' @param String retType | �dd= deleted from old iArray, �aa= added in current iArray, �cc= combination of both (default)
' @return iArray | iArray with differences found
Public Function Difference(ByRef oldArray As StaffList, Optional ByVal retType As String = "c") As StaffList
  Set Difference = New StaffList
  Select Case LCase(retType)
    Case "d"
      For i = 0 To oldArray.Count - 1
        If Me.Contains(oldArray(i)) = False Then Difference.Push oldArray(i)
      Next i
    Case "a"
      For i = 0 To Count - 1
        If oldArray.Contains(Me(i)) = False Then Difference.Push Me(i)
      Next i
    Case "c"
      For i = 0 To oldArray.Count - 1
        If Me.Contains(oldArray(i)) = False Then Difference.Push oldArray(i)
      Next i
      For i = 0 To Count - 1
        If oldArray.Contains(Me(i)) = False Then Difference.Push Me(i)
      Next i
    Case Else
      err.Raise Number:=5, Description:="Unknown Difference return type attribute:" & vbCrLf & _
                                        "Allowed are 'A'dded/'D'eleted/'C'ombination of both"
  End Select
End Function

'DropLeft
' Remove n elements from the beginning of the mainArray. If n > count of iArray elements, all elements are removed.
' @param Long n | Number of elements to be removed
' @return iArray | Array of the removed elements
Public Function DropLeft(ByRef N As Long) As StaffList
  Set DropLeft = New StaffList
  If N > Me.Count Then N = Me.Count
  For i = 0 To N - 1
    DropLeft.Push Me(i)
  Next i
  For i = N - 1 To 0 Step -1
    Me.Remove (i)
  Next i
End Function

'DropRight
' Remove n elements from the end of the mainArray. If n > count of iArray elements, all elements are removed.
' @param Long n | Number of elements to be removed
' @return iArray | Array of the removed elements
Public Function DropRight(ByRef N As Long) As StaffList
  Set DropRight = New StaffList
  If N > Me.Count Then N = Me.Count
  For i = Me.Count - N To Me.Count - 1
    DropRight.Push Me(i)
  Next i
  For i = Me.Count - 1 To Me.Count - N Step -1
    Me.Remove (i)
  Next i
End Function

'Enqueue
' Adds an element at the end of the mainArray.
' @param Variant val | One element (String, number, ...) to add into iArray
' @return Long | Count of elements inside iArray
Public Function Enqueue(ByVal val As Variant) As Long
  Enqueue = Push(val)
End Function

'EnqueueArray
' Adds elements at the end of the iArray
' @param Variant val | Array() or iArray of elements to add into iArray
' @return Long | Count of elements inside array
Public Function EnqueueArray(ByVal val As Variant) As Long
  EnqueueArray = PushArray(val)
End Function

'First
' Returns value of the first element of the mainArray.
' @return Variant | Value of the first element or Empty if iArray is Empty
Public Function First() As Staff
  Set First = IIf(Me.Count > 0, Me(0), Empty)
End Function

'Head
' Returns all elements of iArray, except last one.
' @return iArray | Copy of original array, without last element
Public Function head() As StaffList
  Set head = Me.clone
  head.Pop
End Function

'Intersect
' Search for element that exists in both iArrays.
' @param iArray intArray | iArray to be intersected with current iArray
' @return iArray | Intersected values
Public Function Intersect(ByRef intersectedArr As StaffList) As StaffList
  Set Intersect = New StaffList
  Dim el As Variant
  For Each el In mainArray
    If intersectedArr.Contains(el) Then
      If Not Intersect.Contains(el) Then Intersect.Push (el)
    End If
  Next el
End Function

'ContainsOnlyNumeric
' Verify that all elements are numbers or convertable to numbers
' $return Boolean | True = contains only numeric values, False = contains inconvertible values
Public Function ContainsOnlyNumeric() As Boolean
  ContainsOnlyNumeric = True
  Dim el As Variant
  For Each el In mainArray
    If Not IsNumeric(el) Then ContainsOnlyNumeric = False: Exit Function
  Next el
End Function

'Join
' Joins two iArrays.
' @param iArray jArray | iArray to be joined with current iArray
' @return iArray | Joined iArray
Public Function Join(ByRef joinArr As StaffList) As StaffList
  Set Join = New StaffList
  Join.PushArray Me
  Join.PushArray joinArr
End Function

'Last
' Returns value of the last element of the mainArray.
' @return Variant | Value of the last element or Empty if iArray is Empty
Public Function Last() As Staff
  Set Last = IIf(Me.Count > 0, Me(Me.Count - 1), Empty)
End Function

'OccurrenceIndexes
' Returns all indexes of a value in mainArray.
' @return iArray | iArray containing indexes of occurrence
Public Function OccurenceIndexes(val As Variant) As StaffList
  Set OccurenceIndexes = New StaffList
  For i = 0 To Me.Count - 1
    If Me(i) = val Then
        OccurenceIndexes.Push (i)
    End If
  Next i
End Function

'Pop
' Removes an element from the end of the mainArray.
' @return Variant | Removed element or Empty, if iArray is empty
Public Function Pop() As Staff
  If mainArray.Count > 0 Then
    If VarType(Me(mainArray.Count - 1)) = vbObject Then
       Set Pop = Me(mainArray.Count - 1)
    Else
        Pop = Me(mainArray.Count - 1)
    End If
    mainArray.Remove mainArray.Count
  End If
End Function
  
  

'Push
' Adds an element at the end of the mainArray.
' @param Variant val | One element (String, number, ...) to add into iArray
' @return Long | Count of elements inside iArray
Public Function Push(ByVal val As Staff) As Long
  mainArray.Add val
  Push = mainArray.Count
End Function

'PushArray
' Adds elements at the end of the mainArray.
' @param Variant val | Array() or iArray of elements to add into iArray
' @return Long | Count of elements inside array
Public Function PushArray(ByVal val As Variant) As Long
  If TypeOf val Is StaffList Then
    For i = 0 To val.Count - 1
      Me.Push val(i)
    Next i
  Else
    For i = LBound(val) To UBound(val)
      Me.Push val(i)
    Next i
  End If
  PushArray = Me.Count
End Function

'RemoveDuplicates
' Keeps only the first occurrence of the value. Affects original array
' @return Long | Count of the removed elements
Public Function RemoveDuplicates() As Long
  RemoveDuplicates = 0
  For i = Me.Count - 1 To 0 Step -1
    If Me.CountOccurrences(Me(i)) > 1 Then
      Me.Remove i
      Inc RemoveDuplicates
    End If
  Next i
End Function

'Reverse
' Reverses the content of the iArray
' @return iArray | Reversed iArray
Public Function Reverse() As StaffList
  Set Reverse = New StaffList
  For i = 0 To Me.Count - 1
    Reverse.Unshift Me(i)
  Next i
End Function

'Shift
' Removes an element from the begining of the mainArray.
' @return Variant | Removed element or Empty, if iArray is empty
'轉移
' 從 iArray 的開頭刪除一個元素。
' @返回第一個元素 | 如果 iArray 為空，則刪除元素或為空
Public Function shift() As Staff
  shift = Empty
  If mainArray.Count > 0 Then
    If VarType(Me(0)) = vbString Then
        shift = Me(0)
    ElseIf TypeOf Me(0) Is StaffList Then
        Set shift = Me(0)
    ElseIf VarType(Me(0)) = vbArray Then
        Set shift = Me(0)
    ElseIf VarType(Me(0)) = vbObject Then
        Set shift = Me(0)
    Else
        shift = Me(0)
    End If
    
    mainArray.Remove 1
  End If
End Function

'Shuffle
' Randomly mixes content of the iArray
' @return iArray | Shuffled iArray
' 隨機播放
' 隨機混合 iArray 的內容
'@return iArray | 打亂iArray
Public Function Shuffle() As StaffList
  Set Shuffle = New StaffList
  Dim keys As New StaffList
  For i = 0 To Me.Count - 1
    keys.Push (i)
  Next i
  Dim rndNo As Long
  Do While keys.Count > 0
    rndNo = randomFromTo(0, keys.Count - 1)
    Shuffle.Push Me(keys(rndNo))
    keys.Remove (rndNo)
  Loop
End Function

'Sum
' Calculates the sum of the numeric mainArray.
' @return Variant | Sum value / "NaN" if iArray contains non-numeric value(s)
Public Function sum() As Variant
  If Not Me.ContainsOnlyNumeric Then sum = "NaN": Exit Function
  sum = 0
  Dim el As Variant
  For Each el In mainArray
    sum = sum + el
  Next el
End Function

'Tail
' Returns all elements of iArray, except first one.
' @return iArray | Copy of original array, without first element
'返回陣列中除了第一個元素的剩余元素陣列
Public Function Tail() As StaffList
  Set Tail = Me.clone
  Tail.Dequeue
End Function

Public Function ToList()
  If Me.Count = 0 Then ToList = Null: Exit Function
  Dim tarr()
  ReDim tarr(Me.Count - 1)
  For i = 0 To Me.Count - 1
    If VarType(Me(i)) = vbString Then
        tarr(i) = Me(i)
    ElseIf TypeOf Me(i) Is StaffList Then
        Set tarr(i) = Me(i)
    ElseIf VarType(Me(i)) = vbObject Then
        Set tarr(i) = Me(i)
    Else
        tarr(i) = Me(i)
    End If
  Next i
  ToList = tarr
End Function

'ToString
' Creates string representation of the mainArray.
' @param String delimiter | Optional character to separate the iArray's elements (default = " ")
' @return String | Formated representation of tha iArray
Public Function ToString(Optional ByVal delimiter As String = " ") As String
  If Me.Count = 0 Then ToString = "{}": Exit Function
  ToString = vbNullString
  For i = 0 To Me.Count - 1
    If i = 0 Then ToString = ToString + "{"
    If i > 0 Then ToString = ToString + delimiter
    If VarType(Me(i)) = vbString Then
        ToString = ToString + Chr$(34)
        ToString = ToString + CStr(Me(i))
        ToString = ToString + Chr$(34)
    ElseIf TypeOf Me(i) Is StaffList Then
        ToString = ToString + Me(i).ToString(delimiter)
    ElseIf (VarType(Me(i)) And vbArray) = vbArray Then
        ToString = ToString + "[Array]"
    ElseIf VarType(Me(i)) = vbObject Then
        ToString = ToString + "[Object]"
    Else
        ToString = ToString + CStr(Me(i))
    End If
    
    If i = mainArray.Count - 1 Then ToString = ToString + "}"
  Next i
End Function

'Union
' Combines both iArrays and removes duplicities
' @param iArray uArray | iArray to be unioned with current iArray
' @return iArray | Combined values without duplicities
Public Function Union(ByRef uArr As StaffList) As StaffList
  Set Union = Me.clone
  Union.PushArray uArr
  Union.RemoveDuplicates
End Function

'Unique
' Returns copy of iArray without duplicated values. Original array is not affected
' @return iArray | iArray with unique values
Public Function Unique() As StaffList
  Set Unique = New StaffList
  Dim el As Variant
  For Each el In mainArray
    If Not Unique.Contains(el) Then Unique.Push (el)
  Next el
End Function

'Unshift
' Add an element at the begining of the mainArray.
' @param Variant val | One element (String, number, ...) to add into iArray
' @return Long | Count of elements inside iArray
Public Function Unshift(ByVal val As Variant) As Long
  If mainArray.Count = 0 Then
    Unshift = Push(val)
  Else
    mainArray.Add val, before:=1
    Unshift = mainArray.Count
  End If
End Function

'UnshiftArray
' Add elements at the begining of the mainArray.
' @param Variant val | Array() or iArray of elements to add into iArray
' @return Long | Count of elements inside iArray
Public Function UnshiftArray(ByVal val As Variant) As Long
  If TypeOf val Is StaffList Then
    For i = val.Count - 1 To 0 Step -1
      Unshift val(i)
    Next i
  Else
    For i = UBound(val) To LBound(val) Step -1
      Unshift val(i)
    Next i
  End If
  UnshiftArray = mainArray.Count
End Function


' #####################
' # PRIVATE FUNCTIONS #
' #####################
Sub Inc(ByRef i)
   i = i + 1
End Sub

'Private Function rangeToArray(ByVal rng As Range) As Variant
'  rangeToArray = rng.Value
'End Function

Private Function randomFromTo(ByVal from As Long, ByVal upTo As Long) As Long
  Randomize
  randomFromTo = Int(from + Rnd() * (upTo - from + 1))
End Function

'比對 兩個陣列是否一樣
Private Function ArrayDifference(arr1 As Variant, arr2 As Variant) As Boolean

    Dim i As Integer
    If UBound(arr1) = UBound(arr2) Then
        For i = 0 To UBound(arr1)
            If arr1(i) = arr2(i) Then
                ArrayDifference = True
            Else
                ArrayDifference = False
                Exit Function
            End If
        Next
    Else
        ArrayDifference = False
    End If

End Function

'@Description("changes the contents of the array by removing or replacing existing elements and/or adding new elements in place.")
Public Function Splice( _
        ByVal StartIndex As Long, _
        ParamArray Args() As Variant _
    ) As Variant()
    'Dim LocalItems() As Variant
    Dim ActualStart As Long
    Dim ActualDeleteCount As Long
    Dim ArgsCount As Long
    Dim LocalLength As Long
    Dim LocalArgs() As Variant
    Dim result() As Variant
    Dim i As Long
    Dim TempArray() As Variant
    Dim ItemCount As Long
    Dim TempItems() As Variant
    
    LocalArgs = Args
    'LocalItems = mainArray
    LocalLength = Me.Count
    If StartIndex < LocalLength Then
        ActualStart = StartIndex
    Else
        ActualStart = min(StartIndex, LocalLength)
    End If
    
    ArgsCount = UBound(LocalArgs) + 1
    If ArgsCount = 0 Then
        ' only a start index has been supplied
        ' we're gonna delete everything
        ' 僅提供了起始索引
         '我們要刪除所有內容
        ItemCount = 0
        ActualDeleteCount = LocalLength - ActualStart
    Else
        ' first arg in args is delete count, second onwards are insertion items
        ' args 中的第一個參數是刪除計數，第二個之後是插入項
        ItemCount = ArgsCount - 1
        'deleteCount is first element in args.
        'deleteCount 是 args 中的第一個元素。
        ActualDeleteCount = min(max(Args(LBound(Args)), 0), LocalLength - ActualStart)
    End If
    

    ' get items to be deleted for return val
    ' 取得和刪除
    If ActualDeleteCount > 0 Then
        ReDim result(0 To ActualDeleteCount - 1)
        i = 0
        Do While i < ActualDeleteCount
            If IsObject(Me(ActualStart)) Then
                Set result(i) = Me(ActualStart)
                Me.Remove ActualStart
            Else
                result(i) = Me(ActualStart)
                Me.Remove ActualStart
            End If
            Inc i
        Loop
    Else
        ' return empty array if nothing to be deleted
        ReDim result(0)
    End If
    
    '取得要插入的陣列資料
    If ItemCount > 0 Then
        ReDim TempItems(0 To ItemCount - 1)
        For i = 0 To ItemCount - 1
            If IsObject(LocalArgs(i + 1)) Then
                Set TempItems(i) = LocalArgs(i + 1)
            Else
                TempItems(i) = LocalArgs(i + 1)
            End If
        Next
    Me.AddArrayBefore ActualStart, TempItems
    End If
    
    
    Splice = result
End Function

Attribute VB_Name = "TempoElement"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public typs As String
Public pitch
Public note As AbsoluteElement
Public x As Double
Public tempo As vtempoProperties
Public tuneNumber As Double
Public totalHeightInPitches As Double
Public tempoHeightAbove As Double
    
Public Sub init(tempo As vtempoProperties, tuneNumber As Integer)
        Me.Type = "TempoElement"
        Me.tempo = tempo
        Me.tempo.Type = "tempo"  ''/ TODO-PER: this should be set earlier, in the parser, probably.
        Me.tuneNumber = tuneNumber
        '' TODO: can these two properties be merged?
        Me.totalHeightInPitches = 6
        Me.tempoHeightAbove = Me.totalHeightInPitches
        Me.pitch = undefined  '' This will be set later
        If (Me.tempo.duration And Not Me.tempo.suppressBpm) Then
            Me.note = Me.createNote(tempo, tuneNumber)
        End If
End Sub

Public Sub setX(x As Double)
        Me.x = x
End Sub

 Public Function createNote(tempo As vtempoProperties, tuneNumber As Double) As AbsoluteElement
        Dim temposcale As Double
        Dim duration As Double
        Dim abselem As AbsoluteElement
        Dim dot As Integer
        Dim flag As String
        Dim note As String
        Dim ret As Dictionary
        Dim tempoNote As RelativeElement
        Dim stem As Double
        
        
        temposcale = 0.75
        duration = tempo.duration(0)  '' TODO when multiple durations
        Set abselem = New AbsoluteElement
        abselem.init tempo, duration, 1, "tempo", tuneNumber
        '' There aren't an infinite number of note values, but we are passed a float, so just in case something is off upstream,
        '' merge all of the in between points.
        dot = 0: flag = "": note = ""
        If (duration <= 1 / 32) Then note = "noteheads.quarter": flag = "flags.u32nd": dot = 0
        ElseIf (duration <= 1 / 16) Then note = "noteheads.quarter": flag = "flags.u16th": dot = 0
        ElseIf (duration <= 3 / 32) Then note = "noteheads.quarter": flag = "flags.u16nd": dot = 1
        ElseIf (duration <= 1 / 8) Then note = "noteheads.quarter": flag = "flags.u8th": dot = 0
        ElseIf (duration <= 3 / 16) Then note = "noteheads.quarter": flag = "flags.u8th": dot = 1
        ElseIf (duration <= 1 / 4) Then note = "noteheads.quarter": dot = 0
        ElseIf (duration <= 3 / 8) Then note = "noteheads.quarter": dot = 1
        ElseIf (duration <= 1 / 2) Then note = "noteheads.half": dot = 0
        ElseIf (duration <= 3 / 4) Then note = "noteheads.half": dot = 1
        ElseIf (duration <= 1) Then note = "noteheads.whole": dot = 0
        ElseIf (duration <= 1.5) Then note = "noteheads.whole": dot = 1
        ElseIf (duration <= 2) Then note = "noteheads.dbl": dot = 0
        Else
            note = "noteheads.dbl": dot = 1
        End If
        Dim tmpOpt1 As New Dictionary
        Dim noteOpt As New oNoteHeadOptions
        tmpD1("verticalPos") = 0
        noteOpt.dir = "up"
        noteOpt.flag = flag
        noteOpt.dot = dot
        noteOpt.scale_ = temposcale
        '' This is just temporary: we'll offset the vertical positioning when we get the actual vertical spot.
        Set ret = createNoteHead(abselem, note, tmpD1, noteOpt)
        Set tempoNote = ret("notehead")
        abselem.addHead tempoNote
        Dim p1, p2, dx, width
        If (note <> "noteheads.whole" And note <> "noteheads.dbl") Then
            p1 = 1 / 3 * temposcale
            p2 = 5 * temposcale
            dx = tempoNote.dx + tempoNote.w
            width = -0.6
            Set stem = New RelativeElement
            Set tmpD1 = New Dictionary
            tmpD1("typs") = "stem"
            tmpD1("pitch2") = p2
            tmpD1("linewidth") = width
            stem.init Null, dx, 0, p1, tmpD1
            abselem.addRight stem
        End If
        Set createNote = abselem
End Function

Attribute VB_Name = "TestDll_Print"
Attribute VB_Base = "0{547412D5-03A4-4D77-8328-C2BE83E049B6}{02E5E026-F93D-4C22-888B-F777420B8828}"
Attribute VB_GlobalNameSpace = False
Attribute VB_Creatable = False
Attribute VB_PredeclaredId = True
Attribute VB_Exposed = False
Attribute VB_TemplateDerived = False
Attribute VB_Customizable = False

Option Explicit

Private Sub CommandButton1_Click()
    Dim inss As INS_Object
    Dim ii As Double
    Dim hWnd As Long
    Set inss = New INS_Object
    ii = inss.AddLine(33, 99, 77, 44)
    hWnd = GetActiveWindow
    MsgBox "VBA is GetActiveWindow  : " & hWnd
    
    inss.aPaint hWnd
    
    
End Sub

Private Sub CommandButton2_Click()
    On Error Resume Next
    Dim oApp As Object  ' AcadApplication
    ' Try to connect to a running instance of AutoCAD.
    
    Set oApp = GetObject(, "AutoCAD.Application")
    If err Then
        ' Failed to get AutoCAD.
        MsgBox ("Could not connect to AutoCAD.")
        err.Clear
        Exit Sub
    End If
     
    
    Dim myCom As myCustomCom
    Dim vvv As Variant
    'myCom = oApp.GetInterfaceObject("comArxProject1Lib.myCustomCom1")
    
    Set myCom = New myCustomCom
    Dim x As Single
    Dim y As Single
    Dim Z As Single
    Call myCom.getPosition(x, y, Z)
    myCom.addMuiscText
    MsgBox x & ":" & y & ":" & Z & ":"
  
End Sub
'Imports asdkcomServerFromArxLib
'Imports Autodesk.AutoCAD.Interop
'Imports System.Windows.Forms
'Public Class Form1
'
'Private Sub Button1_Click(ByVal sender As System.Object, ByVal e As System.EventArgs) Handles Button1.Click
'Dim oApp As AcadApplication
'' Try to connect to a running instance of AutoCAD.
'Try
'oApp = GetObject(, "AutoCAD.Application")
'' Failed to get AutoCAD.
'MsgBox ("Could not connect to AutoCAD.")
'Exit Sub
'
'
'End Try
'
'Dim myCom As myCustomCom
'myCom = oApp.GetInterfaceObject("comServerFromArx.myCustomCom")
'
'Dim x As Single
'Dim y As Single
'Dim z As Single
'myCom.getPosition(x, y, z)
'MessageBox.Show ("(" + x.ToString() + "," + y.ToString() + "," + z.ToString() + ")")
'End Sub
'End Class
'
Private Sub CommandButton3_Click()

    Dim returnObj As Object
    Dim basePnt As Variant
    Dim i As Integer
    Dim j As Integer
  
    Dim SEOBJ As SmileyEntity
    
    ThisDrawing.Utility.GetEntity returnObj, basePnt, "選擇要插入有屬性的圖元："
    
    returnObj.center = basePnt
End Sub

Private Sub CommandButton4_Click()
    
    Dim SEOBJ As SmileyEntity
    Dim basePnt(0 To 2) As Double
    Dim cenPnt(0 To 2) As Double
    Dim returnPnt As Variant
    Dim rad As Integer
    
    Me.Hide
    returnPnt = ThisDrawing.Utility.GetPoint(basePnt, "\n選擇要插入的點")
    

    'Set SEOBJ = New SmileyEntity
    Dim SSS As New SmileyApplication
    Dim ss As SmileyUi.SmileyApplication
    
    Set SEOBJ = ThisDrawing.ModelSpace.AddCustomObject("ASDKSMILEY")
    Call SEOBJ.setNewObject(returnPnt, 255)
    
    'sss.CreateSmiley
    
    'Dim aaa As Variant
    'aaa = SEOBJ.MouthCenter
    Me.Show
End Sub

Attribute VB_Name = "TestResult"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
' Copyright 2023 Sam Vanderslink
'
' Permission is hereby granted, free of charge, to any person obtaining a copy
' of this software and associated documentation files (the "Software"), to deal
' in the Software without restriction, including without limitation the rights
' to use, copy, modify, merge, publish, distribute, sublicense, and/or sell
' copies of the Software, and to permit persons to whom the Software is
' furnished to do so, subject to the following conditions:
'
' The above copyright notice and this permission notice shall be included in
' all copies or substantial portions of the Software.
'
' THE SOFTWARE IS PROVIDED "AS IS", WITHOUT WARRANTY OF ANY KIND, EXPRESS OR
' IMPLIED, INCLUDING BUT NOT LIMITED TO THE WARRANTIES OF MERCHANTABILITY,
' FITNESS FOR A PARTICULAR PURPOSE AND NONINFRINGEMENT. IN NO EVENT SHALL THE
' AUTHORS OR COPYRIGHT HOLDERS BE LIABLE FOR ANY CLAIM, DAMAGES OR OTHER
' LIABILITY, WHETHER IN AN ACTION OF CONTRACT, TORT OR OTHERWISE, ARISING
' FROM, OUT OF OR IN CONNECTION WITH THE SOFTWARE OR THE USE OR OTHER DEALINGS
' IN THE SOFTWARE.

Option Explicit

'-------------------------------------------------------------------------------
'   Class: TestResult
'   Simple data class containing a test result.
'-------------------------------------------------------------------------------

' Properties
'-------------------------------------------------------------------------------
Public Name As String
Public Failed As Boolean
Public Message As String

Public Property Get ToString() As String
Attribute ToString.VB_Description = "Returns a string representation of the class."
'   Returns a string representation of the class.
    Dim msg As String
    msg = IIf(Message = "", "", vbNewLine & "     " & Message)
    ToString = IIf(Failed, "!! Fail: ", "   Pass: ") & Name & msg
End Property


' Methods
'-------------------------------------------------------------------------------
Public Function AssertAreEqual( _
    expectedVal, _
    actualVal, _
    Optional forVal As String) As Boolean
Attribute AssertAreEqual.VB_Description = "Asserts expected is equal to actual."
'   Asserts expected is equal to actual.
'
'   Args:
'       expectedVal: The expected value.
'       actualVal: The actual value.
'       forVal: Additional context.
'
'   Returns:
'       False if the assertion passed.
'
    If expectedVal <> actualVal Then
        Failed = True
        SetExpectedActualMessage CStr(expectedVal), CStr(actualVal), forVal
    End If
    AssertAreEqual = Failed
End Function

Public Function AssertAreNotEqual( _
    expectedVal, _
    actualVal, _
    Optional forVal As String) As Boolean
Attribute AssertAreNotEqual.VB_Description = "Asserts values are not equal."
'   Asserts values are not equal.
'
'   Args:
'       expectedVal: The expected value.
'       actualVal: The actual value.
'       forVal: Additional context.
'
'   Returns:
'       False if the assertion passed.
'
    If expectedVal = actualVal Then
        Failed = True
        Message = "Inequality check [" & forVal & "]"
    End If
    AssertAreNotEqual = Failed
End Function

Public Function AssertIsTrue(val As Boolean, ctx As String) As Boolean
Attribute AssertIsTrue.VB_Description = "Asserts the value is true."
'   Asserts the value is true.
'
'   Args:
'       val: The value to test.
'       ctx: Context for the message.
'
'   Returns:
'       False if the assertion passed.
'
    If Not val Then
        Failed = True
        Message = "Failed " & ctx
    End If

    AssertIsTrue = Failed
End Function

Public Function AssertIsFalse(val As Boolean, ctx As String) As Boolean
Attribute AssertIsFalse.VB_Description = "Asserts the value is false."
'   Asserts the value is false.
'
'   Args:
'       val: The value to test.
'       ctx: Context for the message.
'
'   Returns:
'       False if the assertion passed.
'
    If val Then
        Failed = True
        Message = "Failed " & ctx
    End If

    AssertIsFalse = Failed
End Function

Public Function AssertNoException() As Boolean
Attribute AssertNoException.VB_Description = "Asserts no exception raised."
'   Asserts no exception raised.
'
'   Args:
'       errObj: The error object.
'
'   Returns:
'       False if the assertion passed.
'
    If err <> 0 Then
        Failed = True
        Message = err & " - " & err.Description
    End If

    AssertNoException = Failed
End Function

Public Function AssertRaised(errNo As Long) As Boolean
Attribute AssertRaised.VB_Description = "Asserts a specific exception is raised."
'   Asserts a specific exception is raised.
'
'   Args:
'       errNo: The expected exception.
'
'   Returns:
'       False if the assertion passed.
'
    If err = 0 Then
        Failed = True
        Message = "Expected exception " & errNo & " raised but none thrown."
    End If
    
    If err <> errNo Then
        Failed = True
        Message = "Expected exception " & errNo & " raised but got " & err & "."
    End If

    AssertRaised = Failed
End Function


' Helpers
'-------------------------------------------------------------------------------
Private Sub SetExpectedActualMessage(exp As String, act As String, Optional forVal As String)
Attribute SetExpectedActualMessage.VB_Description = "Sets a message based on expected vs actual values."
'   Sets a message based on expected vs actual values.
'
'   Args:
'       exp: The expected value.
'       act: The actual value.
'
    Dim msg As String
    msg = "Expected " & exp & " but got " & act
    Message = IIf(forVal = "", msg, msg & " [" & forVal & "]")
End Sub

Attribute VB_Name = "TextToMusic"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Dim mHowData As Integer      '有多少行資料
Dim mChar As String          '資料的前面字元有那些
Dim mCharI() As Integer
Dim mMete As Integer        '每小節有幾拍
Dim mFontSize As Integer
Dim mTextnote() As String       '把每行資料放進來 這是有陣列的
Dim mmsa(0 To 1) As String

Dim i As Integer
Dim j As Integer
Private Type KeyFormat
        mfingering As String  '指法
        mnote As String           '高低音
        mscale As String          '音階
        mtempo As String         '拍子
        mfPosition As Double    '這是看這字上下移多少
        mnPosition As Double    '這是看這字上下移多少
        msPosition As Double     '這是看這字上下移多少
        mtPosition As Double    '這是看這字上下移多少
End Type

Dim mMusic() As KeyFormat                '了解嗎
Public Sub setLineChar(Char As String, mete As Integer)
    'Char 設定資料的前面字元有那些
    'Mete 每小節有幾拍
    mChar = Char
    mMete = mete
    ReDim mCharI(Len(mChar))
    mHowData = Len(mChar)
    ReDim mTextnote(mHowData + 1)    ' 陳述式將重新調整陣列的大小，且將所有元素內容清除。
                                     ' 因為它從 0 開始 所以要加 1
End Sub

Public Sub setFontSize(fontsize As Integer)
    mFontSize = fontsize
End Sub

Public Sub TextToMusic()
    Dim kNUM1 As String, kNUM2 As String, kNUM3 As String, kNUM4 As String
    Dim kNUM5 As String, kNUM6 As String, kNUM7 As String, kNUM0 As String
    Dim k延長一拍 As String
    Dim kLIN1 As String: Dim kLIN2 As String: Dim kLIN3 As String
    Dim kUP1 As String
    Dim kUP2 As String
    Dim kDOW1 As String
    Dim kDOW2 As String
    Dim kAdot As String
    Dim kBarLine As String
    Dim kFing(30 To 255) As String
    Dim posLinDown As Variant
    Dim posFing(0 To 255) As Integer
    Const MAX200 As Integer = 200
    posLinDown = Array(0, 12, 26, 40)   '這是看低音下點要移多少下去，是當200字型時計算
    
    kNUM1 = ChrW(&H4E52)
    kNUM2 = ChrW(&H4E53)
    kNUM3 = ChrW(&H4E56)
    kNUM4 = ChrW(&H4E58)
    kNUM5 = ChrW(&H4E59)
    kNUM6 = ChrW(&H4E5C)
    kNUM7 = ChrW(&H4E5D)
    kNUM0 = ChrW(&H5D4C)
    k延長一拍 = ChrW(&H5D1F)
    kLIN1 = ChrW(&H5D39): kLIN2 = ChrW(&H5D3A): kLIN3 = ChrW(&H5D3C)
    kUP1 = ChrW(&H66E0): kUP2 = ChrW(&H66E3): kDOW1 = ChrW(&H66E6): kDOW2 = ChrW(&H66E8)
    kAdot = ChrW(&H5D3D)            '符點音符
    kBarLine = ChrW(&H601D)
    kFing(Asc("z")) = ChrW(&H6416)  ' z 大指
    kFing(Asc("x")) = ChrW(&H641A)  ' x 食指
    kFing(Asc("c")) = ChrW(&H641C)  ' c 中指
    kFing(Asc("v")) = ChrW(&H641F)  ' v 無名指
    kFing(Asc("a")) = ChrW(&H6421)  ' a 八度
    kFing(Asc("s")) = ChrW(&H66FC)  ' s 王字指法
    kFing(Asc("d")) = ChrW(&H6700)  ' d 搖指
    kFing(Asc("p")) = ChrW(&H6381)  ' p 卜指法
    kFing(Asc("Z")) = ChrW(&H6418)  ' 大寫Z 反大指法
    kFing(Asc("A")) = ChrW(&H6413)  ' 大寫A 反八度
    kFing(Asc("-")) = ChrW(&H66F7)  ' - 間一旋
    kFing(Asc("=")) = ChrW(&H66F8)  ' = 間二旋
    kFing(Asc("t")) = ChrW(&H670B)  ' t 打圓 托勾
    
    posFing(Asc("z")) = 157  ' z 大指
    posFing(Asc("x")) = 165  ' x 食指
    posFing(Asc("c")) = 157  ' c 中指
    posFing(Asc("v")) = 157  ' v 無名指
    posFing(Asc("a")) = 157  ' a 八度
    posFing(Asc("s")) = 157  ' s 王字指法
    posFing(Asc("d")) = 0  ' d 搖指
    posFing(Asc("p")) = -10  ' p 卜指法
    posFing(Asc("Z")) = 157  ' 大寫Z 反大指法
    posFing(Asc("A")) = 157  ' 大寫A 反八度
    posFing(Asc("-")) = 157  ' - 間一旋
    posFing(Asc("=")) = 157  ' = 間二旋
    posFing(Asc("t")) = 160  ' t 打圓 托勾

    
    Dim c() As String
    ReDim c(Len(mChar))
    ReDim mMusic(Len(mTextnote(MkDoc.iNote)) * 2)
    Dim lsup As Integer
    Dim pos As Integer
    pos = 1
    Call atImputer(mMete)  '這是要加入小節線 ,排拍子
    For i = 1 To Len(mTextnote(MkDoc.iNote))  ' 迴圈每個字
        For j = 1 To Len(mChar)
            c(j) = Mid(mTextnote(j), i, 1)
        Next j
        
        Select Case c(MkDoc.iFinge)     '這是指法
            Case "a" To "z", "A" To "Z", "-", "="
                mMusic(pos).mfingering = kFing(Asc(LCase(c(MkDoc.iFinge))))
                mMusic(pos).mfPosition = posFing(Asc(LCase(c(MkDoc.iFinge)))) _
                                        * mFontSize / MAX200
            Case " "
            Case "("
            Case "|"
            Case Else
                mMusic(pos).mfingering = c(MkDoc.iFinge)
                mMusic(pos).mfPosition = 0
        End Select
        
        lsup = 0
        Select Case c(MkDoc.iTempo)     '這是拍子
            Case " "
            Case "-", "2"
                lsup = 1
                mMusic(pos).mtempo = kLIN1
            Case "=", "4", "3"
                lsup = 2
                mMusic(pos).mtempo = kLIN2
            Case "6", "8", "A"
                lsup = 3
                mMusic(pos).mtempo = kLIN3
            Case "|"
            Case Else
                mMusic(pos).mtempo = c(MkDoc.iTempo)
        End Select
        
                
        Select Case c(MkDoc.iScale)     '這是 八度音
            Case " "
            Case "."        '上一點
                mMusic(pos).mscale = kUP1
                mMusic(pos).msPosition = 0
            Case ":"        '上二點
                mMusic(pos).mscale = kUP2
                mMusic(pos).msPosition = 0
            Case ","        '下一點
                mMusic(pos).mscale = kDOW1
                mMusic(pos).msPosition = -mFontSize * posLinDown(lsup) / MAX200   '這是下移的指令
            Case " "        '上二點
                mMusic(pos).mscale = kDOW2
                mMusic(pos).msPosition = -mFontSize * posLinDown(lsup) / MAX200   '這是下移的指令
            Case "|"
            Case Else
                mMusic(pos).mscale = c(MkDoc.iScale)
        End Select
        
        
        Select Case c(MkDoc.iNote)     '這是音階
            Case "0"
                mMusic(pos).mnote = kNUM0
            Case "1"
                mMusic(pos).mnote = kNUM1
            Case "2"
                mMusic(pos).mnote = kNUM2
            Case "3"
                mMusic(pos).mnote = kNUM3
            Case "4"
                mMusic(pos).mnote = kNUM4
            Case "5"
                mMusic(pos).mnote = kNUM5
            Case "6"
                mMusic(pos).mnote = kNUM6
            Case "7"
                mMusic(pos).mnote = kNUM7
            Case "."
                mMusic(pos).mnote = kAdot
            Case "-"
                mMusic(pos).mnote = k延長一拍
            Case "|"
                mMusic(pos).mnote = "|"
            Case Else
                mMusic(pos).mnote = c(MkDoc.iNote)
                
        End Select

        pos = pos + 1
    Next i
    mMusic(0).mnote = pos
    
End Sub
Private Sub atImputer(iMete As Integer)
    '排成有小節線的文字
    'iMete 每小節裡有幾拍
    Dim testTXT() As String
    ReDim testTXT(Len(Me.TextNote(MkDoc.iNote)))
    Dim c() As String
    ReDim c(Len(mChar))
    
    Dim i As Integer
    Dim j As Integer
    Dim num As Integer
    Dim nownum As Integer
    Dim chackFor As Boolean
    Const A_TEMPO As Integer = 240  '一拍的數值
    
    For i = 1 To Len(mTextnote(MkDoc.iNote))  ' 迴圈每個字
        For j = 1 To Len(mChar)
            c(j) = Mid(mTextnote(j), i, 1)
        Next j
        
        If num >= A_TEMPO * iMete Then
            If c(MkDoc.iNote) <> "|" Then
                num = 0
                For j = 1 To Len(mChar)
                    testTXT(j) = testTXT(j) & "|"
                Next j
            End If
        End If
        
        Select Case c(MkDoc.iNote)
            Case "|":
                num = 0
                nownum = 0
                chackFor = True
            Case "-":
                nownum = A_TEMPO
                chackFor = True
            Case ".":
                nownum = nownum / 2
                chackFor = True
                
            Case " ":
            Case Else:
                Select Case c(MkDoc.iTempo)
                    Case " ", "":
                        nownum = A_TEMPO
                    Case "-", "2":
                        nownum = A_TEMPO / 2
                    Case "=", "4":
                        nownum = A_TEMPO / 4
                    Case "3":
                        nownum = A_TEMPO / 3
                    Case "6":
                        nownum = A_TEMPO / 6
                    Case "8":
                        nownum = A_TEMPO / 8
                    Case "a":
                        nownum = A_TEMPO / 10
                    Case "":
                        
                End Select
                
                chackFor = True
            
        End Select
        If chackFor = True Then
            For j = 1 To Len(mChar)
                If c(j) = "" Then
                    testTXT(j) = testTXT(j) & " "
                Else
                    testTXT(j) = testTXT(j) & c(j)
                End If
            Next j
        End If
        chackFor = False
        num = num + nownum
        
    Next i
    
    For j = 1 To Len(mChar)
        mTextnote(j) = testTXT(j)
    Next j
End Sub
Private Function intComp(myInt1 As Integer, myInt2 As Integer) As Integer
    '比較數值
    '傳回值 = 較大的數值
    If myInt1 >= myInt2 Then
        intComp = myInt1
    Else
        intComp = myInt2
    End If
End Function
Private Sub mTextNoteLenAdd()
    '這函式是要 mTextNote(?) 中的每個長度一樣，不一樣補空白
    Dim x As Integer
    Dim str As String
    Dim BigInt As Integer
    BigInt = 0
    For x = 1 To mHowData
        BigInt = intComp(BigInt, Len(mTextnote(x)))
    Next
    If BigInt <> 0 Then
        
        For x = 1 To mHowData
            str = space(BigInt)
            LSet str = mTextnote(x)
            mTextnote(x) = str
        Next
    
    End If
End Sub

Public Sub setSaveString(tObject As String)
    '這是看進來什麼格式的資料 要放在 mTextNote 的第幾個
    Dim c As String     '記現在是什麼格式的資料
    Static cl As String    '記前一個是什麼格式的資料
    Static num As Integer   ' 記錄著一樣格式的標記 看以經有幾個了 如 |||||
    c = Mid(tObject, 1, 1)
    For i = 1 To mHowData
        If c = Mid(mChar, i, 1) Then
            If i = 1 Then
                ReDim mCharI(Len(mChar))
                Call mTextNoteLenAdd    '這函式是要 mTextNote(?) 中的每個長度一樣，不一樣補空白
            End If
            If mCharI(i) <> 1 Then
                mTextnote(i) = mTextnote(i) + tObject
                mCharI(i) = 1
                Exit For
            End If
        End If
    Next i
    
   
End Sub

Public Property Get TextNote(ii As Integer) As String
    TextNote = mTextnote(ii)
End Property

Public Sub Show()
    Dim ccc As String
    For i = 1 To mHowData
        ccc = ccc + vbCrLf
        ccc = ccc + Mid(mChar, i, 1)
    Next i
    MsgBox "有 " & mHowData & " 個資料   資料的格式是" & ccc
End Sub

Public Sub ShowData()
    Dim ccc As String
    
    For i = 1 To mHowData
        ccc = ccc + vbCrLf
        ccc = ccc & mTextnote(i)
    Next i
    MsgBox " 全部資料的 內容是" & ccc

End Sub
Public Function getMFingering(ii As Integer) As String
    getMFingering = mMusic(ii).mfingering
End Function
Public Function getMNote(ii As Integer) As String
    getMNote = mMusic(ii).mnote
End Function
Public Function getMScale(ii As Integer) As String
    getMScale = mMusic(ii).mscale
End Function
Public Function getMTempo(ii As Integer) As String
    getMTempo = mMusic(ii).mtempo
End Function
Public Function getMScalePosition(ii As Integer) As Double
    getMScalePosition = mMusic(ii).msPosition
End Function
Public Function getMFingPosition(ii As Integer) As Double
    getMFingPosition = mMusic(ii).mfPosition
End Function

Public Function getSaveString(ii As Integer) As String
    getSaveString = mTextnote(ii)
End Function

Attribute VB_Name = "ThisDrawing"
Attribute VB_Base = "0{7AABBB95-79BE-4C0F-8024-EB6AF271231C}"
Attribute VB_GlobalNameSpace = False
Attribute VB_Creatable = False
Attribute VB_PredeclaredId = True
Attribute VB_Exposed = True
Attribute VB_TemplateDerived = False
Attribute VB_Customizable = True
Option Explicit


Sub block_definition_rename()
'圖塊改名
    Dim fileName As String
    Dim oBlkRef As AcadBlockReference
    Dim oEnt As AcadEntity, oBlock As AcadBlock
    Dim varPt
    Dim insVpt, insPt(2) As Double
    Dim BNAME As String
    Dim i As Long, j As Long, idpairs As Long
    Dim expObjs As Variant

    Dim objSelSet As AcadSelectionSet
    Dim objTarget As AcadDocument
    Dim currentdrawing As AcadDocument
    Set currentdrawing = ThisDrawing
    'Dim documents As AcadDocuments
    Dim document As AcadDocument
    Dim objOrgEnts() As Object
    Dim destEnts As Variant
    Dim intCnt As Long
    Dim blo As AcadBlock
    Dim strFullDef As String
    Dim objBlock As AcadBlock
    Dim objBlock1 As AcadBlock
    Dim colBlocks As AcadBlocks
    Dim objArray(0) As Object

    Dim oldname As String

    ThisDrawing.SetVariable "DELOBJ", 1
    On Error Resume Next
    err.Clear
    ThisDrawing.Utility.GetEntity oEnt, varPt, "Select block: "
    If err.Number <> 0 Then
        On Error GoTo 0
        Exit Sub
    End If

    If TypeOf oEnt Is AcadBlockReference Then
        Set oBlkRef = oEnt
        oldname = oBlkRef.EffectiveName
        BNAME = oBlkRef.EffectiveName & "_o"
        BNAME = InputBox("New block name is: ", "BLOCKRENAM", BNAME)


        For Each oBlock In ThisDrawing.Blocks
            If oBlock.Name = BNAME Then
                MsgBox "Block " & BNAME & " does already exist"
                Exit Sub
            End If
        Next

        Set colBlocks = ThisDrawing.Blocks
        Set objBlock = colBlocks.item(oldname)
        objBlock.Name = BNAME

    End If

Err_Control:
    If err.Number = 0 Then
        MsgBox "Done"
    Else
        MsgBox err.Description
    End If
End Sub

Sub DynBlockRename()
    'Dim dybprop As Variant, i As Integer
    Dim dynblock As Object
    Dim ThisDrawing As AcadDocument
    Dim dybprop
    Dim oldname As String
    Dim BNAME As String
    Dim objBlock As AcadBlock
    Dim colBlocks As AcadBlocks
    'Dim InsertionPoint(0 To 2)  As Double
    Set ThisDrawing = AcadApplication.ActiveDocument
    For Each dynblock In ThisDrawing.ModelSpace  'Starts looping through all blocks
        If dynblock.objectName = "AcDbBlockReference" Then 'Check if BlockRef, yes
        
            If dynblock.IsDynamicBlock Then         'Check to see if it is a Dynamic Block
               dybprop = dynblock.GetDynamicBlockProperties
                If dynblock.EffectiveName = "FSM4L- INCH INCREMENT_DONE_01" Then 'Finds Dynamic Block NAME
                    'If dynblock.EffectiveName Like "FSM4L*" Then     THIS WOULD FIND ALL THAT START WITH SAME NAME
                    dynblock.EffectiveName = "ABC123"
                            ThisDrawing.Regen acActiveViewport
                End If
            End If
            
            oldname = dynblock.EffectiveName
            BNAME = dynblock.EffectiveName & "_o"
            Set colBlocks = ThisDrawing.Blocks
            Set objBlock = colBlocks.item(oldname)
            objBlock.Name = BNAME
        End If
    Next

End Sub


Sub sinobj()
Dim i As Integer
Dim sinobj As AcadLWPolyline
Dim plist(0 To 180 * 2 + 1) As Double '在一?周期?等分成180份?描述
For i = 0 To 180 * 2 Step 2
plist(i) = i '180*2
plist(i + 1) = Sin(i / 360 * 8 * Atn(1)) * 100 '?定振幅?100
Next
Set sinobj = ThisDrawing.ModelSpace.AddLightWeightPolyline(plist)
End Sub


Sub sinobj100()
Dim i As Integer
Dim sinobj As AcadLWPolyline
Dim plist(0 To 180 * 2 + 1) As Double '在一?周期?等分成180份?描述
For i = 0 To 180 * 2 Step 2
    plist(i) = i / 100 '180*2
    plist(i + 1) = Sin(i / 100) '?定振幅?100
Next
Set sinobj = ThisDrawing.ModelSpace.AddLightWeightPolyline(plist)
End Sub


Sub sinobj2cos3()
Dim i As Integer
Dim sinobj As AcadLWPolyline
Dim plist() As Double '在一?周期?等分成180份?描述
Dim sval As Double
Dim cval As Double
Dim pos As Integer
Dim dd  As Integer
Dim mm As Double

dd = 360
mm = 36

ReDim plist(0 To (dd * 2) - 1)
For i = 0 To dd - 1
    pos = i * 2
    plist(pos) = i / mm '180*2
    
    If Sin(i / mm) <> 0 Then
        sval = 2 / Sin(i / mm)
    Else
        sval = 0
    End If
        Debug.Print i & ":sval=" & sval
    If Cos(i / mm) <> 0 Then
        cval = 3 / Cos(i / mm)
    Else
        cval = 0
    End If
    
        Debug.Print "   cval=" & cval
    plist(pos + 1) = sval + cval
Next
Set sinobj = ThisDrawing.ModelSpace.AddLightWeightPolyline(plist)
End Sub

Sub ii交點剪段()
    Dim plineObj As AcadLWPolyline
    Dim points(0 To 7) As Double
    
    ' Define the 2D polyline points
    points(0) = -4: points(1) = -1
    points(2) = -4: points(3) = 1
    points(4) = 4: points(5) = 1
    points(6) = 4: points(7) = -1
        
    ' Create a lightweight Polyline object in model space
    Set plineObj = ThisDrawing.ModelSpace.AddLightWeightPolyline(points)
    
   ' Create the circle
    Dim circleObj As AcadCircle
    Dim centerPt(0 To 2) As Double
    Dim radius As Double
    centerPt(0) = 0: centerPt(1) = 1: centerPt(2) = 0
    radius = 1
    Set circleObj = ThisDrawing.ModelSpace.AddCircle(centerPt, radius)
    ZoomAll
      
    ' Find the intersection points between the line and the circle
    Dim intPoints As Variant
    intPoints = plineObj.IntersectWith(circleObj, acExtendNone)
    
    ' Print all the intersection points
    Dim i As Integer, j As Integer, k As Integer
    Dim str As String
    If VarType(intPoints) <> vbEmpty Then
        For i = LBound(intPoints) To UBound(intPoints)
            str = "Intersection Point[" & k & "] is: " & intPoints(j) & "," & intPoints(j + 1) & "," & intPoints(j + 2)
            MsgBox str, , "IntersectWith Example"
            str = ""
            i = i + 2
            j = j + 3
            k = k + 1
        Next
    End If

End Sub


Public Function GetAcad() As AcadApplication

On Error Resume Next

Dim acApp As AcadApplication

Set acApp = GetObject(, "AutoCAD.Application") '<---- without debug generates Runtime Error 13 - Type mismatch

If acApp Is Nothing Then

Set acApp = CreateObject("AutoCAD.Application") '<---- always returns 'Nothing' when triggered

End If

Set GetAcad = acApp

End Function
Sub emptytt()

    Dim ee
    ee = 33
    If Not IsEmpty(ee) Then
        Debug.Print True
    Else
        Debug.Print "no"
    End If

End Sub


Sub runtime_test()
    Dim runT As New runTime
    runT ("asdfyy")
    Dim i As Long
    For i = 0 To 5000
        i = i
        Debug.Print i
    Next
    runT ("asdfyy")
    runT.ToList
End Sub
Function asdf()
    '測式 json
    MsgBox 33
    Dim Json As Object
    Set Json = JsonConverter.ParseJson("{""a"":123,""b"":[1,2,3,4],""c"":{""d"":456}}")
    
    ' Json("a") -> 123
    ' Json("b")(2) -> 2
    ' Json("c")("d") -> 456
    Json("c")("e") = 789
    
    
    Debug.Print Json("a")
    Debug.Print JsonConverter.ConvertToJson(Json)
    ' -> "{"a":123,"b":[1,2,3,4],"c":{"d":456,"e":789}}"
    
    Debug.Print JsonConverter.ConvertToJson(Json, Whitespace:=2)
    ' -> "{
    '       "a": 123,
    '       "b": [
    '         1,
    '         2,
    '         3,
    '         4
    '       ],
    '       "c": {
    '         "d": 456,
    '         "e": 789
    '       }
    '     }"
End Function

Sub sq()
    Dim ia As New MusicItem
    ia.identify_Duration 288

    
End Sub
Sub AddNumber()
'寫上流水號
  
    'Me.Hide
    ' Define the valid keywords
    Dim keywordList As String
    keywordList = "1 2 3 4 0"
    Dim strT As String
    
    Dim textObj As AcadText
    Dim textString As String
    Dim insertionPoint(0 To 2) As Double, alignmentPoint(0 To 2) As Double

    Dim height As Double
   

    ' Call InitializeUserInput to set up the keywords
    ThisDrawing.Utility.InitializeUserInput 129, keywordList
    ' Get the user input
    Dim starNum As Integer
    Dim addNum As Integer
    starNum = ThisDrawing.Utility.GetInteger("要開始的號碼: ")
    addNum = ThisDrawing.Utility.GetInteger("加的倍數: ")

    Dim plineObj As AcadPolyline
    Dim points(0 To 14) As Double
    Dim addX As Double, addY As Double
    
    
    height = 1.8
    textString = val(starNum)

GoToLook:
On Error Resume Next
    
    
    ' Get the user input
    Dim returnPnt As Variant
    returnPnt = ThisDrawing.Utility.GetPoint(, "選位置: ")
    
    If err Then
        '**Description 這個要改的
         If StrComp(err.Description, "使用者輸入的是關鍵字", 1) = 0 Then
         ' One of the keywords was entered
             Dim inputString As String
             err.Clear
             inputString = ThisDrawing.Utility.GetInput
             '取得關鍵字
    '        Select Case inputString
        Else
            Exit Sub
        End If
    End If
    
    addX = returnPnt(0) - (4.6 * 0.8)
    addY = returnPnt(1)
    
    ' Define the 2D polyline points
    points(0) = 0 + addX: points(1) = 0 + addY: points(2) = 0
    points(3) = 4.6 + addX: points(4) = 0 + addY: points(5) = 0
    points(6) = 4.6 + addX: points(7) = 2.7 + addY: points(8) = 0
    points(9) = 0 + addX: points(10) = 2.7 + addY: points(11) = 0
    points(12) = 0 + addX: points(13) = 0 + addY: points(14) = 0
        
    ' Create a lightweight Polyline object in model space
    Set plineObj = ThisDrawing.ModelSpace.AddPolyline(points)
    plineObj.Layer = "TEXT"
    
    ' Define the text object
    
    
    insertionPoint(0) = addX + (4.6 / 2): insertionPoint(1) = addY: insertionPoint(2) = 0
    
    
    ' Create the text object in model space
    Set textObj = ThisDrawing.ModelSpace.AddText(textString, insertionPoint, height)
    
    textObj.Alignment = acAlignmentBottomCenter
    textObj.Layer = "TEXT"
    Call textObj.Move(alignmentPoint, insertionPoint)
    
    
    textString = val(textString) + addNum
    
    GoTo GoToLook
    


End Sub
Sub AllLineAdd()
'計算線的總長度
' Have the user enter a point

    
    ' Create the selection set
    Dim ssetObj As AcadSelectionSet
    'Set ssetObj = ThisDrawing.SelectionSets.Add("TEST_SSET")
    If ThisDrawing.SelectionSets.Count = 0 Then
        Set ssetObj = ThisDrawing.SelectionSets.Add("TEST_SSET")
    Else
        Set ssetObj = ThisDrawing.SelectionSets.item(0)
        ssetObj.Clear
    
    End If
    
    ' Add objects to a selection set by prompting user to select on the screen
    ssetObj.SelectOnScreen
    ssetObj.item (0)
    
    Dim returnPnt As Variant
    Dim str As String
    Dim strAll As String
    Dim i As Integer
    Dim ina As Integer
    Dim counta As Integer
    Dim obj As AcadLine
    Dim allLine As Double
    counta = ssetObj.Count()
    
    
    ' Return a point using a prompt
    ' Translate the point into UCS coordinates
    allLine = 0
    For i = 0 To counta - 1
        Set obj = ssetObj.item(i)
        allLine = allLine + obj.Length
    Next
    

    
    ThisDrawing.Utility.Prompt ("Line all length= " & allLine)

End Sub
Sub InsText()
    'frmInsText.Show 0
    frmInsText.Show
End Sub

Sub mm()
    TestDll_Print.Show 1
End Sub
Sub frmMusic()
    frmMusical.Show 1
End Sub
Sub frmMusicEdit()
    frmEDIT.Show 1
End Sub
Sub easeMusicJoin()
'清除 MusicText 的鏈結
On Error Resume Next
    Dim ent As Object

   
    Dim SSetColl As AcadSelectionSets
    Set SSetColl = ThisDrawing.SelectionSets
    
    ' Create a SelectionSet named "TEST" in the current drawing
    Dim ssetObj As AcadSelectionSet
  
    If SSetColl.Count > 0 Then
        SSetColl.item(0).Delete
    End If
    Set ssetObj = SSetColl.Add("TEST")
    ssetObj.SelectOnScreen
    
    '排序陣列
    Dim TheArray As Variant
    Dim TheArrayEnt As Variant
    Dim coI As Integer
    Dim i As Long
    
    ' Add the dimstyle to the dimstyles collection
    coI = 0
  ' 找出圖面中的每一個選集
    For Each ent In ssetObj
        If (ent.objectName = "MusicText") Then
            ent.RightLink = 0
            ent.LeftLink = 0
            ent.data = "b=!3=c"
            MsgBox ent.data
        End If
    Next
End Sub
Sub addMusicJoin()
'取得物件 MusicText
'用x 軸來鏈結
On Error Resume Next

    Dim ent As Object

   
    Dim SSetColl As AcadSelectionSets
    Set SSetColl = ThisDrawing.SelectionSets
    
    ' Create a SelectionSet named "TEST" in the current drawing
    Dim ssetObj As AcadSelectionSet
  
    If SSetColl.Count > 0 Then
        SSetColl.item(0).Delete
    End If
    Set ssetObj = SSetColl.Add("TEST")
    ssetObj.SelectOnScreen
    
    '排序陣列
    Dim TheArray As Variant
    Dim TheArrayEnt As Variant
    Dim coI As Integer
    Dim i As Long
    
    ' Add the dimstyle to the dimstyles collection
    coI = 0
  ' 找出圖面中的每一個選集
    For Each ent In ssetObj
        If (ent.objectName = "AsdkSmiley") Then
            coI = coI + 1
        End If
    Next
    ReDim TheArray(coI - 1)
    ReDim TheArrayEnt(coI - 1)
    
    coI = 0
    Dim MTobj As SmileyEntity
    Dim pt As Variant
    For Each ent In ssetObj
        If (ent.objectName = "AsdkSmiley") Then
            pt = ent.insertionPoint()
            TheArray(coI) = pt(0)
            Set TheArrayEnt(coI) = ent
            coI = coI + 1
        End If
    Next
    
    
    '只有一個，不用排序了
    If UBound(TheArray) = 1 Then
        Exit Sub
    End If
    
    '排序開始
    SelectionSortMaxTow TheArray, TheArrayEnt
    
    For i = 0 To UBound(TheArray)
        If i = 0 Then
            TheArrayEnt(i).LeftLink = 0
            TheArrayEnt(i).RightLink = TheArrayEnt(i + 1).ObjectID
        ElseIf i = UBound(TheArray) Then
            TheArrayEnt(i).LeftLink = TheArrayEnt(i - 1).ObjectID
            TheArrayEnt(i).RightLink = 0
        Else
            TheArrayEnt(i).RightLink = TheArrayEnt(i + 1).ObjectID
        End If
    Next
      
End Sub




Sub asdfqwe()
    Dim aas As AcadDatabase
    'Set aas = New Aprint.INS_Object
    Dim SEOBJ As SmileyEntity
    Dim entObj As AcadObject
    Dim basePnt(0 To 2) As Double
    
    ThisDrawing.Utility.GetEntity entObj, basePnt, "\n請選擇要修改的物件"
    If (entObj.objectName = "AsdkSmiley") Then
        Set SEOBJ = entObj
        Call SEOBJ.setData(SEOBJ.insertionPoint(), "b !5=z", "MMP2005", 44)
    End If
    'Call aas.AddLine(234, 11, 33, 55)
End Sub

Sub linkRight()
    Dim SEOBJ As SmileyEntity
    Dim basePnt(0 To 2) As Double
    Dim cenPnt(0 To 2) As Double
    Dim returnPnt As Variant
    Dim rad As Integer
    
    returnPnt = ThisDrawing.Utility.GetPoint(basePnt, "\n選擇要插入的點")
    

    'Set SEOBJ = New SmileyEntity
    Dim SSS As New SmileyApplication
    Dim ss As SmileyUi.SmileyApplication
    
    Set SEOBJ = ThisDrawing.ModelSpace.AddCustomObject("ASDKSMILEY")
    Call SEOBJ.setNewObject(returnPnt, 1)
    Call SEOBJ.setData(returnPnt, "#f?2=m", "MMP2005", 44)
    
    Dim entObj As AcadObject
    ThisDrawing.Utility.GetEntity entObj, basePnt, "\n請選擇要鏈結的物件"
    SEOBJ.RightLink = entObj.ObjectID
    
    MsgBox Hex(SEOBJ.RightLink)
End Sub

Sub getlinkRight()
    Dim SEOBJ As SmileyEntity
    Dim basePnt(0 To 2) As Double
    Dim cenPnt(0 To 2) As Double
    Dim returnPnt As Variant
    Dim rad As Integer


    Dim entObj As AcadObject
goUP:
    ThisDrawing.Utility.GetEntity entObj, basePnt, "\n請選擇要鏈結的物件"
    Set SEOBJ = entObj
    MsgBox SEOBJ.ObjectID
    
    MsgBox "這物件的 id- " & Hex(SEOBJ.ObjectID) & vbCrLf & _
        " LeftLink 的id- " & Hex(SEOBJ.LeftLink) & vbCrLf & _
        " RightLink 的id- " & Hex(SEOBJ.RightLink)
    GoTo goUP
End Sub

Sub aa()
    Dim moda As Integer
    mymode = 0
    
    Dim x, y, Z As Double
    Dim ret As Integer
    
    ret = getPT(x, y, Z)
    
    Dim abc As AcadEntity
    Dim pt As Variant
    ThisDrawing.ActiveSelectionSet.SelectOnScreen
    
    Dim oldpt As Variant
    Dim newpt(2) As Double
    oldpt = ThisDrawing.Utility.GetPoint(, "\n指定移?起 as  ")
    
    Dim mylne As AcadLine
    ret = getPT(x, y, Z)
    Dim startPt(2) As Double
    Dim endPt(2) As Double
    
    endPt(0) = x: endPt(1) = y: endPt(2) = Z
    Set mylne = ThisDrawing.ModelSpace.AddLine(oldpt, endPt)
    Dim tmp(0) As Double
    
    Do While ret = 1
    
    ret = getPT(x, y, Z)
    newpt(0) = x: newpt(1) = y: newpt(2) = Z
    mylne.Endpoint = newpt
    For Each ent In ThisDrawing.ActiveSelectionSet
    ent.Move oldpt, newpt

Next
oldpt(0) = newpt(0): oldpt(1) = newpt(1): oldpt(2) = newpt(2)
Loop
mylne.Delete
End Sub



Option Explicit


''設置指定詞典擴展記錄
'
Public Function Dhvb_SetXrecord(objDict As AcadDictionary, _
        XRecordName As String, _
        XRecordData As Variant) _
        As AcadXRecord
        
    Dim objXRecord As AcadXRecord
    Dim XRecordType As Variant
    Dim i As Long
    '檢察對象詞典是否有該名擴展記錄,如果已經存在則刪除
    On Error Resume Next
    Set objXRecord = objDict.GetObject(XRecordName)
    If Not objXRecord Is Nothing Then
        objDict.Remove XRecordName
    End If
    On Error GoTo 0
        '建立擴展記錄數據
    ReDim XRecordType(0 To UBound(XRecordData)) As Integer
    
    For i = 0 To UBound(XRecordData)
        Select Case VarType(XRecordData(i))
        Case vbInteger, vbLong
            XRecordType(i) = 90    '整數組碼=90
        Case vbSingle, vbDouble
            XRecordType(i) = 40    '實數組碼=40
        Case vbString
            XRecordType(i) = 2    '字符組碼=2
        End Select
    Next    '添加擴展記錄到對象詞典
    Set objXRecord = objDict.AddXRecord(XRecordName)
    objXRecord.SetXRecordData XRecordType, XRecordData    '返回擴展記錄對象
    Set Dhvb_SetXrecord = objXRecord
End Function

Sub Test()
' 創建直線
    Dim lineObj As AcadLine
    Dim startPt(0 To 2) As Double, endPt(0 To 2) As Double
    startPt(0) = 1#: startPt(1) = 1#: startPt(2) = 0#
    endPt(0) = 5#: endPt(1) = 5#: endPt(2) = 0#
    Set lineObj = ThisDrawing.ModelSpace.AddLine(startPt, endPt)
    ' 創建擴展數據
    Dim DataType(0 To 1) As Integer
    Dim data(0 To 1) As Variant
    Dim reals3(0 To 2) As Double
    Dim worldPos(0 To 2) As Double
    DataType(0) = 1001: data(0) = "Test_Application" '應用程序名
    DataType(1) = 1000: data(1) = "This is a test for xdata" '字符串類型
    lineObj.SetXData DataType, data '設置擴展數據
    ' 返回直線的擴展數據
    Dim xdataOut As Variant
    Dim xtypeOut As Variant
    lineObj.GetXData "Test_Application", xtypeOut, xdataOut
    
    
    
    
End Sub


'以下是一些在開發人員手冊中的關於擴展數據的示例。
'將擴展數據指定給選擇集中的所有對象
'本例提示用戶選擇圖形中的對象，然後將選定的對象置於選擇集中，並且指定的擴展數據將附著到該選擇集中的所有對象。
Sub Ch10_AttachXDataToSelectionSetObjects()
   'On Error Resume Next
    ' 創建選擇集
    
    Dim sset As AcadSelectionSet
    Dim i As Integer
    'sset.Item(1).Delete
    
    'For i = 0 To ThisDrawing.SelectionSets.Count - 1
        ThisDrawing.SelectionSets.item("SS1").Delete
    'Next
    Set sset = ThisDrawing.SelectionSets.Add("SS1")
    
    ' 提示用戶選擇對象
    sset.SelectOnScreen
    
    ' 定義擴展數據
    Dim appName As String, xdataStr As String
    
    appName = "MY_APP"
    xdataStr = "This is some xdata"
    
    Dim xDataType(0 To 2) As Integer
    Dim xData(0 To 2) As Variant
    
    ' 為每個數組定義值
    '1001 指示 appName
    xDataType(0) = 1001
    xData(0) = appName
    
    '1000 指示字符串值
    xDataType(1) = 1000
    xData(1) = xdataStr
    
    ' 遍歷選擇集中的所有圖元
    ' 將擴展數據設置和指定給每個圖元
    Dim ent As Object
    
    For Each ent In sset
        '1000 指示字符串值
        xDataType(2) = 1000
        xData(2) = ent.objectName
        
        ent.SetXData xDataType, xData
    Next ent

End Sub

'查看選擇集中所有對象的擴展數據
'本例顯示上例所附著的擴展數據。如果附著的擴展數據不是字符串（類型 1000）類型，則需要修改此代碼。
Sub Ch10_ViewXData()

    ' 查找上例中創建的選擇集
    
    Dim sset As Object
    Set sset = ThisDrawing.SelectionSets.item("SS1")
    
    ' 定義擴展數據變量以保存擴展數據信息
    
    Dim xDataType As Variant
    Dim xData As Variant
    Dim xd As Variant
    
    '定義索引計數器
    Dim xdi As Integer
    xdi = 0
    
    ' 遍歷選擇集中的對象
    ' 並檢索對象的擴展數據
    Dim msgstr As String
    Dim appName As String
    Dim ent As AcadEntity
    
    appName = "MY_APP"
    For Each ent In sset
        msgstr = ""
        xdi = 0
        
        ' 檢索 appName 擴展數據類型和值
        ent.GetXData appName, xDataType, xData
        ' 如果未初始化 xdataType 變量，
        ' 則沒有可供該圖元檢索的 appName 擴展數據
        If VarType(xDataType) <> vbEmpty Then
        
            For Each xd In xData
                msgstr = msgstr & vbCrLf & xDataType(xdi) _
                & ": " & xd
                xdi = xdi + 1
            Next xd

        End If
    
        ' 如果 msgstr 變量為 NULL，則沒有擴展數據
        
        If msgstr = "" Then msgstr = vbCrLf & "NONE"
        
        MsgBox appName & " xdata on " & ent.objectName & _
        ":" & vbCrLf & msgstr

    Next ent

End Sub

'選擇包含擴展數據的圓
'下例過濾包含由「MY_APP」應用程序添加的擴展數據的圓：
Sub Ch4_FilterXdata()
    'On Error Resume Next
    Dim sstext As AcadSelectionSet
    Dim mode As Integer
    Dim pointsArray(0 To 11) As Double
    
    mode = acSelectionSetWindowPolygon
    pointsArray(0) = -12#: pointsArray(1) = -7#: pointsArray(2) = 0
    pointsArray(3) = -12#: pointsArray(4) = 10#: pointsArray(5) = 0
    pointsArray(6) = 10#: pointsArray(7) = 10#: pointsArray(8) = 0
    pointsArray(9) = 10#: pointsArray(10) = -7#: pointsArray(11) = 0
    
    Dim FilterType(1) As Integer
    Dim FilterData(1) As Variant
    ThisDrawing.SelectionSets.item("SS9").Delete
    Set sstext = ThisDrawing.SelectionSets.Add("SS9")

    FilterType(0) = 0
    FilterData(0) = "Circle"
    FilterType(1) = 1001
    FilterData(1) = "MY_APP"
    sstext.SelectByPolygon mode, pointsArray, FilterType, FilterData

End Sub


Sub Day15_1_FIX()
    
    Dim rng As Object
    Dim strData
    
    Dim dvbPath As String
    Dim acadPath As String
    acadPath = ThisDrawing.Application.path
    dvbPath = GetDVBThis("MusicalAprintf")
    
    '使用 Open 陳述式，配合Print寫入資料
    '使用&連接自訂的「相隔符號」，取代內建的功能
    
    Open "c:\temp\acad.lsp" For Output As #1
    
    Print #1, "(defun S::STARTUP ()"
    Print #1, "(command ""_vbaload"" "
    Print #1, """" & dvbPath & """"
    Print #1, ")"
    
    

    Print #1, acadPath
    Close #1
'(load "Lispfile1" "nLispfile1 not loaded")
'(load "Lispfile2" "nLispfile2 not loaded")
'(load "Lispfile3" "nLispfile3 not loaded")
    
End Sub
Public Function GetDVBThis(DVBFileName As String) As String
    Dim i As Integer
    Dim strFileName As String
    
    For i = 1 To ThisDrawing.Application.vbe.VBProjects.Count
        strFileName = ThisDrawing.Application.vbe.VBProjects.item(i).fileName
        If InStr(UCase(strFileName), UCase(DVBFileName)) > 0 Then
            GetDVBThis = strFileName
            Exit For
        End If
    
    Next i

End Function
Public Function GetDVBPath(DVBFileName As String) As String
    Dim i As Integer
    Dim strFileName As String
    
    For i = 1 To ThisDrawing.Application.vbe.VBProjects.Count
        strFileName = ThisDrawing.Application.vbe.VBProjects.item(i).fileName
        If InStr(UCase(strFileName), UCase(DVBFileName)) > 0 Then
            GetDVBPath = GetPath(strFileName)
            Exit For
        End If
    
    Next i

End Function
Function GetPath(strFileName As String) As String
    Dim CPath As String
    CPath = left(strFileName, InStrRev(strFileName, "\") - 1)
    GetPath = CPath '< sure wish it was return, I like that better, this makes me think it is redefining the function
End Function

Private Sub AcadDocument_Activate()
    SetMusicTextToolsBar
    'Example_SetTools
    'Example_SetMusicTextTools
End Sub

Private Sub AcadDocument_BeginLisp(ByVal FirstLine As String)
    Dim ppt As New point
    Call ppt.c(4, 4, 0)
    Select Case FirstLine
        Case "(C:LL)"
            lineAndWline
        Case "(C:2L)"
            line2line
        Case "(C:L2)"
            line2
        Case "(C:ZZ)"
            Call donut(ppt, 0, 0.95)
        Case Else
    End Select


End Sub
Private Function donut(tcen As point, o1 As Double, o2 As Double) As AcadLWPolyline
'tcen 環的圓心
'o1 環的內徑
'o2 環的外徑
       '聚合線 畫弧
       Dim plineSlur As AcadLWPolyline
       Dim points(0 To 3) As Double
       Dim lenght As Double '環的距離
       Dim width As Double  '環的寬度
       Dim islurAddX As Integer
       Dim islurAddY As Integer
       lenght = (Abs(o1) + Abs(o2)) / 4
       width = Abs(o1 - o2) / 2
       ' Define the 2D polyline points
       points(0) = tcen.x - lenght
       points(1) = tcen.y
       points(2) = tcen.x + lenght
       points(3) = tcen.y
           
       ' Create a lightweight Polyline object in model space
       Set plineSlur = ThisDrawing.ModelSpace.AddLightWeightPolyline(points)

       ' Change the bulge of the third segment
       plineSlur.SetBulge 0, 1
       plineSlur.SetBulge 1, 1
       plineSlur.setWidth 0, width, width
       plineSlur.setWidth 1, width, width
       plineSlur.Closed = True
       
       
       
       plineSlur.Update
                                    
       Set donut = plineSlur
                    
End Function
Private Sub lineAndWline()
On Error Resume Next
    Dim ent As Object

   
    Dim SSetColl As AcadSelectionSets
    Set SSetColl = ThisDrawing.SelectionSets
    
    ' Create a SelectionSet named "TEST" in the current drawing
    Dim ssetObj As AcadSelectionSet
  
    If SSetColl.Count > 0 Then
        SSetColl.item(0).Delete
    End If
    Set ssetObj = SSetColl.Add("TEST")
    ssetObj.SelectOnScreen
    
    '排序陣列
    Dim TheArray As Variant
    Dim TheArrayEnt As Variant
    Dim coI As Integer
    Dim i As Long
    Dim oLine As AcadPolyline
    Dim startPt As New point
    Dim endPt As New point
    Dim ptlist As New PointList
    Dim retCoord As Variant


    ' Add the dimstyle to the dimstyles collection
    coI = 0
  ' 找出圖面中的每一個選集
    For Each ent In ssetObj
        If (ent.objectName = "AcDb2dPolyline") Then
            
            retCoord = ent.Coordinates
            startPt.x = retCoord(0): startPt.y = retCoord(1): startPt.Z = retCoord(2)
            endPt.x = retCoord(3): endPt.y = retCoord(4): endPt.Z = retCoord(5)
            startPt.x = startPt.x + 1
            endPt.x = endPt.x + 1
            ptlist.addpt startPt
            ptlist.addpt endPt
            Set oLine = ThisDrawing.ModelSpace.AddPolyline(ptlist.list)
            oLine.Layer = ent.Layer
            oLine.ConstantWidth = 0.6
            
        End If
    Next
End Sub
Private Sub line2line()
On Error Resume Next
    Dim ent As Object

   
    Dim SSetColl As AcadSelectionSets
    Set SSetColl = ThisDrawing.SelectionSets
    
    ' Create a SelectionSet named "TEST" in the current drawing
    Dim ssetObj As AcadSelectionSet
  
    If SSetColl.Count > 0 Then
        SSetColl.item(0).Delete
    End If
    Set ssetObj = SSetColl.Add("TEST")
    ssetObj.SelectOnScreen
    
    '排序陣列
    Dim TheArray As Variant
    Dim TheArrayEnt As Variant
    Dim coI As Integer
    Dim i As Long
    Dim oLine As AcadPolyline
    Dim startPt As New point
    Dim endPt As New point
    Dim ptlist As New PointList
    Dim retCoord As Variant
    Dim objDonut As AcadLWPolyline


    ' Add the dimstyle to the dimstyles collection
    coI = 0
  ' 找出圖面中的每一個選集
    For Each ent In ssetObj
        If (ent.objectName = "AcDb2dPolyline") Then
            
            retCoord = ent.Coordinates
            startPt.x = retCoord(0): startPt.y = retCoord(1): startPt.Z = retCoord(2)
            endPt.x = retCoord(3): endPt.y = retCoord(4): endPt.Z = retCoord(5)
            startPt.x = startPt.x + 1
            endPt.x = endPt.x + 1
            ptlist.addpt startPt
            ptlist.addpt endPt
            Set oLine = ThisDrawing.ModelSpace.AddPolyline(ptlist.list)
            oLine.Layer = ent.Layer
            oLine.ConstantWidth = 0.6
            
            '畫第一點
            startPt.x = startPt.x - 1.39 - 1
            startPt.y = startPt.y - 3.55
            Set objDonut = donut(startPt, 0, 0.95)
            objDonut.Layer = ent.Layer
            
            '畫第二點
            startPt.y = startPt.y - 3.47
            Set objDonut = donut(startPt, 0, 0.95)
            objDonut.Layer = ent.Layer
        End If
    Next
End Sub
Private Sub line2()
On Error Resume Next
    Dim ent As Object

   
    Dim SSetColl As AcadSelectionSets
    Set SSetColl = ThisDrawing.SelectionSets
    
    ' Create a SelectionSet named "TEST" in the current drawing
    Dim ssetObj As AcadSelectionSet
  
    If SSetColl.Count > 0 Then
        SSetColl.item(0).Delete
    End If
    Set ssetObj = SSetColl.Add("TEST")
    ssetObj.SelectOnScreen
    
    '排序陣列
    Dim TheArray As Variant
    Dim TheArrayEnt As Variant
    Dim coI As Integer
    Dim i As Long
    Dim oLine As AcadPolyline
    Dim startPt As New point
    Dim endPt As New point
    Dim ptlist As New PointList
    Dim retCoord As Variant
    Dim objDonut As AcadLWPolyline
    


    ' Add the dimstyle to the dimstyles collection
    coI = 0
  ' 找出圖面中的每一個選集
    For Each ent In ssetObj
        If (ent.objectName = "AcDb2dPolyline") Then
            
            retCoord = ent.Coordinates
            startPt.x = retCoord(0): startPt.y = retCoord(1): startPt.Z = retCoord(2)
            endPt.x = retCoord(3): endPt.y = retCoord(4): endPt.Z = retCoord(5)
            startPt.x = startPt.x - 1
            endPt.x = endPt.x - 1
            ptlist.addpt startPt
            ptlist.addpt endPt
            Set oLine = ThisDrawing.ModelSpace.AddPolyline(ptlist.list)
            oLine.Layer = ent.Layer
            oLine.ConstantWidth = 0.6
            '畫第一點
            startPt.x = startPt.x + 1.39 + 1
            startPt.y = startPt.y - 3.55
            Set objDonut = donut(startPt, 0, 0.95)
            objDonut.Layer = ent.Layer
            
            '畫第二點
            startPt.y = startPt.y - 3.47
            Set objDonut = donut(startPt, 0, 0.95)
            objDonut.Layer = ent.Layer
        End If
    Next
End Sub

Private Sub AcadDocument_Deactivate()

    'Example_SetTools
    'Example_SetMusicTextTools
End Sub

Sub Load_TTF_QuGin()
    Call AddFontResource("e:\GuQinKai03.ttf")
    Call AddFontResource("e:\QIN01.ttf")
    Call AddFontResource("e:\QIN02.ttf")
    Call AddFontResource("e:\QIN03.ttf")
    Call SendMessage(HWND_BROADCAST, WM_FONTCHANGE, 0, 0)
End Sub




Sub Example_GetBulge()
    ' This example creates a lightweight polyline in model space.
    ' It then finds and changes the bulge for a given segment.
    '聚合線 畫弧
    Dim plineObj As AcadLWPolyline
    Dim points(0 To 7) As Double
    Dim lenght As Double
    lenght = 51
    
    ' Define the 2D polyline points
    points(0) = 0: points(1) = 0
    points(2) = 1.9 * 2: points(3) = 1.3755 * 2
    points(4) = points(2) + lenght: points(5) = points(3)
    points(6) = points(4) + points(2): points(7) = points(1)
        
    ' Create a lightweight Polyline object in model space
    Set plineObj = ThisDrawing.ModelSpace.AddLightWeightPolyline(points)
    ZoomAll
    
    ' Find the bulge of the third segment
    Dim currentBulge As Double
    currentBulge = plineObj.GetBulge(3)
    ' Change the bulge of the third segment
'    plineObj.SetBulge 0, -0.32401
'    plineObj.SetBulge 2, -0.32401
    plineObj.SetBulge 0, -0.7
    plineObj.SetBulge 2, -0.32401
    plineObj.Update
    
End Sub
Sub Example_GetFont()
    ' This example find the font information for the active text style.
    
    Dim typeFace As String
    Dim Bold As Boolean
    Dim Italic As Boolean
    Dim charSet As Long
    Dim PitchandFamily As Long
    
    ThisDrawing.ActiveTextStyle.GetFont typeFace, Bold, Italic, charSet, PitchandFamily
    
    MsgBox "The current text style has the following font properties:" & vbCrLf _
            & "Typeface: " & typeFace & vbCrLf _
            & "Bold: " & Bold & vbCrLf _
            & "Italic: " & Italic & vbCrLf _
            & "Character set: " & charSet & vbCrLf _
            & "Pitch and Family: " & PitchandFamily
    
End Sub


Sub Ch4_ImportingAndExporting()

    '創建圓用於直觀顯示
    
    Dim circleObj As AcadCircle
    
    Dim centerPt(0 To 2) As Double
    
    Dim radius As Double
    
    centerPt(0) = 2: centerPt(1) = 2: centerPt(2) = 0
    
    radius = 1
    
    Set circleObj = ThisDrawing.ModelSpace.AddCircle(centerPt, radius)
    
    ThisDrawing.Application.ZoomAll
    
    '創建空的選擇集
    
    Dim sset As AcadSelectionSet
    
    Set sset = ThisDrawing.SelectionSets.Add("NEWSSET")
    
    '將當前圖形輸出到AutoCAD 臨時文件目錄下的 DXF 文件
    
    Dim tempPath As String
    
    Dim exportFile As String
    
    Const dxfname As String = "DXFExprt"
    
    tempPath = ThisDrawing.Application.preferences.Files.TempFilePath
    
    exportFile = tempPath & dxfname
    
    ThisDrawing.Export exportFile, "DXF", sset
    
    '刪除空的選擇集
    
    ThisDrawing.SelectionSets.item("NEWSSET").Delete
    
    '打開新圖形
    
    ThisDrawing.Application.Documents.Add "acad.dwt"
    
    '定義輸入
    
    Dim importFile As String
    
    Dim insertPoint(0 To 2) As Double
    
    Dim scalefactor As Double
    
    importFile = tempPath & dxfname & ".dxf"
    
    insertPoint(0) = 0: insertPoint(1) = 0: insertPoint(2) = 0
    
    scalefactor = 2#
    
    '輸入文件
    
    ThisDrawing.Import importFile, insertPoint, scalefactor
    
    ThisDrawing.Application.ZoomAll

End Sub



Sub Ch4_ZoomWindow()
'將當前圖形縮放至兩點定義的窗口。
Dim point1(0 To 2) As Double

Dim point2(0 To 2) As Double

point1(0) = 1.3: point1(1) = 7.8: point1(2) = 0

point2(0) = 13.7: point2(1) = -2.6: point2(2) = 0

ThisDrawing.Application.ZoomWindow point1, point2

End Sub

Sub Ch4_PositionApplicationWindow()
'將 AutoCAD應用程序窗口放在屏幕的左上角，並將其大小調整為寬 400 像素、高 400 像素。
ThisDrawing.Application.WindowTop = 0

ThisDrawing.Application.WindowLeft = 0

ThisDrawing.Application.width = 400

ThisDrawing.Application.height = 400

End Sub


'設置Application對象的WindowState屬性 （acMax、asMin或acNorm）

Sub Ch4_MaximizeApplicationWindow()
'height= 537
'width =315

'將當前圖形縮放至兩點定義的窗口。
    Dim point1(0 To 2) As Double
    
    Dim point2(0 To 2) As Double

    ' Return a point using a base point and a prompt
    Dim onePnt As Variant
    Dim towPnt As Variant
    Dim xx As Double
    Dim yy As Double
    Dim meScale As Double
    Dim ptScale As Double
    
    onePnt = ThisDrawing.Utility.GetPoint(, "第一點: ")
    towPnt = ThisDrawing.Utility.GetPoint(onePnt, "第二點: ")
    point1(0) = onePnt(0): point1(1) = onePnt(1): point1(2) = onePnt(2)
    
    point2(0) = towPnt(0): point2(1) = towPnt(1): point2(2) = towPnt(2)

    '改變應用程序窗口 大小。
    With ThisDrawing
        .Application.WindowState = acMax
        .WindowState = acNorm
        .width = 800
        .height = 580
        xx = Abs(point1(0) - point2(0))
        yy = Abs(point1(1) - point2(1))
        meScale = .width / .height
        ptScale = xx / yy
        
        If (meScale <= ptScale) Then
            .height = yy * (.width / xx)
        .width = 800
            .height = yy * (.width / xx)
        Else
            .width = xx * (.height / yy)
        .height = 580
            .width = xx * (.height / yy)
        End If
        

        .Application.ZoomWindow point1, point2
       
    End With


    Dim SSetColl As AcadSelectionSets
    Set SSetColl = ThisDrawing.SelectionSets
    
    ' Create a SelectionSet named "TEST" in the current drawing
    Dim ssetObj As AcadSelectionSet
  
    If SSetColl.Count = 2 Then
        SSetColl.item(0).Delete
        SSetColl.item(1).Delete
    ElseIf SSetColl.Count > 0 Then
        SSetColl.item(0).Delete
    End If
    Set ssetObj = SSetColl.Add("TEST")

    Call ssetObj.Select(acSelectionSetWindow, point1, point2)
    
    
    ' Define the name for the exported file
    Dim exportFile As String

    exportFile = saveFile("哀哀", _
    "WMF Files (*.WMF)" & Chr$(0) & "*.WMF" & Chr$(0) _
    & "X Files (*.x)" & Chr$(0) & "*.x" & Chr$(0) _
    & "XMesh Files (*.xms)" & Chr$(0) & "*.xms" & Chr$(0) _
    & "All Files (*.*)" + Chr$(0) + "*.*" + Chr$(0))
        
        
    ' Export the current drawing to the file specified above.
    ThisDrawing.Export exportFile, "WMF", ssetObj

'若最小化應用程序窗口 , 則按下列語句:

'ThisDrawing.Application.WindowState = acMin
End Sub
Public Sub GetAttribute()
    '本段代碼從選中的圖塊中獲取屬性值，並對其修改
    Dim entObj As AcadEntity
    Dim pickPnt As Variant
    Dim blkRefObj As AcadBlockReference
    '選擇圖元
    ThisDrawing.Utility.GetEntity entObj, pickPnt
    '判斷是否為塊引用
    If StrComp(entObj.objectName, "AcDbBlockReference", 1) <> 0 Then
        MsgBox "你選擇的不是一個圖塊，程序將退出！"
        '如果選擇的不是一個塊引用則程序退出運行
        Exit Sub
    End If
    '如果選擇的是塊引用，將其賦給塊引用對象
    Set blkRefObj = entObj
    '判斷該塊引用是否含有屬性值
    If Not blkRefObj.HasAttributes Then
        MsgBox "你選擇的圖塊沒有塊屬性，程序將退出！"
        '如果不含由屬性值退出
        Exit Sub
    End If
    Dim attVars As Variant
    Dim i As Integer
    Dim SSATT As String
    '獲取塊引用中的塊屬性對象
    attVars = blkRefObj.GetAttributes
    '對塊屬性對象進行遍歷
    SSATT = ""
    For i = 0 To UBound(attVars)
        SSATT = SSATT & vbCrLf & _
           "Case """ & attVars(i).TagString & """"
'        MsgBox "第" & I + 1 & "屬性對象的屬性值分別如下：" & Chr(13) & Chr(13) & _
'               "屬性標籤為：" & attVars(I).TagString & Chr(13) & _
'               "屬性值為：" & attVars(I).textString
    Next
    ThisDrawing.Utility.Prompt SSATT
    '將塊屬性的標籤和值進行修改
    'attVars(0).TagString = "New Tag"
    'attVars(0).textString = "New Value"
    'ThisDrawing.Regen True
End Sub

Attribute VB_Name = "TieElem"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public typs As String
Public isTie As Boolean
Public stemdir As String
Public dotted As Boolean
Public anchor1 As RelativeElement
Public anchor2 As RelativeElement
Public isGrace As Boolean
Public fixedY As Boolean
Public voicenumber As Integer
Public internalNotes As RelativeElementList
Public top As Double
Public bottom As Double
Public startLimitX As AbsoluteElement
Public endLimitX As AbsoluteElement
Public above As Boolean
Public startX As Double
Public endX As Double
Public startY As Double
Public endY As Double
Public elemset As iArray    'SVGPathElement[]
Public hint As Boolean
Public Sub init(options As Dictionary)
        Me.typs = "TieElem"
        ''  console.log("constructor", options.anchor1 ? options.anchor1.pitch : "N/A", options.anchor2 ? options.anchor2.pitch : "N/A", options.isTie, options.isGrace)
        Set Me.anchor1 = options("anchor1")  '' must have a .x and a .pitch, and a .parent property or be null (means starts at the "beginning" of the line - after keysig)
        Set Me.anchor2 = options("anchor2")  '' must have a .x and a .pitch property or be null (means ends at the end of the line)
        If (options("isGrace")) Then Me.isGrace = True
        If (options("fixedY")) Then Me.fixedY = True
        If (options("stemDir")) Then Me.stemdir = options("stemDir")
        If (options("voiceNumber")) Then Me.voicenumber = options("voiceNumber")
        If (options("style")) Then Me.dotted = True
        Set Me.internalNotes = New RelativeElementList
End Sub

Public Sub addInternalNote(note)
        Me.internalNotes.Push note
End Sub

Public Sub setEndAnchor(anchor2 As RelativeElement)
        ''  console.log("end", me.anchor1 ? me.anchor1.pitch : "N/A", anchor2 ? anchor2.pitch : "N/A", me.isTie, me.isGrace)
        Set Me.anchor2 = anchor2  '' must have a .x and a .pitch property or be null (means ends at the end of the line)

        '' we don't really have enough info to know what the vertical extent is yet and we won't until drawing. This will just give it enough
        '' room on either side (we don't even know if the slur will be above yet). We need to set this so that we can make sure the voice has
        '' at least enough room that the line doesn't get cut off if the tie or slur is the lowest thing.
        If Not (Me.anchor1 Is Nothing) Then
            Me.top = Math.max(Me.anchor1.pitch, Me.anchor2.pitch) + 4
            Me.bottom = Math.min(Me.anchor1.pitch, Me.anchor2.pitch) - 4
         Else
            Me.top = Me.anchor2.pitch + 4
            Me.bottom = Me.anchor2.pitch - 4
        End If
End Sub

    '' If we encounter a repeat sign, then we don't want to extend either a tie or a slur past it, so these are called to be a limit.
Public Sub setStartX(startLimitElem As AbsoluteElement)
        Set Me.startLimitX = startLimitElem
End Sub

Public Sub setEndX(endLimitElem As AbsoluteElement)
        Set Me.endLimitX = endLimitElem
End Sub

Public Sub setHint()
        Me.hint = True
End Sub

Public Sub calcTieDirection()
        '' The rules:
        '' 1) If it is in a grace note group, then the direction is always BELOW.
        '' 2) If it is in a single voice, then the direction is always OPPOSITE of the stem (or where the stem would have been in the case of whole notes.)
        '' 3) If the stem direction is forced (probably because there are two voices on the same line), then the direction is the SAME as the stem direction.

        If (Me.isGrace) Then
            Me.above = False
        ElseIf (Me.voicenumber = 0) Then
            Me.above = True
        ElseIf (Me.voicenumber > 0) Then
            Me.above = False
        Else
            Dim referencePitch As Integer
            If (Not Me.anchor1 Is Nothing) Then
                referencePitch = Me.anchor1.pitch
            ElseIf Not (Me.anchor2 Is Nothing) Then
                referencePitch = Me.anchor2.pitch
            Else
                referencePitch = 14  '' TODO-PER: this can't really happen normally. This would imply that a tie crossed over three lines, something like "C-\nz\nC"
            '' Put the arc in the opposite direction of the stem. That isn't always the pitch if one or both of the notes are beamed with something that affects its stem.
            If (Not Me.anchor1 Is Nothing) And (Not Me.anchor2 Is Nothing) Then
                    If (Me.anchor1.stemdir = "down") And (Me.anchor2.stemdir = "down") Then
                        Me.above = True
                    ElseIf (Me.anchor1.stemdir = "up") And (Me.anchor2.stemdir = "up") Then
                        Me.above = False
                    Else
                        Me.above = referencePitch >= 6
                    End If
            ElseIf (Not Me.anchor1 Is Nothing) Then
                Me.above = (Me.anchor1.stemdir = "down")
            ElseIf (Not Me.anchor2 Is Nothing) Then
                Me.above = (Me.anchor2.stemdir = "down")
            Else
                Me.above = referencePitch >= 6
        End If
End Sub

    '' From "standard music notation practice" by Music Publishers’ Association:
    '' 1) Slurs are placed under the note heads if all stems go up.
    '' 2) Slurs are placed over the note heads if all stems go down.
    '' 3) If there are both up stems and down stems, prefer placing the slur over.
    '' 4) When the staff has opposite stemmed voices, all slurs should be on the stemmed side.

Public Sub calcSlurDirection()
        If (Me.isGrace) Then
            Me.above = False
        ElseIf (Me.voicenumber = 0) Then
            Me.above = True
        ElseIf (Me.voicenumber > 0) Then
            Me.above = False
        Else
            Dim hasDownStem   As Boolean
            Dim i As Integer
            Dim rel As RelativeElement
            hasDownStem = False
            
            If (Not Me.anchor1 Is Nothing) Then
                hasDownStem = IIf(Me.anchor1.stemdir = "down", True, False)
            Else
                hasDownStem = False
            End If
            If (Not Me.anchor2 Is Nothing) Then
                hasDownStem = IIf(Me.anchor2.stemdir = "down", True, False)
            Else
                hasDownStem = False
            End If
            
            For i = 0 To Me.internalNotes.Count - 1
                Set rel = Me.internalNotes(i)
                If (rel.stemdir = "down") Then
                    hasDownStem = True
                End If
            Next
            Me.above = hasDownStem
        
End Sub

Public Sub calcX(lineStartX As Double, lineEndX As Double)
        If (Not Me.anchor1 Is Nothing) Then
            Me.startX = Me.anchor1.x  '' The normal case where there is a starting element to attach to.
            If (Me.anchor1.scalex < 1) Then '' this is a grace note - don't offset the tie as much.
                Me.startX = Me.startX - 3
        ElseIf Not (Me.startLimitX Is Nothing) Then
            Me.startX = Me.startLimitX.x + Me.startLimitX.w  '' if there is no start element, but there is a repeat mark before the start of the line.
        Else
            If (Not Me.anchor2 Is Nothing) Then
                Me.startX = Me.anchor2.x - 20  '' There is no element and no repeat mark: make a small arc
            Else
                Me.startX = lineStartX  '' Don't have any guidance, so extend to beginning of line
            End If
        End If
        If (Me.anchor1 Is Nothing) And Me.dotted Then
            Me.startX = Me.startX - 3 '' The arc needs to be long enough to tell that it is dotted.
        End If
        

        If Not (Me.anchor2 Is Nothing) Then
            Me.endX = Me.anchor2.x  '' The normal case where there is a starting element to attach to.
        ElseIf Not (Me.endLimitX Is Nothing) Then
            Me.endX = Me.endLimitX.x  '' if there is no start element, but there is a repeat mark before the start of the line.
        Else
            Me.endX = lineEndX  '' There is no element and no repeat mark: extend to the beginning of the line.

End Sub

Public Sub calcTieY()
        '' If the tie comes from another line, then one or both anchors will be missing.
        If Not (Me.anchor1 Is Nothing) Then
            Me.startY = Me.anchor1.pitch
        ElseIf Not (Me.anchor2 Is Nothing) Then
            Me.startY = Me.anchor2.pitch
        Else
            Me.startY = IIf(Me.above, 14, 0)

        If Not (Me.anchor2 Is Nothing) Then
            Me.endY = Me.anchor2.pitch
        ElseIf Not (Me.anchor1 Is Nothing) Then
            Me.endY = Me.anchor1.pitch
        Else
            Me.endY = IIf(Me.above, 14, 0)
End Sub

    '' From "standard music notation practice" by Music Publishers’ Association:
    '' 1) If the anchor note is down stem, the slur points to the note head.
    '' 2) If the anchor note is up stem, and the slur is over, then point to middle of stem.

Public Sub calcSlurY()
        If Not (Me.anchor1 Is Nothing) And Not (Me.anchor2 Is Nothing) Then
            If (Me.above And Me.anchor1.stemdir = "up" And Not Me.fixedY) Then
                Me.startY = (Me.anchor1.highestVert + Me.anchor1.pitch) / 2
                Me.startX = Me.startX + Me.anchor1.w / 2 '' When going to the middle of the stem, bump the line to the right a little bit to make it look right.
             Else
                Me.startY = Me.anchor1.pitch
            End If
            Dim beamInterferes As Boolean
            '' If the closing note has an up stem, and it is beamed, and it isn't the first note in the beam, then the beam will get in the way.
            beamInterferes = Me.anchor2.parent.Beam And Me.anchor2.parent.Beam.stemsUp And (Me.anchor2.parent.Beam.elems(0) = Me.anchor2.parent)
            Dim Midpoint As Double
            Midpoint = (Me.anchor2.highestVert + Me.anchor2.pitch) / 2
            If (Me.above And Me.anchor2.stemdir = "up" And Not Me.fixedY And _
                Not beamInterferes And (Midpoint < Me.startY)) Then
                Me.endY = Midpoint
                Me.endX = Me.endX + Math.Round(Me.anchor2.w / 2) '' When going to the middle of the stem, bump the line to the right a little bit to make it look right.
             Else
                Me.endY = IIf(Me.above And beamInterferes, Me.anchor2.highestVert, Me.anchor2.pitch)
            End If

         ElseIf Not (Me.anchor1 Is Nothing) Then
            Me.startY = Me.endY = Me.anchor1.pitch
         ElseIf Not (Me.anchor2 Is Nothing) Then
            Me.startY = Me.endY = Me.anchor2.pitch
         Else
            '' This is the case where the slur covers the entire line.
            '' TODO-PER: figure out where the real top and bottom of the line are.
            Me.startY = IIf(Me.above, 14, 0)
            Me.endY = IIf(Me.above, 14, 0)
        End If
End Sub

Public Sub avoidCollisionAbove()
        Dim i As Integer, maxInnerHeight As Double
        '' Double check that an interior note in the slur isn't so high that it interferes.
        If (Me.above) Then
            maxInnerHeight = -50
            For i = 0 To Me.internalNotes.Count - 1
                If (Me.internalNotes(i).highestVert > maxInnerHeight) Then
                    maxInnerHeight = Me.internalNotes(i).highestVert
                End If
            Next
            If (maxInnerHeight > Me.startY And maxInnerHeight > Me.endY) Then
                Me.startY = Me.endY = maxInnerHeight - 1
            End If
        End If
End Sub
Public Function clone() As TieElem
    Dim cope As New TieElem
    
    cope.typs = Me.typs
    cope.isTie = Me.isTie
    cope.stemdir = Me.stemdir
    cope.dotted = Me.dotted
Set cope.anchor1 = Me.anchor1
Set cope.anchor2 = Me.anchor2
    cope.isGrace = Me.isGrace
    cope.fixedY = Me.fixedY
    cope.voicenumber = Me.voicenumber
Set cope.internalNotes = Me.internalNotes
    cope.top = Me.top
    cope.bottom = Me.bottom
Set cope.startLimitX = Me.startLimitX
Set cope.endLimitX = Me.endLimitX
    cope.above = Me.above
    cope.startX = Me.startX
    cope.endX = Me.endX
    cope.startY = Me.startY
    cope.endY = Me.endY
Set cope.elemset = Me.elemset
    cope.hint = Me.hint
    
    Set clone = cope
End Function

Attribute VB_Name = "TieElemList"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
'MIT License
'
'Copyright (c) 2019-2021 Petr Katerinak
'
'Permission is hereby granted, free of charge, to any person obtaining a copy
'of this software and associated documentation files (the "Software"), to deal
'in the Software without restriction, including without limitation the rights
'to use, copy, modify, merge, publish, distribute, sublicense, and/or sell
'copies of the Software, and to permit persons to whom the Software is
'furnished to do so, subject to the following conditions:
'
'The above copyright notice and this permission notice shall be included in all
'copies or substantial portions of the Software.
'
'THE SOFTWARE IS PROVIDED "AS IS", WITHOUT WARRANTY OF ANY KIND, EXPRESS OR
'IMPLIED, INCLUDING BUT NOT LIMITED TO THE WARRANTIES OF MERCHANTABILITY,
'FITNESS FOR A PARTICULAR PURPOSE AND NONINFRINGEMENT. IN NO EVENT SHALL THE
'AUTHORS OR COPYRIGHT HOLDERS BE LIABLE FOR ANY CLAIM, DAMAGES OR OTHER
'LIABILITY, WHETHER IN AN ACTION OF CONTRACT, TORT OR OTHERWISE, ARISING FROM,
'OUT OF OR IN CONNECTION WITH THE SOFTWARE OR THE USE OR OTHER DEALINGS IN THE
'SOFTWARE.
'
' Version of iArray: 1.0
''修正 元素從 0 開始

Private mainArray As New Collection
Private i As Long ' Counter

' #####################
' #    CONSTRUCTOR    #
' #####################
'Private Sub Class_Initialize()
'  Set mainArray = New Collection
'End Sub

' #####################
' #  Getter / Setter  #
' #####################
'Attribute Element.VB_UserMemId = 0 saved in both procedures

'@DefaultMember
Public Property Get element(ByVal index As Long) As TieElem
Attribute element.VB_UserMemId = 0
    If index + 1 < 1 Or index + 1 > mainArray.Count Then
        Set element = Nothing
        Exit Property
    End If
    If IsObject(mainArray(index + 1)) = True Then
        Set element = mainArray(index + 1)
    Else
        element = mainArray(index + 1)
    End If

 
End Property

'@DefaultMember
Public Property Let element(ByVal index As Long, ByVal val As TieElem)
Attribute element.VB_UserMemId = 0
  If index = 0 And mainArray.Count = 0 Then
    Me.Push val
    Exit Property
  End If
  If index + 1 > mainArray.Count Then
    Dim eMsg As String
    eMsg = IIf(mainArray.Count > 0, _
               "Index (" & index + 1 & ") out of iArray bounds (1-" & mainArray.Count & ")", _
               "iArray doesn't have any indexes")
    err.Raise Number:=9, Description:=eMsg
    Exit Property
  End If
  mainArray.Add val, after:=index + 1
  mainArray.Remove index + 1
End Property

' #############################
' # COMMON COLLECTION METHODS #
' #############################
Public Function Count() As Long
  Count = mainArray.Count
End Function
Public Sub Add(ByVal val As TieElem, Optional ByVal bef As Variant = Empty, Optional ByVal aft As Variant = Empty)
  If IsEmpty(bef) And IsEmpty(aft) Then
    mainArray.Add val
  ElseIf IsEmpty(bef) Then
    mainArray.Add val, , , aft
  ElseIf IsEmpty(aft) Then
    mainArray.Add val, , bef
  Else
    mainArray.Add val, , bef, aft
  End If
End Sub
Public Sub Remove(index As Long)
  mainArray.Remove index + 1
End Sub

' ####################
' #  PUBLIC METHODS  #
' ####################

'AddAfter
' Adds element after given index.
' {1,2,3} -> index >= 3 -> Push val
' {1,2,3} -> index < 1 -> Unshift val
' {} -> index = any -> Push val
' @param Long index | Index after which will be added an element
' @param Variant val | One element (String, number, ...) to add into iArray
' @return Long | Count of elements inside iArray
Public Function AddAfter(ByVal index As Long, ByVal val As TieElem) As Long
  If Me.Count < 1 Or index + 1 >= Me.Count Then
    Me.Push val
  ElseIf index + 1 < 1 Then
    Me.Unshift val
  Else
    Me.Add val, aft:=index + 1
  End If
  AddAfter = Me.Count
End Function

'AddArrayAfter
' Adds elements after given index.
' {1,2,3} -> index >= 3 -> PushArray val
' {1,2,3} -> index < 1 -> UnshiftArray val
' {} -> index = any -> PushArray val
' @param Long index | Index after which will be added an element
' @param Variant val | Array() or iArray of elements to add into iArray
' @return Long | Count of elements inside iArray
Public Function AddArrayAfter(ByVal index As Long, ByVal val As Variant) As Long
  If Me.Count < 1 Or index + 1 >= Me.Count Then
    Me.PushArray val
  ElseIf index + 1 < 1 Then
    Me.UnshiftArray val
  Else
    If TypeOf val Is TieElemList Then
      For i = 0 To val.Count - 1
        Me.Add val(i), aft:=index + 1
        Inc index
      Next i
    Else
      For i = LBound(val) To UBound(val)
        Me.Add val(i), aft:=index + 1
        Inc index
      Next i
    End If
  End If
  AddArrayAfter = Me.Count
End Function

'AddArrayBefore
' Adds elements before given index.
' {1,2,3} -> index > 3 -> PushArray val
' {1,2,3} -> index <= 1 -> UnshiftArray val
' {} -> index = any -> PushArray val
' @param Long index | Index after which will be added an element
' @param Variant val | Array() or iArray of elements to add into iArray
' @return Long | Count of elements inside iArray
Public Function AddArrayBefore(ByVal index As Long, ByVal val As Variant) As Long
  If Me.Count < 1 Or index + 1 > Me.Count Then
    Me.PushArray val
  ElseIf index <= 0 Then
    Me.UnshiftArray val
  Else
    If TypeOf val Is TieElemList Then
      For i = val.Count - 1 To 0 Step -1
        Me.Add val(i), bef:=index + 1
      Next i
    Else
      For i = UBound(val) To LBound(val) Step -1
        Me.Add val(i), bef:=index + 1
      Next i
    End If
  End If
  AddArrayBefore = Me.Count
End Function

'AddBefore
' Adds element before given index.
' {1,2,3} -> index > 3 -> Push val
' {1,2,3} -> index <= 1 -> Unshift val
' {} -> index = any -> Push val
' @param Long index | Index before which will be added an element
' @param Variant val | One element (String, number, ...) to add into iArray
' @return Long | Count of elements inside iArray
Public Function AddBefore(ByVal index As Long, ByVal val As TieElem) As Long
  If Me.Count < 1 Or index + 1 > Me.Count Then
    Me.Push val
  ElseIf index + 1 <= 1 Then
    Me.Unshift val
  Else
    Me.Add val, bef:=index + 1
  End If
  AddBefore = Me.Count
End Function

'Avg
' Calculates the average of the numeric mainArray.
' @return Variant | Average value / "NaN" if iArray contains non-numeric value(s)
Public Function Avg() As Variant
  If Not Me.ContainsOnlyNumeric Then Avg = "NaN": Exit Function
  Avg = Me.sum / Me.Count
End Function

'Clear
' Empties iArray
Public Function Clear() As Boolean
  For i = mainArray.Count - 1 To 0 Step -1
    mainArray.Remove i + 1
  Next i
  Clear = IIf(mainArray.Count = 0, True, False)
End Function

'Clone
' Makes a hard copy of the mainArray
' @return mainArray | Return exact copy of itself
Public Function clone() As TieElemList
  Set clone = New TieElemList
  For i = 0 To Me.Count - 1
    clone.Push Me(i)
  Next i
End Function

'Contains
' Checks if given value is used inside mainArray.
' @param Variant val | One element (String, number, ...) to by checked if it exists in iArray
' $return Boolean | True = exists, False = doesn't exists
Public Function Contains(ByVal val As TieElem) As Boolean
  Contains = False
  Dim el As Variant
  For Each el In mainArray
    If IsObject(val) = True Or VarType(val) And 8192 Then
        If (VarType(el) And 8192) And (VarType(val) And 8192) Then
            If ArrayDifference(el, val) Then
                Contains = True: Exit Function
            End If
        ElseIf IsObject(el) = True And IsObject(val) = True Then
            If el Is val Then
                Contains = True: Exit Function
            End If
        End If
    Else
        If IsObject(el) = False And (VarType(el) And 8192) <> 8192 Then
            If el = val Then
            Contains = True: Exit Function
            End If
        End If
    End If
  Next el
End Function

'ContainsAll
' Checks if all given values are used inside mainArray.
' @param Variant val | values to by checked if it exists in iArray
' $return Boolean | True = all exists, False = one ore more values doesn't exists
Public Function ContainsAll(ByVal val As TieElemList) As Boolean
  ContainsAll = False
  Dim foundOccurrences As Integer: foundOccurrences = 0
  Dim values As New TieElemList
  If Not TypeOf val Is TieElemList Then
    If IsArray(val) Then
      values.PushArray (val)
    Else
      values.Push (val)
    End If
  Else
    Set values = val
  End If
  For i = 0 To values.Count - 1
    If Me.Contains(values(i)) Then Inc foundOccurrences
  Next i
  If foundOccurrences = values.Count Then ContainsAll = True
End Function

'CountOccurrences
' Checks how many times is given value used inside mainArray.
' @param Variant val | One element (String, number, ...) to by checked
' @return Long | Count of matched occurrences
Public Function CountOccurrences(val As Variant) As Long
  CountOccurrences = 0
  Dim el As Variant
  For Each el In mainArray
  
    If IsObject(val) = True Or VarType(val) And 8192 Then
        If VarType(el) And 8192 And VarType(val) And 8192 Then
            If ArrayDifference(el, val) Then
                Inc CountOccurrences
                Exit Function
            End If
        ElseIf IsObject(el) = True And IsObject(val) = True Then
            If el Is val Then
                Inc CountOccurrences
                Exit Function
            End If
        End If
    Else
        If IsObject(el) = False And Not (VarType(el) And 8192) Then
            If el = val Then
                Inc CountOccurrences
                Exit Function
            End If
        End If
    End If
  
     'If el = val Then Inc CountOccurrences
  Next el
End Function

'Dequeue
' Removes an element from the begining of the mainArray.
' @return Variant | Removed element or Empty, if iArray is empty
'刪除開頭一個元素。
Public Function Dequeue() As TieElem
  Dequeue = Empty
  If mainArray.Count > 0 Then
    If VarType(Me(0)) = vbString Then
        Dequeue = Me(0)
    ElseIf TypeOf Me(0) Is TieElemList Then
        Set Dequeue = Me(0)
    ElseIf VarType(Me(0)) = vbArray Then
        Set Dequeue = Me(0)
    ElseIf VarType(Me(0)) = vbObject Then
        Set Dequeue = Me(0)
    Else
        Dequeue = Me(0)
    End If
    
    mainArray.Remove 1
  End If
End Function

'Difference
' Checks for number of differences between two arrays, what was added/deleted or combination.
' @param iArray oldArray | Old iArray to be compared with current iArray
' @param String retType | �dd= deleted from old iArray, �aa= added in current iArray, �cc= combination of both (default)
' @return iArray | iArray with differences found
Public Function Difference(ByRef oldArray As TieElemList, Optional ByVal retType As String = "c") As TieElemList
  Set Difference = New TieElemList
  Select Case LCase(retType)
    Case "d"
      For i = 0 To oldArray.Count - 1
        If Me.Contains(oldArray(i)) = False Then Difference.Push oldArray(i)
      Next i
    Case "a"
      For i = 0 To Count - 1
        If oldArray.Contains(Me(i)) = False Then Difference.Push Me(i)
      Next i
    Case "c"
      For i = 0 To oldArray.Count - 1
        If Me.Contains(oldArray(i)) = False Then Difference.Push oldArray(i)
      Next i
      For i = 0 To Count - 1
        If oldArray.Contains(Me(i)) = False Then Difference.Push Me(i)
      Next i
    Case Else
      err.Raise Number:=5, Description:="Unknown Difference return type attribute:" & vbCrLf & _
                                        "Allowed are 'A'dded/'D'eleted/'C'ombination of both"
  End Select
End Function

'DropLeft
' Remove n elements from the beginning of the mainArray. If n > count of iArray elements, all elements are removed.
' @param Long n | Number of elements to be removed
' @return iArray | Array of the removed elements
Public Function DropLeft(ByRef N As Long) As TieElemList
  Set DropLeft = New TieElemList
  If N > Me.Count Then N = Me.Count
  For i = 0 To N - 1
    DropLeft.Push Me(i)
  Next i
  For i = N - 1 To 0 Step -1
    Me.Remove (i)
  Next i
End Function

'DropRight
' Remove n elements from the end of the mainArray. If n > count of iArray elements, all elements are removed.
' @param Long n | Number of elements to be removed
' @return iArray | Array of the removed elements
Public Function DropRight(ByRef N As Long) As TieElemList
  Set DropRight = New TieElemList
  If N > Me.Count Then N = Me.Count
  For i = Me.Count - N To Me.Count - 1
    DropRight.Push Me(i)
  Next i
  For i = Me.Count - 1 To Me.Count - N Step -1
    Me.Remove (i)
  Next i
End Function

'Enqueue
' Adds an element at the end of the mainArray.
' @param Variant val | One element (String, number, ...) to add into iArray
' @return Long | Count of elements inside iArray
Public Function Enqueue(ByVal val As Variant) As Long
  Enqueue = Push(val)
End Function

'EnqueueArray
' Adds elements at the end of the iArray
' @param Variant val | Array() or iArray of elements to add into iArray
' @return Long | Count of elements inside array
Public Function EnqueueArray(ByVal val As Variant) As Long
  EnqueueArray = PushArray(val)
End Function

'First
' Returns value of the first element of the mainArray.
' @return Variant | Value of the first element or Empty if iArray is Empty
Public Function First() As TieElem
  Set First = IIf(Me.Count > 0, Me(0), Empty)
End Function

'Head
' Returns all elements of iArray, except last one.
' @return iArray | Copy of original array, without last element
Public Function head() As TieElemList
  Set head = Me.clone
  head.Pop
End Function

'Intersect
' Search for element that exists in both iArrays.
' @param iArray intArray | iArray to be intersected with current iArray
' @return iArray | Intersected values
Public Function Intersect(ByRef intersectedArr As TieElemList) As TieElemList
  Set Intersect = New TieElemList
  Dim el As Variant
  For Each el In mainArray
    If intersectedArr.Contains(el) Then
      If Not Intersect.Contains(el) Then Intersect.Push (el)
    End If
  Next el
End Function

'ContainsOnlyNumeric
' Verify that all elements are numbers or convertable to numbers
' $return Boolean | True = contains only numeric values, False = contains inconvertible values
Public Function ContainsOnlyNumeric() As Boolean
  ContainsOnlyNumeric = True
  Dim el As Variant
  For Each el In mainArray
    If Not IsNumeric(el) Then ContainsOnlyNumeric = False: Exit Function
  Next el
End Function

'Join
' Joins two iArrays.
' @param iArray jArray | iArray to be joined with current iArray
' @return iArray | Joined iArray
Public Function Join(ByRef joinArr As TieElemList) As TieElemList
  Set Join = New TieElemList
  Join.PushArray Me
  Join.PushArray joinArr
End Function

'Last
' Returns value of the last element of the mainArray.
' @return Variant | Value of the last element or Empty if iArray is Empty
Public Function Last() As TieElem
  Set Last = IIf(Me.Count > 0, Me(Me.Count - 1), Empty)
End Function

'OccurrenceIndexes
' Returns all indexes of a value in mainArray.
' @return iArray | iArray containing indexes of occurrence
Public Function OccurenceIndexes(val As Variant) As TieElemList
  Set OccurenceIndexes = New TieElemList
  For i = 0 To Me.Count - 1
    If Me(i) = val Then
        OccurenceIndexes.Push (i)
    End If
  Next i
End Function

'Pop
' Removes an element from the end of the mainArray.
' @return Variant | Removed element or Empty, if iArray is empty
Public Function Pop() As TieElem
  If mainArray.Count > 0 Then
    If VarType(Me(mainArray.Count - 1)) = vbObject Then
       Set Pop = Me(mainArray.Count - 1)
    Else
        Pop = Me(mainArray.Count - 1)
    End If
    mainArray.Remove mainArray.Count
  End If
End Function
  
  

'Push
' Adds an element at the end of the mainArray.
' @param Variant val | One element (String, number, ...) to add into iArray
' @return Long | Count of elements inside iArray
Public Function Push(ByVal val As TieElem) As Long
  mainArray.Add val
  Push = mainArray.Count
End Function

'PushArray
' Adds elements at the end of the mainArray.
' @param Variant val | Array() or iArray of elements to add into iArray
' @return Long | Count of elements inside array
Public Function PushArray(ByVal val As Variant) As Long
  If TypeOf val Is TieElemList Then
    For i = 0 To val.Count - 1
      Me.Push val(i)
    Next i
  Else
    For i = LBound(val) To UBound(val)
      Me.Push val(i)
    Next i
  End If
  PushArray = Me.Count
End Function

'RemoveDuplicates
' Keeps only the first occurrence of the value. Affects original array
' @return Long | Count of the removed elements
Public Function RemoveDuplicates() As Long
  RemoveDuplicates = 0
  For i = Me.Count - 1 To 0 Step -1
    If Me.CountOccurrences(Me(i)) > 1 Then
      Me.Remove i
      Inc RemoveDuplicates
    End If
  Next i
End Function

'Reverse
' Reverses the content of the iArray
' @return iArray | Reversed iArray
Public Function Reverse() As TieElemList
  Set Reverse = New TieElemList
  For i = 0 To Me.Count - 1
    Reverse.Unshift Me(i)
  Next i
End Function

'Shift
' Removes an element from the begining of the mainArray.
' @return Variant | Removed element or Empty, if iArray is empty
'轉移
' 從 iArray 的開頭刪除一個元素。
' @返回第一個元素 | 如果 iArray 為空，則刪除元素或為空
Public Function shift() As TieElem
  shift = Empty
  If mainArray.Count > 0 Then
    If VarType(Me(0)) = vbString Then
        shift = Me(0)
    ElseIf TypeOf Me(0) Is TieElemList Then
        Set shift = Me(0)
    ElseIf VarType(Me(0)) = vbArray Then
        Set shift = Me(0)
    ElseIf VarType(Me(0)) = vbObject Then
        Set shift = Me(0)
    Else
        shift = Me(0)
    End If
    
    mainArray.Remove 1
  End If
End Function

'Shuffle
' Randomly mixes content of the iArray
' @return iArray | Shuffled iArray
' 隨機播放
' 隨機混合 iArray 的內容
'@return iArray | 打亂iArray
Public Function Shuffle() As TieElemList
  Set Shuffle = New TieElemList
  Dim keys As New TieElemList
  For i = 0 To Me.Count - 1
    keys.Push (i)
  Next i
  Dim rndNo As Long
  Do While keys.Count > 0
    rndNo = randomFromTo(0, keys.Count - 1)
    Shuffle.Push Me(keys(rndNo))
    keys.Remove (rndNo)
  Loop
End Function

'Sum
' Calculates the sum of the numeric mainArray.
' @return Variant | Sum value / "NaN" if iArray contains non-numeric value(s)
Public Function sum() As Variant
  If Not Me.ContainsOnlyNumeric Then sum = "NaN": Exit Function
  sum = 0
  Dim el As Variant
  For Each el In mainArray
    sum = sum + el
  Next el
End Function

'Tail
' Returns all elements of iArray, except first one.
' @return iArray | Copy of original array, without first element
'返回陣列中除了第一個元素的剩余元素陣列
Public Function Tail() As TieElemList
  Set Tail = Me.clone
  Tail.Dequeue
End Function

Public Function ToList()
  If Me.Count = 0 Then ToList = Null: Exit Function
  Dim tarr()
  ReDim tarr(Me.Count - 1)
  For i = 0 To Me.Count - 1
    If VarType(Me(i)) = vbString Then
        tarr(i) = Me(i)
    ElseIf TypeOf Me(i) Is TieElemList Then
        Set tarr(i) = Me(i)
    ElseIf VarType(Me(i)) = vbObject Then
        Set tarr(i) = Me(i)
    Else
        tarr(i) = Me(i)
    End If
  Next i
  ToList = tarr
End Function

'ToString
' Creates string representation of the mainArray.
' @param String delimiter | Optional character to separate the iArray's elements (default = " ")
' @return String | Formated representation of tha iArray
Public Function ToString(Optional ByVal delimiter As String = " ") As String
  If Me.Count = 0 Then ToString = "{}": Exit Function
  ToString = vbNullString
  For i = 0 To Me.Count - 1
    If i = 0 Then ToString = ToString + "{"
    If i > 0 Then ToString = ToString + delimiter
    If VarType(Me(i)) = vbString Then
        ToString = ToString + Chr$(34)
        ToString = ToString + CStr(Me(i))
        ToString = ToString + Chr$(34)
    ElseIf TypeOf Me(i) Is TieElemList Then
        ToString = ToString + Me(i).ToString(delimiter)
    ElseIf (VarType(Me(i)) And vbArray) = vbArray Then
        ToString = ToString + "[Array]"
    ElseIf VarType(Me(i)) = vbObject Then
        ToString = ToString + "[Object]"
    Else
        ToString = ToString + CStr(Me(i))
    End If
    
    If i = mainArray.Count - 1 Then ToString = ToString + "}"
  Next i
End Function

'Union
' Combines both iArrays and removes duplicities
' @param iArray uArray | iArray to be unioned with current iArray
' @return iArray | Combined values without duplicities
Public Function Union(ByRef uArr As TieElemList) As TieElemList
  Set Union = Me.clone
  Union.PushArray uArr
  Union.RemoveDuplicates
End Function

'Unique
' Returns copy of iArray without duplicated values. Original array is not affected
' @return iArray | iArray with unique values
Public Function Unique() As TieElemList
  Set Unique = New TieElemList
  Dim el As Variant
  For Each el In mainArray
    If Not Unique.Contains(el) Then Unique.Push (el)
  Next el
End Function

'Unshift
' Add an element at the begining of the mainArray.
' @param Variant val | One element (String, number, ...) to add into iArray
' @return Long | Count of elements inside iArray
Public Function Unshift(ByVal val As Variant) As Long
  If mainArray.Count = 0 Then
    Unshift = Push(val)
  Else
    mainArray.Add val, before:=1
    Unshift = mainArray.Count
  End If
End Function

'UnshiftArray
' Add elements at the begining of the mainArray.
' @param Variant val | Array() or iArray of elements to add into iArray
' @return Long | Count of elements inside iArray
Public Function UnshiftArray(ByVal val As Variant) As Long
  If TypeOf val Is TieElemList Then
    For i = val.Count - 1 To 0 Step -1
      Unshift val(i)
    Next i
  Else
    For i = UBound(val) To LBound(val) Step -1
      Unshift val(i)
    Next i
  End If
  UnshiftArray = mainArray.Count
End Function


' #####################
' # PRIVATE FUNCTIONS #
' #####################
Sub Inc(ByRef i)
   i = i + 1
End Sub

'Private Function rangeToArray(ByVal rng As Range) As Variant
'  rangeToArray = rng.Value
'End Function

Private Function randomFromTo(ByVal from As Long, ByVal upTo As Long) As Long
  Randomize
  randomFromTo = Int(from + Rnd() * (upTo - from + 1))
End Function

'比對 兩個陣列是否一樣
Private Function ArrayDifference(arr1 As Variant, arr2 As Variant) As Boolean

    Dim i As Integer
    If UBound(arr1) = UBound(arr2) Then
        For i = 0 To UBound(arr1)
            If arr1(i) = arr2(i) Then
                ArrayDifference = True
            Else
                ArrayDifference = False
                Exit Function
            End If
        Next
    Else
        ArrayDifference = False
    End If

End Function

'@Description("changes the contents of the array by removing or replacing existing elements and/or adding new elements in place.")
Public Function Splice( _
        ByVal StartIndex As Long, _
        ParamArray Args() As Variant _
    ) As Variant()
    'Dim LocalItems() As Variant
    Dim ActualStart As Long
    Dim ActualDeleteCount As Long
    Dim ArgsCount As Long
    Dim LocalLength As Long
    Dim LocalArgs() As Variant
    Dim result() As Variant
    Dim i As Long
    Dim TempArray() As Variant
    Dim ItemCount As Long
    Dim TempItems() As Variant
    
    LocalArgs = Args
    'LocalItems = mainArray
    LocalLength = Me.Count
    If StartIndex < LocalLength Then
        ActualStart = StartIndex
    Else
        ActualStart = min(StartIndex, LocalLength)
    End If
    
    ArgsCount = UBound(LocalArgs) + 1
    If ArgsCount = 0 Then
        ' only a start index has been supplied
        ' we're gonna delete everything
        ' 僅提供了起始索引
         '我們要刪除所有內容
        ItemCount = 0
        ActualDeleteCount = LocalLength - ActualStart
    Else
        ' first arg in args is delete count, second onwards are insertion items
        ' args 中的第一個參數是刪除計數，第二個之後是插入項
        ItemCount = ArgsCount - 1
        'deleteCount is first element in args.
        'deleteCount 是 args 中的第一個元素。
        ActualDeleteCount = min(max(Args(LBound(Args)), 0), LocalLength - ActualStart)
    End If
    

    ' get items to be deleted for return val
    ' 取得和刪除
    If ActualDeleteCount > 0 Then
        ReDim result(0 To ActualDeleteCount - 1)
        i = 0
        Do While i < ActualDeleteCount
            If IsObject(Me(ActualStart)) Then
                Set result(i) = Me(ActualStart)
                Me.Remove ActualStart
            Else
                result(i) = Me(ActualStart)
                Me.Remove ActualStart
            End If
            Inc i
        Loop
    Else
        ' return empty array if nothing to be deleted
        ReDim result(0)
    End If
    
    '取得要插入的陣列資料
    If ItemCount > 0 Then
        ReDim TempItems(0 To ItemCount - 1)
        For i = 0 To ItemCount - 1
            If IsObject(LocalArgs(i + 1)) Then
                Set TempItems(i) = LocalArgs(i + 1)
            Else
                TempItems(i) = LocalArgs(i + 1)
            End If
        Next
    Me.AddArrayBefore ActualStart, TempItems
    End If
    
    
    Splice = result
End Function

Attribute VB_Name = "ToolsSet"
Option Explicit

Sub SetMusicTextToolsBar()
    ' This example uses MenuGroups to obtain a reference to the AutoCAD main menu.
    ' It then creates a new Toolbar (TestMenu) and inserts a ToolBarButton
    ' with a custom icon. The menu is automatically shown.
    '
    ' * NOTE: The paths of the icons for the new toolbar should be updated
    ' before running this example.
        
    Dim currMenuGroup As AcadMenuGroup
    Dim newToolBar As AcadToolbar, newToolBarButton As AcadToolbarItem
    Dim loadMusic As String
    Dim unloadMusic As String
    Dim loadMusicdvb As String
    Dim ShowMusic As String
    Dim ShowMusicEdit As String
    Dim ShowABCEdit As String
    Dim SetWindowSaveWmf As String
    Dim ToBWMFWmf As String
    Dim SmallBitmapName  As String, LargeBitmapName  As String
    
    On Error GoTo ERRORTRAP
    
    ' Use MenuGroups property to obtain reference to main AutoCAD menu
    Set currMenuGroup = ThisDrawing.Application.MenuGroups.item("ACAD")
    
    If IsFindArrayName("MenuToolsBar", currMenuGroup.Toolbars) > 0 Then
            Set newToolBar = currMenuGroup.Toolbars.item("MenuToolsBar")
    Else
        ' Create the new Toolbar in this group
        Set newToolBar = currMenuGroup.Toolbars.Add("MenuToolsBar")
    End If

    ShowMusicEdit = Chr(3) & Chr(3) & Chr(95) & "-vbarun frmMusicEdit" & vbCr
    Set newToolBarButton = newToolBar.AddToolbarButton(newToolBar.Count + 1, "開起 MusicEdit 介面", "開起 MusicEdit 介面", ShowMusicEdit, False)
    

    ShowABCEdit = Chr(3) & Chr(3) & Chr(95) & "-vbarun Baidu_appition" & vbCr
    Set newToolBarButton = newToolBar.AddToolbarButton(newToolBar.Count + 1, "ABC 介面 Chrome", "ABC 介面 Chrome", ShowABCEdit, False)
    
   
    ' Read icon paths for this Toolbar button
'    GoSub READPATHS
    
'    ' Change the default icon (smile face) for the new toolbar button
'    SmallBitmapName = "c:\images\16x16.bmp"     ' Use a 16x16 pixel .BMP image
'    LargeBitmapName = "c:\images\32x32.bmp"     ' Use a 32x32 pixel .BMP image
'    newToolBarButton.SetBitmaps SmallBitmapName, LargeBitmapName
'
    ' Read icon paths for this Toolbar button
'    GoSub READPATHS
    
    Exit Sub
    
READPATHS:
    ' Read icon paths for this Toolbar button
    newToolBarButton.GetBitmaps SmallBitmapName, LargeBitmapName
'    MsgBox "The new Toolbar uses the following icon files: " & _
'           vbCrLf & vbCrLf & "Small Bitmap: " & SmallBitmapName & vbCrLf & _
'           "Large Bitmap: " & LargeBitmapName
    Return

ERRORTRAP:
  '  MsgBox "The following error has occurred: " & Err.Description
End Sub

Public Function IsFindArrayName( _
  findName As String, _
  arr As Variant, _
  Optional nthOccurrence As Long = 1 _
  ) As Long

    IsFindArrayName = -1

    Dim i As Long
    For i = 1 To arr.Count - 1
        If arr(i).Name = findName Then
            If nthOccurrence > 1 Then
                nthOccurrence = nthOccurrence - 1
                GoTo continue
            End If
            IsFindArrayName = i
            Exit Function
        End If
continue:
    Next i

End Function


Sub Example_SetTools()
    ' This example uses MenuGroups to obtain a reference to the AutoCAD main menu.
    ' It then creates a new Toolbar (TestMenu) and inserts a ToolBarButton
    ' with a custom icon. The menu is automatically shown.
    '
    ' * NOTE: The paths of the icons for the new toolbar should be updated
    ' before running this example.
        
    Dim currMenuGroup As AcadMenuGroup
    Dim newToolBar As AcadToolbar, newToolBarButton As AcadToolbarItem
    Dim loadMusic As String
    Dim unloadMusic As String
    Dim loadMusicdvb As String
    Dim ShowMusic As String
    Dim ShowMusicEdit As String
    Dim SetWindowSaveWmf As String
    Dim ToBWMFWmf As String
    Dim SmallBitmapName  As String, LargeBitmapName  As String
    
    On Error GoTo ERRORTRAP
    
    ' Use MenuGroups property to obtain reference to main AutoCAD menu
    Set currMenuGroup = ThisDrawing.Application.MenuGroups.item("ACAD")
    
    ' Create the new Toolbar in this group
    Set newToolBar = currMenuGroup.Toolbars.Add("TestMenu")
    
    ' Add an item to the new Toolbar and assign an Open macro
    ' (VBA equivalent of: "ESC ESC _open ")
    loadMusic = Chr(3) & Chr(3) & Chr(95) & "_arx l " & """Z:/download/備份簡譜/Musical/debug/AsdkMusicalDb.dbx""" & Chr(32)

    Set newToolBarButton = newToolBar.AddToolbarButton(newToolBar.Count + 1, "載入 Musical.dbx", "載入 Musical.dbx", loadMusic, False)
   
    unloadMusic = Chr(3) & Chr(3) & Chr(95) & "_arx U asdkmusicaldb.dbx" & vbCr
    Set newToolBarButton = newToolBar.AddToolbarButton(newToolBar.Count + 1, "釋放 Musical.dbx", "釋放 Musical.dbx", unloadMusic, False)
    
    loadMusicdvb = Chr(3) & Chr(3) & Chr(95) & "-vbaload " & """Z:/download/備份簡譜/Musical/debug/MusicalAprintf.dvb""" & Chr(32)
    Set newToolBarButton = newToolBar.AddToolbarButton(newToolBar.Count + 1, "截入 MusicalAprintf.dvb", "截入 MusicalAprintf.dvb", loadMusicdvb, False)
    
    ShowMusic = Chr(3) & Chr(3) & Chr(95) & "-vbarun frmMusic" & vbCr
    Set newToolBarButton = newToolBar.AddToolbarButton(newToolBar.Count + 1, "開起 Music 介面", "開起 Music 介面", ShowMusic, False)
    
    ShowMusicEdit = Chr(3) & Chr(3) & Chr(95) & "-vbarun frmMusicEdit" & vbCr
    Set newToolBarButton = newToolBar.AddToolbarButton(newToolBar.Count + 1, "開起 MusicEdit 介面", "開起 MusicEdit 介面", ShowMusicEdit, False)
    
    SetWindowSaveWmf = Chr(3) & Chr(3) & Chr(95) & "-vbarun Ch4_MaximizeApplicationWindow" & vbCr
    Set newToolBarButton = newToolBar.AddToolbarButton(newToolBar.Count + 1, "將當前圖形縮放至兩點定義的窗口", "將當前圖形縮放至兩點定義的窗口", SetWindowSaveWmf, False)
   
    ToBWMFWmf = Chr(3) & Chr(3) & Chr(95) & "bwmfout" & vbCr
    Set newToolBarButton = newToolBar.AddToolbarButton(newToolBar.Count + 1, "BWMF 兩點定義的窗口", "BWMF 兩點定義的窗口", ToBWMFWmf, False)
   
   
   
    ' Read icon paths for this Toolbar button
'    GoSub READPATHS
    
'    ' Change the default icon (smile face) for the new toolbar button
'    SmallBitmapName = "c:\images\16x16.bmp"     ' Use a 16x16 pixel .BMP image
'    LargeBitmapName = "c:\images\32x32.bmp"     ' Use a 32x32 pixel .BMP image
'    newToolBarButton.SetBitmaps SmallBitmapName, LargeBitmapName
'
    ' Read icon paths for this Toolbar button
'    GoSub READPATHS
    
    Exit Sub
    
READPATHS:
    ' Read icon paths for this Toolbar button
    newToolBarButton.GetBitmaps SmallBitmapName, LargeBitmapName
'    MsgBox "The new Toolbar uses the following icon files: " & _
'           vbCrLf & vbCrLf & "Small Bitmap: " & SmallBitmapName & vbCrLf & _
'           "Large Bitmap: " & LargeBitmapName
    Return

ERRORTRAP:
'    MsgBox "The following error has occurred: " & Err.Description
End Sub

Sub Example_exTools()
'匯出工具列
    ' This example uses MenuGroups to obtain a reference to the AutoCAD main menu.
    ' It then creates a new Toolbar (TestMenu) and inserts a ToolBarButton
    ' with a custom icon. The menu is automatically shown.
    '
    ' * NOTE: The paths of the icons for the new toolbar should be updated
    ' before running this example.
        
    Dim currMenuGroup As AcadMenuGroup
    Dim newToolBar As AcadToolbar, newToolBarButton As AcadToolbarItem
    Dim loadMusic As String
    Dim unloadMusic As String
    Dim ShowMusic As String
    Dim ShowMusicEdit As String
    Dim SmallBitmapName  As String, LargeBitmapName  As String
    
    'On Error GoTo ERRORTRAP
    On Error Resume Next
    
    ' Use MenuGroups property to obtain reference to main AutoCAD menu
    Set currMenuGroup = ThisDrawing.Application.MenuGroups.item("ACAD")
    
    ' Create the new Toolbar in this group
    Set newToolBar = currMenuGroup.Toolbars.item("MusicText")
    
    ' Add an item to the new Toolbar and assign an Open macro
    ' (VBA equivalent of: "ESC ESC _open ")
    
    Dim help1 As String
    Dim code As String
    Dim i As Integer
    For i = 1 To newToolBar.Count - 1
        help1 = newToolBar.item(i).Name
        code = newToolBar.item(i).Macro
        ThisDrawing.Utility.Prompt "\n第" & i & "個," & help1 & "," & code
    Next
'
'    loadMusic = Chr(3) & Chr(3) & Chr(95) & "_arx l " & """E:/games/AutoCad_Arx/samples/entity/Musical/debug/AsdkMusicalDb.dbx""" & Chr(32)
'    Set newToolBarButton = newToolBar.AddToolbarButton(newToolBar.count + 1, "載入 Musical.dbx", "載入 Musical.dbx", loadMusic, False)
'
'    'unloadMusic = Chr(3) & Chr(3) & Chr(95) & "_arx U " & "AsdkMusicalDb.dbx "
'    unloadMusic = Chr(3) & Chr(3) & Chr(95) & "_arx U asdkmusicaldb.dbx" & vbCr
'    Set newToolBarButton = newToolBar.AddToolbarButton(newToolBar.count + 1, "釋放 Musical.dbx", "釋放 Musical.dbx", unloadMusic, False)
'
'    ShowMusic = Chr(3) & Chr(3) & Chr(95) & "-vbarun frmMusic" & vbCr
'    Set newToolBarButton = newToolBar.AddToolbarButton(newToolBar.count + 1, "開起 Music 介面", "開起 Music 介面", ShowMusic, False)
'
'    ShowMusicEdit = Chr(3) & Chr(3) & Chr(95) & "-vbarun frmMusicEdit" & vbCr
'    Set newToolBarButton = newToolBar.AddToolbarButton(newToolBar.count + 1, "開起 MusicEdit 介面", "開起 MusicEdit 介面", ShowMusicEdit, False)
'
    ' Read icon paths for this Toolbar button
'    GoSub READPATHS
    
'    ' Change the default icon (smile face) for the new toolbar button
'    SmallBitmapName = "c:\images\16x16.bmp"     ' Use a 16x16 pixel .BMP image
'    LargeBitmapName = "c:\images\32x32.bmp"     ' Use a 32x32 pixel .BMP image
'    newToolBarButton.SetBitmaps SmallBitmapName, LargeBitmapName
'
    ' Read icon paths for this Toolbar button
'    GoSub READPATHS
    
    Exit Sub
    
READPATHS:
    ' Read icon paths for this Toolbar button
    newToolBarButton.GetBitmaps SmallBitmapName, LargeBitmapName
'    MsgBox "The new Toolbar uses the following icon files: " & _
'           vbCrLf & vbCrLf & "Small Bitmap: " & SmallBitmapName & vbCrLf & _
'           "Large Bitmap: " & LargeBitmapName
    Return

ERRORTRAP:
    'MsgBox "The following error has occurred: " & Err.Description
End Sub


Sub Example_SetMusicTextTools()
    ' This example uses MenuGroups to obtain a reference to the AutoCAD main menu.
    ' It then creates a new Toolbar (TestMenu) and inserts a ToolBarButton
    ' with a custom icon. The menu is automatically shown.
    '
    ' * NOTE: The paths of the icons for the new toolbar should be updated
    ' before running this example.
        
    Dim currMenuGroup As AcadMenuGroup
    Dim newToolBar As AcadToolbar, newToolBarButton As AcadToolbarItem
    Dim loadMusic As String
    Dim unloadMusic As String
    Dim ShowMusic As String
    Dim ShowMusicEdit As String
    Dim SmallBitmapName  As String, LargeBitmapName  As String
    
    On Error GoTo ERRORTRAP
    
    ' Use MenuGroups property to obtain reference to main AutoCAD menu
    Set currMenuGroup = ThisDrawing.Application.MenuGroups.item("ACAD")
    
    ' Create the new Toolbar in this group
    Set newToolBar = currMenuGroup.Toolbars.Add("MusicText")
    Dim i As Integer
    Dim Marco(10, 2) As String
    Dim vbaPATH As String
    Dim imagePATH As String
    Dim pos As Integer
Marco(0, 0) = "Unload 釋放AsdkMusicText"
Marco(1, 0) = "Load 載入AsdkMusicText"
Marco(2, 0) = "開起 Edit 介面"
Marco(3, 0) = "加入符號"
Marco(4, 0) = "開起 PageMusic 頁面"
Marco(5, 0) = "連結拍子"
Marco(6, 0) = "移除連結"
Marco(7, 0) = "IsSet"
Marco(8, 0) = "SelectDraw"

Marco(0, 1) = Chr(3) & Chr(3) & Chr(95) & "_arx u AsdkMusicText.arx" & vbCr
Marco(1, 1) = Chr(3) & Chr(3) & Chr(95) & "_arx l " & """AsdkMusicText.arx""" & Chr(32)
Marco(2, 1) = Chr(3) & Chr(3) & Chr(95) & "_musicsample "
Marco(3, 1) = Chr(3) & Chr(3) & Chr(95) & "_addmusictext "
Marco(4, 1) = Chr(3) & Chr(3) & Chr(95) & "_addMusicTextPage "
Marco(5, 1) = Chr(3) & Chr(3) & Chr(95) & "_addMusicJoinMany "
Marco(6, 1) = Chr(3) & Chr(3) & Chr(95) & "_addMusicEraseMany "
Marco(7, 1) = Chr(3) & Chr(3) & Chr(95) & "_IsSet "
Marco(8, 1) = Chr(3) & Chr(3) & Chr(95) & "_-vbarun ThisDrawing.Example_SelectOnScreen "

    vbaPATH = ThisDrawing.Application.vbe.ActiveVBProject.fileName
    pos = InStrRev(vbaPATH, "\")
    imagePATH = Mid(vbaPATH, 1, pos) & "image\"
Marco(0, 2) = imagePATH & "UnLoad.BMP"
Marco(1, 2) = imagePATH & "Load.BMP"
Marco(2, 2) = imagePATH & "SEdit.BMP"
Marco(3, 2) = imagePATH & "AddMusicText.BMP"
Marco(4, 2) = imagePATH & "PageMusic.BMP"
Marco(5, 2) = imagePATH & "JoinMany.BMP"
Marco(6, 2) = imagePATH & "EraseMany.BMP"
Marco(7, 2) = imagePATH & "IsSet.BMP"
Marco(8, 2) = imagePATH & "IsSet.BMP"
    
    For i = 0 To 8
        Set newToolBarButton = newToolBar.AddToolbarButton(newToolBar.Count + 1, Marco(i, 0), Marco(i, 0), Marco(i, 1), False)
        
        newToolBarButton.SetBitmaps Marco(i, 2), Marco(i, 2)
    Next
    ' Add an item to the new Toolbar and assign an Open macro
    ' (VBA equivalent of: "ESC ESC _open ")
    'loadMusic = Chr(3) & Chr(3) & Chr(95) & "_arx l " & """E:/games/AutoCad_Arx/samples/entity/Musical/debug/AsdkMusicalDb.dbx""" & Chr(32)
    'Set newToolBarButton = newToolBar.AddToolbarButton(newToolBar.count + 1, "載入 Musical.dbx", "載入 Musical.dbx", loadMusic, False)
    
'    ' Change the default icon (smile face) for the new toolbar button
    'SmallBitmapName = "c:\images\16x16.bmp"     ' Use a 16x16 pixel .BMP image
    'LargeBitmapName = "c:\images\32x32.bmp"     ' Use a 32x32 pixel .BMP image
    'newToolBarButton.SetBitmaps SmallBitmapName, LargeBitmapName
'
    ' Read icon paths for this Toolbar button
'    GoSub READPATHS
    
    Exit Sub
    
READPATHS:
    ' Read icon paths for this Toolbar button
    newToolBarButton.GetBitmaps SmallBitmapName, LargeBitmapName
'    MsgBox "The new Toolbar uses the following icon files: " & _
'           vbCrLf & vbCrLf & "Small Bitmap: " & SmallBitmapName & vbCrLf & _
'           "Large Bitmap: " & LargeBitmapName
    Return

ERRORTRAP:
    'MsgBox "The following error has occurred: " & Err.Description
End Sub

Attribute VB_Name = "TripletElem"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public typs As String     '"TripletElem"
Public anchor1 As RelativeElement
Public anchor2 As RelativeElement
Public Number As Integer
Public durationClass As String
Public middleElems As RelativeElementList
Public flatBeams As Boolean
Public endingHeightAbove As Double
Public Sub init(Number As Double, anchor1 As RelativeElement, options As Dictionary)
        Me.typs = "TripletElem"
        Set Me.anchor1 = anchor1  '' must have a .x and a .parent property or be null (means starts at the "beginning" of the line - after key signature)
        Me.Number = Number
        Me.durationClass = ("d" + (Math.Round(anchor1.parent.durationClass * 1000) / 1000))
        Me.durationClass = Replace(Me.durationClass, ".", "-")
        Set Me.middleElems = New RelativeElementList  '' This is to calculate the highest interior pitch. It is used to make sure that the drawn bracket never crosses a really high middle note.
        Me.flatBeams = options("flatBeams")
End Sub

Public Function isClosed() As Boolean
        isClosed = IIf(Not (Me.anchor2 Is Nothing), True, False)
End Function

Public Sub middleNote(elem As RelativeElement)
        Me.middleElems.Push elem
End Sub

Public Sub setCloseAnchor(anchor2 As RelativeElement)
        Set Me.anchor2 = anchor2
        '' TODO-PER: This used to be just for beamed triplets but it looks like bracketed triplets need extra room, too. The only one that doesn't is stem down and beamed
        ''if (me.anchor1.parent.beam)
        If (Not Me.anchor1.parent.Beam Or Me.anchor1.stemdir = "up") Then
            Me.endingHeightAbove = 4
        End If
End Sub

Public Function clone() As TripletElem
    Dim cope As New TripletElem
    
    cope.typs = Me.typs
Set cope.anchor1 = Me.anchor1
Set cope.anchor2 = Me.anchor2
    cope.Number = Me.Number
    cope.durationClass = Me.durationClass
Set cope.middleElems = Me.middleElems
    cope.flatBeams = Me.flatBeams
    cope.endingHeightAbove = Me.endingHeightAbove

End Function

Attribute VB_Name = "TuneData"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public formatting As vFormatting
Public engraver As EngraverController
Public lines As TuneLineList
Public media As String 'Dictionary media
Public metaText As vMetaText
Public metaTextInfo As vMetaTextInfo
Public version As String
'    lineBreaksas  Array<number>
'    visualTransposeas Number
    
Public staffNum As Double
Public voiceNum As Double
Public lineNum As Double
Public runningFonts As vFormatting   'vFont
Public lineBreaks As iArray     ' Array<double>
Public visualTranspose As Double
Public TopText As Dictionary 'TopText
Public BottomText As Dictionary 'BottomText
Public totalTime
Public totalBeats
Public meter As vMeterFraction
Public tempoLocations
Public noteTimings As iArray
    
    
Private Sub Class_Initialize()
    Me.reset
End Sub

    
Public Sub reset()


        Me.version = "1.1.0"
        Me.media = "screen"
        Set Me.metaText = New vMetaText
        Set Me.metaTextInfo = New vMetaTextInfo
        Set Me.formatting = New vFormatting
        Set Me.lines = New TuneLineList
        Me.staffNum = 0
        Me.voiceNum = 0
        Me.lineNum = 0
        Set Me.runningFonts = New vFormatting
        'delete Me.visualTranspose
End Sub

'    copy(dest, src, prop, attrs) {
'        for (var i = 0  i < attrs.length  i++)
'            dest[prop][attrs[i]] = src[prop][attrs[i]]
'    }
'
'    copyTopInfo(src) {
'        var attrs = ['tempo', 'title', 'header', 'rhythm', 'origin', 'composer', 'author', 'partOrder']
'        me.copy(this, src, "metaText", attrs)
'        me.copy(this, src, "metaTextInfo", attrs)
'    }
'
'    copyBottomInfo(src) {
'        var attrs = ['unalignedWords',
'            'book',
'            'source',
'            'discography',
'            'notes',
'            'transcription',
'            'history',
'            'abc-copyright',
'            'abc-creator',
'            'abc-edited-by',
'            'footer']
'        me.copy(this, src, "metaText", attrs)
'        me.copy(this, src, "metaTextInfo", attrs)
'    }

    '' The structure consists of a hash with the following two items:
    '' metaText: a hash of {key, value}, where key is one of: title, author, rhythm, source, transcription, unalignedWords, etc...
    '' tempo: { noteLength: number (e.g. .125), bpm: number }
    '' lines: an array of elements, or one of the following:
    ''
    '' STAFF: array of elements
    '' SUBTITLE: string
    ''
    '' TODO: actually, the start and end char should modify each part of the note type
    '' The elements all have a type field and a start and end char
    '' field. The rest of the fields depend on the type and are listed below:
    '' REST: duration=1,2,4,8  chord: string
    '' NOTE: accidental=none,dbl_flat,flat,natural,sharp,dbl_sharp
    ''      pitch: "C" is 0. The numbers refer to the pitch letter.
    ''      duration: .5 (sixteenth), .75 (dotted sixteenth), 1 (eighth), 1.5 (dotted eighth)
    ''          2 (quarter), 3 (dotted quarter), 4 (half), 6 (dotted half) 8 (whole)
    ''      chord: { name:chord, position: one of 'default', 'above', 'below' }
    ''      end_beam = true or undefined if this is the last note in a beam.
    ''      lyric: array of { syllable: xxx, divider: one of " -_" }
    ''      startTie = true|undefined
    ''      endTie = true|undefined
    ''      startTriplet = num <- that is the number to print
    ''      endTriplet = true|undefined (the last note of the triplet)
    '' TODO: actually, decoration should be an array.
    ''      decoration: upbow, downbow, accent
    '' BAR: type=bar_thin, bar_thin_thick, bar_thin_thin, bar_thick_thin, bar_right_repeat, bar_left_repeat, bar_double_repeat
    ''  number: 1 or 2: if it is the start of a first or second ending
    '' CLEF: type=treble,bass
    '' KEY-SIG:
    ''      accidentals[]: { acc:sharp|dblsharp|natural|flat|dblflat,  note:a|b|c|d|e|f|g }
    '' METER: type: common_time,cut_time,specified
    ''      if specified, { num: 99, den: 99 }

Public Function getBeatLength() As Double
        '' This returns a fraction: for instance 1/4 for a quarter
        '' There are two types of meters: compound and regular. Compound meter has 3 beats counted as one.
        Dim meter As vMeterFraction
        Dim multiplier As Integer
        Set meter = Me.getMeterFraction()
        multiplier = 1
        If (meter.num = 6 Or meter.num = 9 Or meter.num = 12) Then
            multiplier = 3
        ElseIf (meter.num = 3 And meter.den = 8) Then
            multiplier = 3
        End If

        getBeatLength = multiplier / meter.den
End Function

'    computePickupLength(lines, barLength): number {
'        var pickupLength = 0
'        for (var i = 0  i < lines.length  i++) {
'            if (lines[i].staff) {
'                for (var j = 0  j < lines[i].staff.length  j++) {
'                    for (var v = 0  v < lines[i].staff[j].voices.length  v++) {
'                        var voice = lines[i].staff[j].voices[v]
'                        var tripletMultiplier = 1
'                        for (var el = 0  el < voice.length  el++) {
'                            var isSpacer = voice[el].rest && voice[el].rest.type === "spacer"
'                            if (voice[el].startTriplet)
'                                tripletMultiplier = voice[el].tripletMultiplier
'                            if (voice[el].duration && !isSpacer && voice[el].el_type !== "tempo")
'                                pickupLength += voice[el].duration * tripletMultiplier
'                            if (voice[el].endTriplet)
'                                tripletMultiplier = 1
'                            if (pickupLength >= barLength)
'                                pickupLength -= barLength
'                            if (voice[el].el_type === 'bar')
'                                return pickupLength
'                        }
'                    }
'                }
'            }
'        }
'
'        return pickupLength
'    }
'    getPickupLength(): number {
'        var barLength = Me.getBarLength()
'        var pickupLength = Me.computePickupLength(Me.lines, barLength)
'
'        '' If computed pickup length is very close to 0 or the bar length, we assume
'        '' that we actually have a full bar and hence no pickup.
'        return (pickupLength < 1e-8 || barLength - pickupLength < 1e-8) ? 0 : pickupLength
'    }

Public Function getBarLength() As Double
        Dim meter As vMeterFraction
        Set meter = Me.getMeterFraction()
        getBarLength = meter.num / meter.den
End Function

Public Function getTotalTime() As Double
       getTotalTime = Me.totalTime
End Function

Public Function getTotalBeats() As Double
        getTotalBeats = Me.totalBeats
End Function

Public Function millisecondsPerMeasure(bpmOverride As Integer) As Double
        Dim bpm As Integer
        Dim tempo As vtempoProperties
        If (bpmOverride <> 0) Then
            bpm = bpmOverride
        Else
            Set tempo = IIf(Me.metaText Is Nothing, Nothing, Me.metaText.tempo)
            bpm = Me.getBpm(tempo)
        End If
        If (bpm <= 0) Then
            bpm = 1  '' I don't think this can happen, but we don't want a possibility of dividing by zero.
        End If

        Dim beatsPerMeasure
        Dim minutesPerMeasure
         beatsPerMeasure = Me.getBeatsPerMeasure()

         minutesPerMeasure = beatsPerMeasure / bpm
        millisecondsPerMeasure = minutesPerMeasure * 60000
End Function

Public Function getBeatsPerMeasure() As Double
        Dim beatLen, barLen
        beatLen = Me.getBeatLength()
        barLen = Me.getBarLength()
        getBeatsPerMeasure = barLen / beatLen
End Function

Public Function getMeter() As vMeter
        Dim i As Integer, j As Integer
        Dim line As TuneLine
        Dim meter As vMeter
        For i = 0 To Me.lines.Count - 1
            Set line = Me.lines(i)
            If Not (line.Staffs Is Nothing) Then
                For j = 0 To line.Staffs.Count - 1
                    Set meter = line.Staffs(j).meter
                    If Not (meter Is Nothing) Then
                        Set getMeter = meter
                        Exit Function
                    End If
                Next
            End If
        Next
        Set meter = New vMeter
        meter.typs = "common_time"
        Set getMeter = meter
End Function

Public Function getMeterFraction() As vMeterFraction
        Dim meter As vMeter
        Dim num As Integer, den As Integer
        Set meter = Me.getMeter()
        num = 4
        den = 4
        If Not (meter Is Nothing) Then
            If (meter.typs = "specified") Then
                num = CInt(meter.value(0).num)
                den = CInt(meter.value(0).den)
            ElseIf (meter.typs = "cut_time") Then
                num = 2
                den = 2
            ElseIf (meter.typs = "common_time") Then
                num = 4
                den = 4
            End If
        End If
        Set Me.meter = New vMeterFraction
        Me.meter.num = num
        Me.meter.den = den
        Set getMeterFraction = Me.meter  '' TODO-PER: is this saved value used anywhere? A get function shouldn't change state.
End Function

Public Function getKeySignature() As vKeySignature


        Dim i As Integer, j As Integer
        Dim line As TuneLine
        For i = 0 To Me.lines.Count - 1
            Set line = Me.lines(i)
            If Not (line.Staff Is Nothing) Then
                For j = 0 To line.Staff.Count - 1
                    If Not (line.Staff(j).key Is Nothing) Then
                        Set getKeySignature = line.Staff(j).key
                    End If
                Next
            End If
        Next
        Set getKeySignature = Nothing
End Function

'    getElementFromChar(charPos: number): VoiceItem {
'        for (var i = 0  i < me.lines.length  i++) {
'            var line = me.lines[i]
'            if (line.staff) {
'                for (var j = 0  j < line.staff.length  j++) {
'                    var staff = line.staff[j]
'                    for (var k = 0  k < staff.voices.length  k++) {
'                        var voice = staff.voices[k]
'                        for (var ii = 0  ii < voice.length  ii++) {
'                            var elem = voice[ii]
'                            if (elem.startChar && elem.endChar &&
'                                elem.startChar <= charPos && elem.endChar > charPos)
'                                return elem
'                        }
'                    }
'                }
'            }
'        }
'        return null
'    }
'
'    addVerticalInfo(timingEvents) {
'        '' Add vertical info to the bar events: put the next event's top, and the event after the next measure's top.
'        var lastBarTop
'        var lastBarBottom
'        var lastEventTop
'        var lastEventBottom
'        for (var e = timingEvents.length - 1  e >= 0  e--) {
'            var ev = timingEvents[e]
'            if (ev.type === 'bar') {
'                ev.top = lastEventTop
'                ev.nextTop = lastBarTop
'                lastBarTop = lastEventTop
'
'                ev.bottom = lastEventBottom
'                ev.nextBottom = lastBarBottom
'                lastBarBottom = lastEventBottom
'            } else if (ev.type === 'event') {
'                lastEventTop = ev.top
'                lastEventBottom = ev.top + ev.height
'            }
'        }
'    }
'
'    makeSortedArray(hash) {
'        var arr = []
'        for (var k in hash) {
'            if (hash.hasOwnProperty(k))
'                arr.push(hash[k])
'        }
'        arr = arr.sort(function (a, b) {
'            var Diff = a.milliseconds - b.milliseconds
'            '' if the events have the same time, make sure a bar comes before a note
'            if (diff !== 0) {
'                return diff
'            }
'            else {
'                return a.type === "bar" ? -1 : 1
'            }
'        })
'        return arr
'    }
'
'    addElementToEvents(eventHash, element, voiceTimeMilliseconds, top, height, line, measureNumber, timeDivider, isTiedState, nextIsBar) {
'        if (element.hint)
'            return { isTiedState: undefined, duration: 0 }
'        var realDuration = element.durationClass ? element.durationClass : element.duration
'        if (element.abcelem.rest && element.abcelem.rest.type === "spacer")
'            realDuration = 0
'        if (realDuration > 0) {
'            var es = []
'            '' If there is an invisible rest, then there are not elements, so don't push a null one.
'            for (var i = 0  i < element.elemset.length  i++) {
'                if (element.elemset[i] !== null)
'                    es.push(element.elemset[i])
'            }
'            var isTiedToNext = Element.startTie
'            if (isTiedState !== undefined) {
'                eventHash ["event" + isTiedState].elements.Push(es) '' Add the tied note to the first note that it is tied to
'                if (nextIsBar) {
'                    if (!eventHash["event" + voiceTimeMilliseconds]) {
'                        eventHash["event" + voiceTimeMilliseconds] = {
'                            type: "event",
'                            milliseconds: voiceTimeMilliseconds,
'                            line: line,
'                            measureNumber: measureNumber,
'                            top: top,
'                            height: height,
'                            left: null,
'                            width: 0,
'                            elements: [],
'                            startChar: null,
'                            endChar: null,
'                            startCharArray: [],
'                            endCharArray:[],
'                        }
'                    }
'                    eventHash ["event" + voiceTimeMilliseconds].measureStart = True
'                    nextIsBar = False
'                }
'                if (!isTiedToNext)
'                    isTiedState = undefined
'            } else {
'                '' the last note wasn't tied.
'                if (!eventHash["event" + voiceTimeMilliseconds]) {
'                    eventHash["event" + voiceTimeMilliseconds] = {
'                        type: "event",
'                        milliseconds: voiceTimeMilliseconds,
'                        line: line,
'                        measureNumber: measureNumber,
'                        top: top,
'                        height: height,
'                        left: element.x,
'                        width: element.w,
'                        elements: [es],
'                        startChar: element.abcelem.startChar,
'                        endChar: element.abcelem.endChar,
'                        startCharArray: [element.abcelem.startChar],
'                        endCharArray: [element.abcelem.endChar],
'                        midiPitches: element.abcelem.midiPitches ? parseCommon.cloneArray(element.abcelem.midiPitches) : []
'                    }
'                    if (element.abcelem.midiGraceNotePitches)
'                        eventHash ["event" + voiceTimeMilliseconds].midiGraceNotePitches = parseCommon.cloneArray(Element.abcelem.midiGraceNotePitches)
'                } else {
'                    '' If there is more than one voice then two notes can fall at the same time. Usually they would be lined up in the same place, but if it is a whole rest, then it is placed funny. In any case, the left most element wins.
'                    if (eventHash["event" + voiceTimeMilliseconds].left)
'                        eventHash["event" + voiceTimeMilliseconds].left = Math.min(eventHash["event" + voiceTimeMilliseconds].left, element.x)
'                    Else
'                        eventHash ["event" + voiceTimeMilliseconds].left = Element.x
'                    eventHash ["event" + voiceTimeMilliseconds].elements.Push(es)
'                    eventHash ["event" + voiceTimeMilliseconds].startCharArray.Push(Element.abcelem.startChar)
'                    eventHash ["event" + voiceTimeMilliseconds].endCharArray.Push(Element.abcelem.endChar)
'                    if (eventHash["event" + voiceTimeMilliseconds].startChar === null)
'                        eventHash ["event" + voiceTimeMilliseconds].startChar = Element.abcelem.startChar
'                    if (eventHash["event" + voiceTimeMilliseconds].endChar === null)
'                        eventHash ["event" + voiceTimeMilliseconds].endChar = Element.abcelem.endChar
'                    if (element.abcelem.midiPitches && element.abcelem.midiPitches.length) {
'                        if (!eventHash["event" + voiceTimeMilliseconds].midiPitches)
'                            eventHash ["event" + voiceTimeMilliseconds].midiPitches = []
'                        for (var i = 0  i < element.abcelem.midiPitches.length  i++)
'                            eventHash["event" + voiceTimeMilliseconds].midiPitches.push(element.abcelem.midiPitches[i])
'                    }
'                    if (element.abcelem.midiGraceNotePitches && element.abcelem.midiGraceNotePitches.length) {
'                        if (!eventHash["event" + voiceTimeMilliseconds].midiGraceNotePitches)
'                            eventHash ["event" + voiceTimeMilliseconds].midiGraceNotePitches = []
'                        for (var j = 0  j < element.abcelem.midiGraceNotePitches.length  j++)
'                            eventHash["event" + voiceTimeMilliseconds].midiGraceNotePitches.push(element.abcelem.midiGraceNotePitches[j])
'                    }
'                }
'                if (nextIsBar) {
'                    eventHash ["event" + voiceTimeMilliseconds].measureStart = True
'                    nextIsBar = False
'                }
'                if (isTiedToNext)
'                    isTiedState = voiceTimeMilliseconds
'            }
'        }
'        return { isTiedState: isTiedState, duration: realDuration / timeDivider, nextIsBar: nextIsBar || element.type === 'bar' }
'    }
'
'    makeVoicesArray(): Array<Selectable[]> {
'        '' First make a new array that is arranged by voice so that the repeats that span different lines are handled correctly.
'        var voicesArr = []
'        var measureNumber = []
'        var tempos = {}
'        for (var line = 0  line < me.engraver.staffgroups.length  line++) {
'            var group = me.engraver.staffgroups[line]
'            if (group && group.staffs && group.staffs.length > 0) {
'                var firstStaff = group.staffs[0]
'                var middleC = firstStaff.absoluteY
'                var top = middleC - firstStaff.top * spacing.STEP
'                var lastStaff = group.staffs[group.staffs.length - 1]
'                middleC = lastStaff.absoluteY
'                var bottom = middleC - lastStaff.bottom * spacing.STEP
'                var height = bottom - top
'
'                var voices = group.voices
'                for (var v = 0  v < voices.length  v++) {
'                    if (voices[v].staff && voices[v].staff.isTabStaff)
'                        continue
'                    var noteFound = False
'                    if (!voicesArr[v])
'                        voicesArr [v] = []
'                    if (measureNumber[v] === undefined)
'                        measureNumber [v] = 0
'                    var elements = voices[v].children
'                    for (var elem = 0  elem < elements.length  elem++) {
'                        if (elements[elem].type === "tempo")
'                            tempos[measureNumber[v]] = me.getBpm(elements[elem].abcelem)
'                        voicesArr[v].push({ top: top, height: height, line: group.line, measureNumber: measureNumber[v], elem: elements[elem] })
'                        if (elements[elem].type === 'bar' && noteFound) '' Count the measures by counting the bar lines, but skip a bar line that appears at the left of the music, before any notes.
'                            measureNumber[v]++
'                        if (elements[elem].type === 'note' || elements[elem].type === 'rest')
'                            noteFound = True
'                    }
'                }
'            }
'        }
'        Me.tempoLocations = tempos  '' This should be passed back, but the function is accessible publicly so that would break the interface.
'        return voicesArr
'    }
'
'    setupEvents(startingDelay, timeDivider, startingBpm, warp) {
'        if (!warp) warp = 1
'        var timingEvents = []
'
'        var eventHash = {}
'        '' The time is the number of seconds from the beginning of the piece.
'        '' The units we are scanning are in notation units (i.e. 0.25 is a quarter note)
'        var time = startingDelay
'        var isTiedState
'        var nextIsBar = True
'        var voices = Me.makeVoicesArray()
'        var maxVoiceTimeMilliseconds = 0
'        for (var v = 0  v < voices.length  v++) {
'            var voiceTime = time
'            var voiceTimeMilliseconds = Math.Round(voiceTime * 1000)
'            var startingRepeatElem = 0
'            var endingRepeatElem = -1
'            var elements = voices[v]
'            var bpm = startingBpm
'            timeDivider = Me.getBeatLength() * bpm / 60
'            var tempoDone = -1
'            for (var elem = 0  elem < elements.length  elem++) {
'                var thisMeasure = elements[elem].measureNumber
'                if (tempoDone !== thisMeasure && me.tempoLocations[thisMeasure]) {
'                    bpm = me.tempoLocations[thisMeasure]
'                    timeDivider = warp * Me.getBeatLength() * bpm / 60
'                    tempoDone = thisMeasure
'                }
'                var element = elements[elem].elem
'                var ret = me.addElementToEvents(eventHash, element, voiceTimeMilliseconds, elements[elem].top, elements[elem].height, elements[elem].line, elements[elem].measureNumber, timeDivider, isTiedState, nextIsBar)
'                isTiedState = ret.isTiedState
'                nextIsBar = ret.nextIsBar
'                voiceTime += ret.duration
'                var lastHash
'                if (element.duration > 0 && eventHash["event" + voiceTimeMilliseconds]) '' This won't exist if this is the end of a tie.
'                    lastHash = "event" + voiceTimeMilliseconds
'                voiceTimeMilliseconds = Math.Round(voiceTime * 1000)
'                if (element.type === 'bar') {
'                    var barType = Element.abcelem.Type
'                    var endRepeat = (barType === "bar_right_repeat" || barType === "bar_dbl_repeat")
'                    var startEnding = (element.abcelem.startEnding === '1')
'                    var startRepeat = (barType === "bar_left_repeat" || barType === "bar_dbl_repeat" || barType === "bar_right_repeat")
'                    if (endRepeat) {
'                        '' Force the end of the previous note to the position of the measure - the cursor won't go past the end repeat
'                        if (elem > 0) {
'                            eventHash [lastHash].endX = Element.x
'                        }
'
'                        if (endingRepeatElem === -1)
'                            endingRepeatElem = elem
'                        var lastVoiceTimeMilliseconds = 0
'                        tempoDone = -1
'                        for (var el2 = startingRepeatElem  el2 < endingRepeatElem  el2++) {
'                            thisMeasure = elements[el2].measureNumber
'                            if (tempoDone !== thisMeasure && me.tempoLocations[thisMeasure]) {
'                                bpm = me.tempoLocations[thisMeasure]
'                                timeDivider = warp * Me.getBeatLength() * bpm / 60
'                                tempoDone = thisMeasure
'                            }
'                            var element2 = elements[el2].elem
'                            ret = me.addElementToEvents(eventHash, element2, voiceTimeMilliseconds, elements[el2].top, elements[el2].height, elements[el2].line, elements[el2].measureNumber, timeDivider, isTiedState, nextIsBar)
'                            isTiedState = ret.isTiedState
'                            nextIsBar = ret.nextIsBar
'                            voiceTime += ret.duration
'                            lastVoiceTimeMilliseconds = voiceTimeMilliseconds
'                            voiceTimeMilliseconds = Math.Round(voiceTime * 1000)
'                        }
'                        if (eventHash["event" + lastVoiceTimeMilliseconds]) '' This won't exist if it is the beginning of the next line. That's ok because we will just count the end of the last line as the end.
'                            eventHash["event" + lastVoiceTimeMilliseconds].endX = elements[endingRepeatElem].elem.x
'                        nextIsBar = True
'                        endingRepeatElem = -1
'                    }
'                    if (startEnding)
'                        endingRepeatElem = elem
'                    if (startRepeat)
'                        startingRepeatElem = elem
'                }
'            }
'            maxVoiceTimeMilliseconds = Math.max(maxVoiceTimeMilliseconds, voiceTimeMilliseconds)
'        }
'        '' now we have all the events, but if there are multiple voices then there may be events out of order or duplicated, so normalize it.
'        timingEvents = Me.makeSortedArray(eventHash)
'        Me.addVerticalInfo (timingEvents)
'        me.addEndPoints(me.lines, timingEvents)
'        timingEvents.push({ type: "end", milliseconds: maxVoiceTimeMilliseconds })
'        me.addUsefulCallbackInfo(timingEvents, bpm * warp)
'        return timingEvents
'    }
'
'    addUsefulCallbackInfo(timingEvents, bpm) {
'        var millisecondsPerMeasure = Me.millisecondsPerMeasure(bpm)
'        for (var i = 0  i < timingEvents.length  i++) {
'            var ev = timingEvents[i]
'            ev.millisecondsPerMeasure = millisecondsPerMeasure
'        }
'    }
'
'    skipTies(elements, index) {
'        while (index < elements.length && elements[index].left === null)
'            index++
'        return elements[index]
'    }
'    addEndPoints(lines, elements) {
'        if (elements.length < 1)
'            Return
'        for (var i = 0  i < elements.length - 1  i++) {
'            var el = elements[i]
'            var next = me.skipTies(elements, i + 1)
'            if (el.left !== null) {
'                '' If there is no left element that is because this is a tie so it should be skipped.
'                var endX = (next && el.top === next.top) ? next.left : lines[el.line].staffGroup.w
'                '' If this is already set, it is because the notes aren't sequential here, like the next thing is a repeat bar line.
'                '' In that case, the right-most position is passed in. There could still be an intervening note in another voice, so always look for the closest position.
'                '' If there is a repeat that stays on the same line, the endX set above won't be right because the next note will be before. In that case, use the endX that was calculated.
'                if (el.endX !== undefined) {
'                    if (endX > el.left)
'                        el.endX = Math.min(el.endX, endX)
'                } else
'                    el.endX = endX
'            }
'        }
'        var lastEl = elements[elements.length - 1]
'        lastEl.endX = lines[lastEl.line].staffGroup.w
'    }
'
'    getBpm(tempo): number {
'        var bpm
'        if (tempo) {
'            bpm = tempo.bpm
'            var beatLength = Me.getBeatLength()
'            var statedBeatLength = tempo.duration && tempo.duration.length > 0 ? tempo.duration[0] : beatLength
'            bpm = bpm * statedBeatLength / beatLength
'        }
'        if (!bpm) {
'            bpm = 180
'            '' Compensate for compound meter, where the beat isn't a beat.
'            var meter = Me.getMeterFraction()
'            if (meter && meter.num !== 3 && (meter.num % 3 === 0)) {
'                bpm = 120
'            }
'        }
'        return bpm
'    }
'
'    setTiming(bpm?: number, measuresOfDelay?: number) {
'        measuresOfDelay = measuresOfDelay || 0
'        if (!me.engraver || !me.engraver.staffgroups) {
'            console.Log ("setTiming cannot be called before the tune is drawn.")
'            Me.noteTimings = []
'            return me.noteTimings
'        }
'
'        var tempo = me.metaText ? me.metaText.tempo : null
'        var naturalBpm = Me.getBpm(tempo)
'        var warp = 1
'        if (bpm) {
'            if (tempo)
'                warp = bpm / naturalBpm
'        } else
'            bpm = naturalBpm
'
'        '' Calculate the basic midi data. We only care about the qpm variable here.
'        ''me.setUpAudio({qpm: bpm})
'
'        var beatLength = Me.getBeatLength()
'        var beatsPerSecond = bpm / 60
'
'        var measureLength = Me.getBarLength()
'
'        var startingDelay = measureLength / beatLength * measuresOfDelay / beatsPerSecond
'        if (startingDelay)
'            startingDelay -= me.getPickupLength() / beatLength / beatsPerSecond
'        var timeDivider = beatLength * beatsPerSecond
'
'        Me.noteTimings = Me.setupEvents(startingDelay, timeDivider, bpm, warp)
'        if (me.noteTimings.length > 0) {
'            me.totalTime = me.noteTimings[me.noteTimings.length - 1].milliseconds / 1000
'            Me.totalBeats = Me.totalTime * beatsPerSecond
'        } else {
'            Me.totalTime = undefined
'            Me.totalBeats = undefined
'        }
'        return me.noteTimings
'    }
'
'    setUpAudio(options: SynthOptions): AudioTracks {
'        if (!options) options = {}
'        var seq = sequence(This, options)
'        return flatten(seq, options, me.formatting.percmap, me.formatting.midi)
'    }
'    deline(options) {
'        return delineTune(me.lines, options)
'    }
'

Attribute VB_Name = "TuneLine"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public columns As Dictionary     ' as  { formatting as  any, lines as  any }
Public image As String
Public newpage As Integer
Public staffbreak As Integer
    '' Only one of separator, subtitle, text, or staff will be present
Public separator As Dictionary
'    {
'        endChar As Number
'        lineLength As Number
'        spaceAbove As Number
'        spaceBelow As Number
'        startChar As Number
'    }
Public subtitle As Dictionary
'    {
'        endChar As Number
'        startChar As Number
'                text As String
'    }
Public text As Dictionary
'    {
'        endChar As Number
'        startChar As Number
'        text As TextFieldProperties
'    }
Public Staffs      As StaffList  ' Array<Staff>
Public staffGroup As StaffGroupElement
Public vskip As Double

Attribute VB_Name = "TuneLineList"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
'MIT License
'
'Copyright (c) 2019-2021 Petr Katerinak
'
'Permission is hereby granted, free of charge, to any person obtaining a copy
'of this software and associated documentation files (the "Software"), to deal
'in the Software without restriction, including without limitation the rights
'to use, copy, modify, merge, publish, distribute, sublicense, and/or sell
'copies of the Software, and to permit persons to whom the Software is
'furnished to do so, subject to the following conditions:
'
'The above copyright notice and this permission notice shall be included in all
'copies or substantial portions of the Software.
'
'THE SOFTWARE IS PROVIDED "AS IS", WITHOUT WARRANTY OF ANY KIND, EXPRESS OR
'IMPLIED, INCLUDING BUT NOT LIMITED TO THE WARRANTIES OF MERCHANTABILITY,
'FITNESS FOR A PARTICULAR PURPOSE AND NONINFRINGEMENT. IN NO EVENT SHALL THE
'AUTHORS OR COPYRIGHT HOLDERS BE LIABLE FOR ANY CLAIM, DAMAGES OR OTHER
'LIABILITY, WHETHER IN AN ACTION OF CONTRACT, TORT OR OTHERWISE, ARISING FROM,
'OUT OF OR IN CONNECTION WITH THE SOFTWARE OR THE USE OR OTHER DEALINGS IN THE
'SOFTWARE.
'
' Version of iArray: 1.0
''修正 元素從 0 開始

Private mainArray As New Collection
Private i As Long ' Counter

' #####################
' #    CONSTRUCTOR    #
' #####################
'Private Sub Class_Initialize()
'  Set mainArray = New Collection
'End Sub

' #####################
' #  Getter / Setter  #
' #####################
'Attribute Element.VB_UserMemId = 0 saved in both procedures

'@DefaultMember
Public Property Get element(ByVal index As Long) As TuneLine
Attribute element.VB_UserMemId = 0
    If index + 1 < 1 Or index + 1 > mainArray.Count Then
        Set element = Nothing
        Exit Property
    End If
    If IsObject(mainArray(index + 1)) = True Then
        Set element = mainArray(index + 1)
    Else
        element = mainArray(index + 1)
    End If

 
End Property

'@DefaultMember
Public Property Let element(ByVal index As Long, ByVal val As TuneLine)
Attribute element.VB_UserMemId = 0
  If index = 0 And mainArray.Count = 0 Then
    Me.Push val
    Exit Property
  End If
  If index + 1 > mainArray.Count Then
    Dim eMsg As String
    eMsg = IIf(mainArray.Count > 0, _
               "Index (" & index + 1 & ") out of iArray bounds (1-" & mainArray.Count & ")", _
               "iArray doesn't have any indexes")
    err.Raise Number:=9, Description:=eMsg
    Exit Property
  End If
  mainArray.Add val, after:=index + 1
  mainArray.Remove index + 1
End Property

' #############################
' # COMMON COLLECTION METHODS #
' #############################
Public Function Count() As Long
  Count = mainArray.Count
End Function
Public Sub Add(ByVal val As TuneLine, Optional ByVal bef As Variant = Empty, Optional ByVal aft As Variant = Empty)
  If IsEmpty(bef) And IsEmpty(aft) Then
    mainArray.Add val
  ElseIf IsEmpty(bef) Then
    mainArray.Add val, , , aft
  ElseIf IsEmpty(aft) Then
    mainArray.Add val, , bef
  Else
    mainArray.Add val, , bef, aft
  End If
End Sub
Public Sub Remove(index As Long)
  mainArray.Remove index + 1
End Sub

' ####################
' #  PUBLIC METHODS  #
' ####################

'AddAfter
' Adds element after given index.
' {1,2,3} -> index >= 3 -> Push val
' {1,2,3} -> index < 1 -> Unshift val
' {} -> index = any -> Push val
' @param Long index | Index after which will be added an element
' @param Variant val | One element (String, number, ...) to add into iArray
' @return Long | Count of elements inside iArray
Public Function AddAfter(ByVal index As Long, ByVal val As TuneLine) As Long
  If Me.Count < 1 Or index + 1 >= Me.Count Then
    Me.Push val
  ElseIf index + 1 < 1 Then
    Me.Unshift val
  Else
    Me.Add val, aft:=index + 1
  End If
  AddAfter = Me.Count
End Function

'AddArrayAfter
' Adds elements after given index.
' {1,2,3} -> index >= 3 -> PushArray val
' {1,2,3} -> index < 1 -> UnshiftArray val
' {} -> index = any -> PushArray val
' @param Long index | Index after which will be added an element
' @param Variant val | Array() or iArray of elements to add into iArray
' @return Long | Count of elements inside iArray
Public Function AddArrayAfter(ByVal index As Long, ByVal val As Variant) As Long
  If Me.Count < 1 Or index + 1 >= Me.Count Then
    Me.PushArray val
  ElseIf index + 1 < 1 Then
    Me.UnshiftArray val
  Else
    If TypeOf val Is TuneLineList Then
      For i = 0 To val.Count - 1
        Me.Add val(i), aft:=index + 1
        Inc index
      Next i
    Else
      For i = LBound(val) To UBound(val)
        Me.Add val(i), aft:=index + 1
        Inc index
      Next i
    End If
  End If
  AddArrayAfter = Me.Count
End Function

'AddArrayBefore
' Adds elements before given index.
' {1,2,3} -> index > 3 -> PushArray val
' {1,2,3} -> index <= 1 -> UnshiftArray val
' {} -> index = any -> PushArray val
' @param Long index | Index after which will be added an element
' @param Variant val | Array() or iArray of elements to add into iArray
' @return Long | Count of elements inside iArray
Public Function AddArrayBefore(ByVal index As Long, ByVal val As Variant) As Long
  If Me.Count < 1 Or index + 1 > Me.Count Then
    Me.PushArray val
  ElseIf index <= 0 Then
    Me.UnshiftArray val
  Else
    If TypeOf val Is TuneLineList Then
      For i = val.Count - 1 To 0 Step -1
        Me.Add val(i), bef:=index + 1
      Next i
    Else
      For i = UBound(val) To LBound(val) Step -1
        Me.Add val(i), bef:=index + 1
      Next i
    End If
  End If
  AddArrayBefore = Me.Count
End Function

'AddBefore
' Adds element before given index.
' {1,2,3} -> index > 3 -> Push val
' {1,2,3} -> index <= 1 -> Unshift val
' {} -> index = any -> Push val
' @param Long index | Index before which will be added an element
' @param Variant val | One element (String, number, ...) to add into iArray
' @return Long | Count of elements inside iArray
Public Function AddBefore(ByVal index As Long, ByVal val As TuneLine) As Long
  If Me.Count < 1 Or index + 1 > Me.Count Then
    Me.Push val
  ElseIf index + 1 <= 1 Then
    Me.Unshift val
  Else
    Me.Add val, bef:=index + 1
  End If
  AddBefore = Me.Count
End Function

'Avg
' Calculates the average of the numeric mainArray.
' @return Variant | Average value / "NaN" if iArray contains non-numeric value(s)
Public Function Avg() As Variant
  If Not Me.ContainsOnlyNumeric Then Avg = "NaN": Exit Function
  Avg = Me.sum / Me.Count
End Function

'Clear
' Empties iArray
Public Function Clear() As Boolean
  For i = mainArray.Count - 1 To 0 Step -1
    mainArray.Remove i + 1
  Next i
  Clear = IIf(mainArray.Count = 0, True, False)
End Function

'Clone
' Makes a hard copy of the mainArray
' @return mainArray | Return exact copy of itself
Public Function clone() As TuneLineList
  Set clone = New TuneLineList
  For i = 0 To Me.Count - 1
    clone.Push Me(i)
  Next i
End Function

'Contains
' Checks if given value is used inside mainArray.
' @param Variant val | One element (String, number, ...) to by checked if it exists in iArray
' $return Boolean | True = exists, False = doesn't exists
Public Function Contains(ByVal val As TuneLine) As Boolean
  Contains = False
  Dim el As Variant
  For Each el In mainArray
    If IsObject(val) = True Or VarType(val) And 8192 Then
        If (VarType(el) And 8192) And (VarType(val) And 8192) Then
            If ArrayDifference(el, val) Then
                Contains = True: Exit Function
            End If
        ElseIf IsObject(el) = True And IsObject(val) = True Then
            If el Is val Then
                Contains = True: Exit Function
            End If
        End If
    Else
        If IsObject(el) = False And (VarType(el) And 8192) <> 8192 Then
            If el = val Then
            Contains = True: Exit Function
            End If
        End If
    End If
  Next el
End Function

'ContainsAll
' Checks if all given values are used inside mainArray.
' @param Variant val | values to by checked if it exists in iArray
' $return Boolean | True = all exists, False = one ore more values doesn't exists
Public Function ContainsAll(ByVal val As TuneLineList) As Boolean
  ContainsAll = False
  Dim foundOccurrences As Integer: foundOccurrences = 0
  Dim values As New TuneLineList
  If Not TypeOf val Is TuneLineList Then
    If IsArray(val) Then
      values.PushArray (val)
    Else
      values.Push (val)
    End If
  Else
    Set values = val
  End If
  For i = 0 To values.Count - 1
    If Me.Contains(values(i)) Then Inc foundOccurrences
  Next i
  If foundOccurrences = values.Count Then ContainsAll = True
End Function

'CountOccurrences
' Checks how many times is given value used inside mainArray.
' @param Variant val | One element (String, number, ...) to by checked
' @return Long | Count of matched occurrences
Public Function CountOccurrences(val As Variant) As Long
  CountOccurrences = 0
  Dim el As Variant
  For Each el In mainArray
  
    If IsObject(val) = True Or VarType(val) And 8192 Then
        If VarType(el) And 8192 And VarType(val) And 8192 Then
            If ArrayDifference(el, val) Then
                Inc CountOccurrences
                Exit Function
            End If
        ElseIf IsObject(el) = True And IsObject(val) = True Then
            If el Is val Then
                Inc CountOccurrences
                Exit Function
            End If
        End If
    Else
        If IsObject(el) = False And Not (VarType(el) And 8192) Then
            If el = val Then
                Inc CountOccurrences
                Exit Function
            End If
        End If
    End If
  
     'If el = val Then Inc CountOccurrences
  Next el
End Function

'Dequeue
' Removes an element from the begining of the mainArray.
' @return Variant | Removed element or Empty, if iArray is empty
'刪除開頭一個元素。
Public Function Dequeue() As TuneLine
  Dequeue = Empty
  If mainArray.Count > 0 Then
    If VarType(Me(0)) = vbString Then
        Dequeue = Me(0)
    ElseIf TypeOf Me(0) Is TuneLineList Then
        Set Dequeue = Me(0)
    ElseIf VarType(Me(0)) = vbArray Then
        Set Dequeue = Me(0)
    ElseIf VarType(Me(0)) = vbObject Then
        Set Dequeue = Me(0)
    Else
        Dequeue = Me(0)
    End If
    
    mainArray.Remove 1
  End If
End Function

'Difference
' Checks for number of differences between two arrays, what was added/deleted or combination.
' @param iArray oldArray | Old iArray to be compared with current iArray
' @param String retType | �dd= deleted from old iArray, �aa= added in current iArray, �cc= combination of both (default)
' @return iArray | iArray with differences found
Public Function Difference(ByRef oldArray As TuneLineList, Optional ByVal retType As String = "c") As TuneLineList
  Set Difference = New TuneLineList
  Select Case LCase(retType)
    Case "d"
      For i = 0 To oldArray.Count - 1
        If Me.Contains(oldArray(i)) = False Then Difference.Push oldArray(i)
      Next i
    Case "a"
      For i = 0 To Count - 1
        If oldArray.Contains(Me(i)) = False Then Difference.Push Me(i)
      Next i
    Case "c"
      For i = 0 To oldArray.Count - 1
        If Me.Contains(oldArray(i)) = False Then Difference.Push oldArray(i)
      Next i
      For i = 0 To Count - 1
        If oldArray.Contains(Me(i)) = False Then Difference.Push Me(i)
      Next i
    Case Else
      err.Raise Number:=5, Description:="Unknown Difference return type attribute:" & vbCrLf & _
                                        "Allowed are 'A'dded/'D'eleted/'C'ombination of both"
  End Select
End Function

'DropLeft
' Remove n elements from the beginning of the mainArray. If n > count of iArray elements, all elements are removed.
' @param Long n | Number of elements to be removed
' @return iArray | Array of the removed elements
Public Function DropLeft(ByRef N As Long) As TuneLineList
  Set DropLeft = New TuneLineList
  If N > Me.Count Then N = Me.Count
  For i = 0 To N - 1
    DropLeft.Push Me(i)
  Next i
  For i = N - 1 To 0 Step -1
    Me.Remove (i)
  Next i
End Function

'DropRight
' Remove n elements from the end of the mainArray. If n > count of iArray elements, all elements are removed.
' @param Long n | Number of elements to be removed
' @return iArray | Array of the removed elements
Public Function DropRight(ByRef N As Long) As TuneLineList
  Set DropRight = New TuneLineList
  If N > Me.Count Then N = Me.Count
  For i = Me.Count - N To Me.Count - 1
    DropRight.Push Me(i)
  Next i
  For i = Me.Count - 1 To Me.Count - N Step -1
    Me.Remove (i)
  Next i
End Function

'Enqueue
' Adds an element at the end of the mainArray.
' @param Variant val | One element (String, number, ...) to add into iArray
' @return Long | Count of elements inside iArray
Public Function Enqueue(ByVal val As Variant) As Long
  Enqueue = Push(val)
End Function

'EnqueueArray
' Adds elements at the end of the iArray
' @param Variant val | Array() or iArray of elements to add into iArray
' @return Long | Count of elements inside array
Public Function EnqueueArray(ByVal val As Variant) As Long
  EnqueueArray = PushArray(val)
End Function

'First
' Returns value of the first element of the mainArray.
' @return Variant | Value of the first element or Empty if iArray is Empty
Public Function First() As TuneLine
  Set First = IIf(Me.Count > 0, Me(0), Empty)
End Function

'Head
' Returns all elements of iArray, except last one.
' @return iArray | Copy of original array, without last element
Public Function head() As TuneLineList
  Set head = Me.clone
  head.Pop
End Function

'Intersect
' Search for element that exists in both iArrays.
' @param iArray intArray | iArray to be intersected with current iArray
' @return iArray | Intersected values
Public Function Intersect(ByRef intersectedArr As TuneLineList) As TuneLineList
  Set Intersect = New TuneLineList
  Dim el As Variant
  For Each el In mainArray
    If intersectedArr.Contains(el) Then
      If Not Intersect.Contains(el) Then Intersect.Push (el)
    End If
  Next el
End Function

'ContainsOnlyNumeric
' Verify that all elements are numbers or convertable to numbers
' $return Boolean | True = contains only numeric values, False = contains inconvertible values
Public Function ContainsOnlyNumeric() As Boolean
  ContainsOnlyNumeric = True
  Dim el As Variant
  For Each el In mainArray
    If Not IsNumeric(el) Then ContainsOnlyNumeric = False: Exit Function
  Next el
End Function

'Join
' Joins two iArrays.
' @param iArray jArray | iArray to be joined with current iArray
' @return iArray | Joined iArray
Public Function Join(ByRef joinArr As TuneLineList) As TuneLineList
  Set Join = New TuneLineList
  Join.PushArray Me
  Join.PushArray joinArr
End Function

'Last
' Returns value of the last element of the mainArray.
' @return Variant | Value of the last element or Empty if iArray is Empty
Public Function Last() As TuneLine
  Set Last = IIf(Me.Count > 0, Me(Me.Count - 1), Empty)
End Function

'OccurrenceIndexes
' Returns all indexes of a value in mainArray.
' @return iArray | iArray containing indexes of occurrence
Public Function OccurenceIndexes(val As Variant) As TuneLineList
  Set OccurenceIndexes = New TuneLineList
  For i = 0 To Me.Count - 1
    If Me(i) = val Then
        OccurenceIndexes.Push (i)
    End If
  Next i
End Function

'Pop
' Removes an element from the end of the mainArray.
' @return Variant | Removed element or Empty, if iArray is empty
Public Function Pop() As TuneLine
  If mainArray.Count > 0 Then
    If VarType(Me(mainArray.Count - 1)) = vbObject Then
       Set Pop = Me(mainArray.Count - 1)
    Else
        Pop = Me(mainArray.Count - 1)
    End If
    mainArray.Remove mainArray.Count
  End If
End Function
  
  

'Push
' Adds an element at the end of the mainArray.
' @param Variant val | One element (String, number, ...) to add into iArray
' @return Long | Count of elements inside iArray
Public Function Push(ByVal val As TuneLine) As Long
  mainArray.Add val
  Push = mainArray.Count
End Function

'PushArray
' Adds elements at the end of the mainArray.
' @param Variant val | Array() or iArray of elements to add into iArray
' @return Long | Count of elements inside array
Public Function PushArray(ByVal val As Variant) As Long
  If TypeOf val Is TuneLineList Then
    For i = 0 To val.Count - 1
      Me.Push val(i)
    Next i
  Else
    For i = LBound(val) To UBound(val)
      Me.Push val(i)
    Next i
  End If
  PushArray = Me.Count
End Function

'RemoveDuplicates
' Keeps only the first occurrence of the value. Affects original array
' @return Long | Count of the removed elements
Public Function RemoveDuplicates() As Long
  RemoveDuplicates = 0
  For i = Me.Count - 1 To 0 Step -1
    If Me.CountOccurrences(Me(i)) > 1 Then
      Me.Remove i
      Inc RemoveDuplicates
    End If
  Next i
End Function

'Reverse
' Reverses the content of the iArray
' @return iArray | Reversed iArray
Public Function Reverse() As TuneLineList
  Set Reverse = New TuneLineList
  For i = 0 To Me.Count - 1
    Reverse.Unshift Me(i)
  Next i
End Function

'Shift
' Removes an element from the begining of the mainArray.
' @return Variant | Removed element or Empty, if iArray is empty
'轉移
' 從 iArray 的開頭刪除一個元素。
' @返回第一個元素 | 如果 iArray 為空，則刪除元素或為空
Public Function shift() As TuneLine
  shift = Empty
  If mainArray.Count > 0 Then
    If VarType(Me(0)) = vbString Then
        shift = Me(0)
    ElseIf TypeOf Me(0) Is TuneLineList Then
        Set shift = Me(0)
    ElseIf VarType(Me(0)) = vbArray Then
        Set shift = Me(0)
    ElseIf VarType(Me(0)) = vbObject Then
        Set shift = Me(0)
    Else
        shift = Me(0)
    End If
    
    mainArray.Remove 1
  End If
End Function

'Shuffle
' Randomly mixes content of the iArray
' @return iArray | Shuffled iArray
' 隨機播放
' 隨機混合 iArray 的內容
'@return iArray | 打亂iArray
Public Function Shuffle() As TuneLineList
  Set Shuffle = New TuneLineList
  Dim keys As New TuneLineList
  For i = 0 To Me.Count - 1
    keys.Push (i)
  Next i
  Dim rndNo As Long
  Do While keys.Count > 0
    rndNo = randomFromTo(0, keys.Count - 1)
    Shuffle.Push Me(keys(rndNo))
    keys.Remove (rndNo)
  Loop
End Function

'Sum
' Calculates the sum of the numeric mainArray.
' @return Variant | Sum value / "NaN" if iArray contains non-numeric value(s)
Public Function sum() As Variant
  If Not Me.ContainsOnlyNumeric Then sum = "NaN": Exit Function
  sum = 0
  Dim el As Variant
  For Each el In mainArray
    sum = sum + el
  Next el
End Function

'Tail
' Returns all elements of iArray, except first one.
' @return iArray | Copy of original array, without first element
'返回陣列中除了第一個元素的剩余元素陣列
Public Function Tail() As TuneLineList
  Set Tail = Me.clone
  Tail.Dequeue
End Function

Public Function ToList()
  If Me.Count = 0 Then ToList = Null: Exit Function
  Dim tarr()
  ReDim tarr(Me.Count - 1)
  For i = 0 To Me.Count - 1
    If VarType(Me(i)) = vbString Then
        tarr(i) = Me(i)
    ElseIf TypeOf Me(i) Is TuneLineList Then
        Set tarr(i) = Me(i)
    ElseIf VarType(Me(i)) = vbObject Then
        Set tarr(i) = Me(i)
    Else
        tarr(i) = Me(i)
    End If
  Next i
  ToList = tarr
End Function

'ToString
' Creates string representation of the mainArray.
' @param String delimiter | Optional character to separate the iArray's elements (default = " ")
' @return String | Formated representation of tha iArray
Public Function ToString(Optional ByVal delimiter As String = " ") As String
  If Me.Count = 0 Then ToString = "{}": Exit Function
  ToString = vbNullString
  For i = 0 To Me.Count - 1
    If i = 0 Then ToString = ToString + "{"
    If i > 0 Then ToString = ToString + delimiter
    If VarType(Me(i)) = vbString Then
        ToString = ToString + Chr$(34)
        ToString = ToString + CStr(Me(i))
        ToString = ToString + Chr$(34)
    ElseIf TypeOf Me(i) Is TuneLineList Then
        ToString = ToString + Me(i).ToString(delimiter)
    ElseIf (VarType(Me(i)) And vbArray) = vbArray Then
        ToString = ToString + "[Array]"
    ElseIf VarType(Me(i)) = vbObject Then
        ToString = ToString + "[Object]"
    Else
        ToString = ToString + CStr(Me(i))
    End If
    
    If i = mainArray.Count - 1 Then ToString = ToString + "}"
  Next i
End Function

'Union
' Combines both iArrays and removes duplicities
' @param iArray uArray | iArray to be unioned with current iArray
' @return iArray | Combined values without duplicities
Public Function Union(ByRef uArr As TuneLineList) As TuneLineList
  Set Union = Me.clone
  Union.PushArray uArr
  Union.RemoveDuplicates
End Function

'Unique
' Returns copy of iArray without duplicated values. Original array is not affected
' @return iArray | iArray with unique values
Public Function Unique() As TuneLineList
  Set Unique = New TuneLineList
  Dim el As Variant
  For Each el In mainArray
    If Not Unique.Contains(el) Then Unique.Push (el)
  Next el
End Function

'Unshift
' Add an element at the begining of the mainArray.
' @param Variant val | One element (String, number, ...) to add into iArray
' @return Long | Count of elements inside iArray
Public Function Unshift(ByVal val As Variant) As Long
  If mainArray.Count = 0 Then
    Unshift = Push(val)
  Else
    mainArray.Add val, before:=1
    Unshift = mainArray.Count
  End If
End Function

'UnshiftArray
' Add elements at the begining of the mainArray.
' @param Variant val | Array() or iArray of elements to add into iArray
' @return Long | Count of elements inside iArray
Public Function UnshiftArray(ByVal val As Variant) As Long
  If TypeOf val Is TuneLineList Then
    For i = val.Count - 1 To 0 Step -1
      Unshift val(i)
    Next i
  Else
    For i = UBound(val) To LBound(val) Step -1
      Unshift val(i)
    Next i
  End If
  UnshiftArray = mainArray.Count
End Function


' #####################
' # PRIVATE FUNCTIONS #
' #####################
Sub Inc(ByRef i)
   i = i + 1
End Sub

'Private Function rangeToArray(ByVal rng As Range) As Variant
'  rangeToArray = rng.Value
'End Function

Private Function randomFromTo(ByVal from As Long, ByVal upTo As Long) As Long
  Randomize
  randomFromTo = Int(from + Rnd() * (upTo - from + 1))
End Function

'比對 兩個陣列是否一樣
Private Function ArrayDifference(arr1 As Variant, arr2 As Variant) As Boolean

    Dim i As Integer
    If UBound(arr1) = UBound(arr2) Then
        For i = 0 To UBound(arr1)
            If arr1(i) = arr2(i) Then
                ArrayDifference = True
            Else
                ArrayDifference = False
                Exit Function
            End If
        Next
    Else
        ArrayDifference = False
    End If

End Function

'@Description("changes the contents of the array by removing or replacing existing elements and/or adding new elements in place.")
Public Function Splice( _
        ByVal StartIndex As Long, _
        ParamArray Args() As Variant _
    ) As Variant()
    'Dim LocalItems() As Variant
    Dim ActualStart As Long
    Dim ActualDeleteCount As Long
    Dim ArgsCount As Long
    Dim LocalLength As Long
    Dim LocalArgs() As Variant
    Dim result() As Variant
    Dim i As Long
    Dim TempArray() As Variant
    Dim ItemCount As Long
    Dim TempItems() As Variant
    
    LocalArgs = Args
    'LocalItems = mainArray
    LocalLength = Me.Count
    If StartIndex < LocalLength Then
        ActualStart = StartIndex
    Else
        ActualStart = min(StartIndex, LocalLength)
    End If
    
    ArgsCount = UBound(LocalArgs) + 1
    If ArgsCount = 0 Then
        ' only a start index has been supplied
        ' we're gonna delete everything
        ' 僅提供了起始索引
         '我們要刪除所有內容
        ItemCount = 0
        ActualDeleteCount = LocalLength - ActualStart
    Else
        ' first arg in args is delete count, second onwards are insertion items
        ' args 中的第一個參數是刪除計數，第二個之後是插入項
        ItemCount = ArgsCount - 1
        'deleteCount is first element in args.
        'deleteCount 是 args 中的第一個元素。
        ActualDeleteCount = min(max(Args(LBound(Args)), 0), LocalLength - ActualStart)
    End If
    

    ' get items to be deleted for return val
    ' 取得和刪除
    If ActualDeleteCount > 0 Then
        ReDim result(0 To ActualDeleteCount - 1)
        i = 0
        Do While i < ActualDeleteCount
            If IsObject(Me(ActualStart)) Then
                Set result(i) = Me(ActualStart)
                Me.Remove ActualStart
            Else
                result(i) = Me(ActualStart)
                Me.Remove ActualStart
            End If
            Inc i
        Loop
    Else
        ' return empty array if nothing to be deleted
        ReDim result(0)
    End If
    
    '取得要插入的陣列資料
    If ItemCount > 0 Then
        ReDim TempItems(0 To ItemCount - 1)
        For i = 0 To ItemCount - 1
            If IsObject(LocalArgs(i + 1)) Then
                Set TempItems(i) = LocalArgs(i + 1)
            Else
                TempItems(i) = LocalArgs(i + 1)
            End If
        Next
    Me.AddArrayBefore ActualStart, TempItems
    End If
    
    
    Splice = result
End Function

Attribute VB_Name = "VoiceABC"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public el_typs As String
Public typs As String
    ''VoiceItemClef {
Public stafflines As Double
Public staffscale As Double
Public transpose As Double
Public verticalPos As Double
Public clefPos As Double
Public startChar As Integer
Public endChar As Integer
    '' VoiceItemBar {
Public barNumber As Integer
Public chord As iArray     'Array<ChordProperties>
Public decoration As iArray     'Array<Decorations>
Public endEnding As Boolean
Public startEnding As String
    '' VoiceItemGap {
Public gap As Double
Public accidentals As iArray     'Array<Accidental>;
Public root As String
Public acc As String
Public mode As String
    '' VoiceItemKey extends KeySignature {
    '' VoiceItemMeter extends Meter {
    '' Meter {
Public value As vMeterFractionList     ' Array<MeterFraction>
Public beat_division As vMeterFractionList     '  Array<MeterFraction>
    '' VoiceItemMidi {

Public cmd As Dictionary ' MidiCommands
Public params As iArray    ' Array<string | number>
    '' VoiceItemOverlay {
    ''el_type as  "overlay"
    ''startChar as  number
    ''endChar as  number
    ''overlay as  Array<NoteProperties>
    '' VoiceItemPart {

Public title As String
    '' VoiceItemScale {

Public size As Double
    '' VoiceItemStem {

Public Direction As String ' StemDirection
    '' VoiceItemStyle {

Public head As String ' NoteHeadType
    '' VoiceItemTempo extends TempoProperties {

    '' TempoProperties {
    ''duration as  Array<number>
Public bpm As Double
Public preString As String
Public postString As String
Public suppress As Boolean
Public suppressBpm As Boolean
    '' VoiceItemTranspose {

Public steps As Double
    '' VoiceItemNote extends NoteProperties {

    '' NoteProperties {'' TODO
    ''type as  string
    ''el_type as  string  ''TODO enumerate these
    ''abselem as  AbsoluteElement

Public beambr As Double
Public duration As Double
Public endBeam As Boolean
Public endSlur As iArray    ' Array<number>
Public endTriplet As Boolean     'true
Public fonts As Dictionary
'{
'        annotationfont as  Font,
'        gchordfont as  Font,
'        measurefont as  Font,
'        repeatfont as  Font,
'        tripletfont as  Font,
'        vocalfont As font
'    }
Public gracenotes As vpitchesNoteList
Public lyric As iArray    'Array<{ syllable as  string  divider as  ' ' | '-' | '_'  }>
Public nostem As Boolean
Public midiPitches As Dictionary ' midiPitches
Public midiGraceNotePitches As Dictionary  ' MidiGracePitches
Public pitches As vpitchesNoteList
'Array<{
'        accidental As AccidentalName
'        pitch As Double
'        name As String
'        startSlur as  {
'            label As Double
'            direction as  'up', 'down'
'            style as  'dotted'
'        }[]
'        endSlur as  Array<number>
'        startTie as  {
'            direction as  'up', 'down'
'            style as  'dotted'
'        }
'        endTie As Boolean
'        verticalPos As Double
'        highestVert As Double
'        style As NoteHeadType
'    }>
Public positioning As Dictionary
'{
'        chordPosition as  'above' | 'below' | 'hidden'
'        dynamicPosition as  'above' | 'below' | 'hidden'
'        ornamentPosition as  'above' | 'below' | 'hidden'
'        vocalPosition as  'above' | 'below' | 'hidden'
'        volumePosition as  'above' | 'below' | 'hidden'
'    }
Public rest As vrestNote
'{
'        type as  'invisible' | 'spacer' | 'rest' | 'multimeasure' | 'invisible-multimeasure' | 'whole'
' text As Double
'        startTie as  {
'            direction as  'up', 'down'
'            style as  'dotted'
'        }
' endTie As Boolean
'    }
Public startBeam As Boolean
Public startSlur As vSlurList
Public startTriplet As Double
Public tripletMultiplier As Double
Public tripletR As Double
Public stemConnectsToAbove As Boolean    'true
Public style As String  'NoteHeadType
    ''startChar as  number
    ''endChar as  number
    '' VoiceItemBeam {
Public averagepitch As Double
Public minPitch As Double
Public maxPitch As Double
    '' VoiceItemChord extends ChordProperties {
    '' ChordProperties {
Public Name As String
Public position As String 'ChordPlacement
Public rel_position As point
Public dots As Integer


Public Function clone() As VoiceABC
    Dim cope As New VoiceABC
    cope.averagepitch = Me.averagepitch
    cope.barNumber = Me.barNumber
    cope.beambr = Me.beambr
 Set cope.beat_division = Me.beat_division
    cope.bpm = Me.bpm
   Set cope.chord = Me.chord
    cope.clefPos = Me.clefPos
   Set cope.cmd = Me.cmd
   Set cope.decoration = Me.decoration
    cope.Direction = Me.Direction
    cope.duration = Me.duration
    cope.el_typs = Me.el_typs
    cope.endBeam = Me.endBeam
    cope.endChar = Me.endChar
    cope.endEnding = Me.endEnding
 Set cope.endSlur = Me.endSlur
    cope.endTriplet = Me.endTriplet
 Set cope.fonts = Me.fonts
    cope.gap = Me.gap
 Set cope.gracenotes = Me.gracenotes
    cope.head = Me.head
  Set cope.lyric = Me.lyric
    cope.maxPitch = Me.maxPitch
  Set cope.midiPitches = Me.midiPitches
  Set cope.midiGraceNotePitches = Me.midiGraceNotePitches
    cope.minPitch = Me.minPitch
    cope.Name = Me.Name
    cope.nostem = Me.nostem
   Set cope.params = Me.params
   Set cope.pitches = Me.pitches
    cope.position = Me.position
   Set cope.positioning = Me.positioning
    cope.postString = Me.postString
    cope.preString = Me.preString
  Set cope.rel_position = Me.rel_position
  Set cope.rest = Me.rest
    cope.size = Me.size
    cope.stafflines = Me.stafflines
    cope.staffscale = Me.staffscale
    cope.startBeam = Me.startBeam
    cope.startChar = Me.startChar
    cope.startEnding = Me.startEnding
  Set cope.startSlur = Me.startSlur
    cope.startTriplet = Me.startTriplet
    cope.stemConnectsToAbove = Me.stemConnectsToAbove
    cope.steps = Me.steps
    cope.style = Me.style
    cope.suppress = Me.suppress
    cope.suppressBpm = Me.suppressBpm
    cope.title = Me.title
    cope.transpose = Me.transpose
    cope.tripletMultiplier = Me.tripletMultiplier
    cope.tripletR = Me.tripletR
    cope.typs = Me.typs
 Set cope.value = Me.value
    cope.verticalPos = Me.verticalPos
        
    Set clone = cope
    
End Function

Attribute VB_Name = "VoiceABCList"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
'MIT License
'
'Copyright (c) 2019-2021 Petr Katerinak
'
'Permission is hereby granted, free of charge, to any person obtaining a copy
'of this software and associated documentation files (the "Software"), to deal
'in the Software without restriction, including without limitation the rights
'to use, copy, modify, merge, publish, distribute, sublicense, and/or sell
'copies of the Software, and to permit persons to whom the Software is
'furnished to do so, subject to the following conditions:
'
'The above copyright notice and this permission notice shall be included in all
'copies or substantial portions of the Software.
'
'THE SOFTWARE IS PROVIDED "AS IS", WITHOUT WARRANTY OF ANY KIND, EXPRESS OR
'IMPLIED, INCLUDING BUT NOT LIMITED TO THE WARRANTIES OF MERCHANTABILITY,
'FITNESS FOR A PARTICULAR PURPOSE AND NONINFRINGEMENT. IN NO EVENT SHALL THE
'AUTHORS OR COPYRIGHT HOLDERS BE LIABLE FOR ANY CLAIM, DAMAGES OR OTHER
'LIABILITY, WHETHER IN AN ACTION OF CONTRACT, TORT OR OTHERWISE, ARISING FROM,
'OUT OF OR IN CONNECTION WITH THE SOFTWARE OR THE USE OR OTHER DEALINGS IN THE
'SOFTWARE.
'
' Version of iArray: 1.0
''修正 元素從 0 開始

Private mainArray As New Collection
Private i As Long ' Counter

' #####################
' #    CONSTRUCTOR    #
' #####################
'Private Sub Class_Initialize()
'  Set mainArray = New Collection
'End Sub

' #####################
' #  Getter / Setter  #
' #####################
'Attribute Element.VB_UserMemId = 0 saved in both procedures

'@DefaultMember
Public Property Get element(ByVal index As Long) As VoiceABC
Attribute element.VB_UserMemId = 0
    If index + 1 < 1 Or index + 1 > mainArray.Count Then
        Set element = Nothing
        Exit Property
    End If
    If IsObject(mainArray(index + 1)) = True Then
        Set element = mainArray(index + 1)
    Else
        element = mainArray(index + 1)
    End If

 
End Property

'@DefaultMember
Public Property Let element(ByVal index As Long, ByVal val As VoiceABC)
Attribute element.VB_UserMemId = 0
  If index = 0 And mainArray.Count = 0 Then
    Me.Push val
    Exit Property
  End If
  If index + 1 > mainArray.Count Then
    Dim eMsg As String
    eMsg = IIf(mainArray.Count > 0, _
               "Index (" & index + 1 & ") out of iArray bounds (1-" & mainArray.Count & ")", _
               "iArray doesn't have any indexes")
    err.Raise Number:=9, Description:=eMsg
    Exit Property
  End If
  mainArray.Add val, after:=index + 1
  mainArray.Remove index + 1
End Property

' #############################
' # COMMON COLLECTION METHODS #
' #############################
Public Function Count() As Long
  Count = mainArray.Count
End Function
Public Sub Add(ByVal val As VoiceABC, Optional ByVal bef As Variant = Empty, Optional ByVal aft As Variant = Empty)
  If IsEmpty(bef) And IsEmpty(aft) Then
    mainArray.Add val
  ElseIf IsEmpty(bef) Then
    mainArray.Add val, , , aft
  ElseIf IsEmpty(aft) Then
    mainArray.Add val, , bef
  Else
    mainArray.Add val, , bef, aft
  End If
End Sub
Public Sub Remove(index As Long)
  mainArray.Remove index + 1
End Sub

' ####################
' #  PUBLIC METHODS  #
' ####################

'AddAfter
' Adds element after given index.
' {1,2,3} -> index >= 3 -> Push val
' {1,2,3} -> index < 1 -> Unshift val
' {} -> index = any -> Push val
' @param Long index | Index after which will be added an element
' @param Variant val | One element (String, number, ...) to add into iArray
' @return Long | Count of elements inside iArray
Public Function AddAfter(ByVal index As Long, ByVal val As VoiceABC) As Long
  If Me.Count < 1 Or index + 1 >= Me.Count Then
    Me.Push val
  ElseIf index + 1 < 1 Then
    Me.Unshift val
  Else
    Me.Add val, aft:=index + 1
  End If
  AddAfter = Me.Count
End Function

'AddArrayAfter
' Adds elements after given index.
' {1,2,3} -> index >= 3 -> PushArray val
' {1,2,3} -> index < 1 -> UnshiftArray val
' {} -> index = any -> PushArray val
' @param Long index | Index after which will be added an element
' @param Variant val | Array() or iArray of elements to add into iArray
' @return Long | Count of elements inside iArray
Public Function AddArrayAfter(ByVal index As Long, ByVal val As Variant) As Long
  If Me.Count < 1 Or index + 1 >= Me.Count Then
    Me.PushArray val
  ElseIf index + 1 < 1 Then
    Me.UnshiftArray val
  Else
    If TypeOf val Is VoiceABCList Then
      For i = 0 To val.Count - 1
        Me.Add val(i), aft:=index + 1
        Inc index
      Next i
    Else
      For i = LBound(val) To UBound(val)
        Me.Add val(i), aft:=index + 1
        Inc index
      Next i
    End If
  End If
  AddArrayAfter = Me.Count
End Function

'AddArrayBefore
' Adds elements before given index.
' {1,2,3} -> index > 3 -> PushArray val
' {1,2,3} -> index <= 1 -> UnshiftArray val
' {} -> index = any -> PushArray val
' @param Long index | Index after which will be added an element
' @param Variant val | Array() or iArray of elements to add into iArray
' @return Long | Count of elements inside iArray
Public Function AddArrayBefore(ByVal index As Long, ByVal val As Variant) As Long
  If Me.Count < 1 Or index + 1 > Me.Count Then
    Me.PushArray val
  ElseIf index <= 0 Then
    Me.UnshiftArray val
  Else
    If TypeOf val Is VoiceABCList Then
      For i = val.Count - 1 To 0 Step -1
        Me.Add val(i), bef:=index + 1
      Next i
    Else
      For i = UBound(val) To LBound(val) Step -1
        Me.Add val(i), bef:=index + 1
      Next i
    End If
  End If
  AddArrayBefore = Me.Count
End Function

'AddBefore
' Adds element before given index.
' {1,2,3} -> index > 3 -> Push val
' {1,2,3} -> index <= 1 -> Unshift val
' {} -> index = any -> Push val
' @param Long index | Index before which will be added an element
' @param Variant val | One element (String, number, ...) to add into iArray
' @return Long | Count of elements inside iArray
Public Function AddBefore(ByVal index As Long, ByVal val As VoiceABC) As Long
  If Me.Count < 1 Or index + 1 > Me.Count Then
    Me.Push val
  ElseIf index + 1 <= 1 Then
    Me.Unshift val
  Else
    Me.Add val, bef:=index + 1
  End If
  AddBefore = Me.Count
End Function



'Clear
' Empties iArray
Public Function Clear() As Boolean
  For i = mainArray.Count - 1 To 0 Step -1
    mainArray.Remove i + 1
  Next i
  Clear = IIf(mainArray.Count = 0, True, False)
End Function

'Clone
' Makes a hard copy of the mainArray
' @return mainArray | Return exact copy of itself
Public Function clone() As VoiceABCList
  Set clone = New VoiceABCList
  For i = 0 To Me.Count - 1
    clone.Push Me(i)
  Next i
End Function

'Contains
' Checks if given value is used inside mainArray.
' @param Variant val | One element (String, number, ...) to by checked if it exists in iArray
' $return Boolean | True = exists, False = doesn't exists
Public Function Contains(ByVal val As VoiceABC) As Boolean
  Contains = False
  Dim el As Variant
  For Each el In mainArray
    If IsObject(val) = True Or VarType(val) And 8192 Then
        If (VarType(el) And 8192) And (VarType(val) And 8192) Then
            If ArrayDifference(el, val) Then
                Contains = True: Exit Function
            End If
        ElseIf IsObject(el) = True And IsObject(val) = True Then
            If el Is val Then
                Contains = True: Exit Function
            End If
        End If
    Else
        If IsObject(el) = False And (VarType(el) And 8192) <> 8192 Then
            If el = val Then
            Contains = True: Exit Function
            End If
        End If
    End If
  Next el
End Function

'ContainsAll
' Checks if all given values are used inside mainArray.
' @param Variant val | values to by checked if it exists in iArray
' $return Boolean | True = all exists, False = one ore more values doesn't exists
Public Function ContainsAll(ByVal val As VoiceABCList) As Boolean
  ContainsAll = False
  Dim foundOccurrences As Integer: foundOccurrences = 0
  Dim values As New VoiceABCList
  If Not TypeOf val Is VoiceABCList Then
    If IsArray(val) Then
      values.PushArray (val)
    Else
      values.Push (val)
    End If
  Else
    Set values = val
  End If
  For i = 0 To values.Count - 1
    If Me.Contains(values(i)) Then Inc foundOccurrences
  Next i
  If foundOccurrences = values.Count Then ContainsAll = True
End Function


'Dequeue
' Removes an element from the begining of the mainArray.
' @return Variant | Removed element or Empty, if iArray is empty
'刪除開頭一個元素。
Public Function Dequeue() As VoiceABC
  Dequeue = Empty
  If mainArray.Count > 0 Then
    If VarType(Me(0)) = vbString Then
        Dequeue = Me(0)
    ElseIf TypeOf Me(0) Is VoiceABCList Then
        Set Dequeue = Me(0)
    ElseIf VarType(Me(0)) = vbArray Then
        Set Dequeue = Me(0)
    ElseIf VarType(Me(0)) = vbObject Then
        Set Dequeue = Me(0)
    Else
        Dequeue = Me(0)
    End If
    
    mainArray.Remove 1
  End If
End Function

'Difference
' Checks for number of differences between two arrays, what was added/deleted or combination.
' @param iArray oldArray | Old iArray to be compared with current iArray
' @param String retType | �dd= deleted from old iArray, �aa= added in current iArray, �cc= combination of both (default)
' @return iArray | iArray with differences found
Public Function Difference(ByRef oldArray As VoiceABCList, Optional ByVal retType As String = "c") As VoiceABCList
  Set Difference = New VoiceABCList
  Select Case LCase(retType)
    Case "d"
      For i = 0 To oldArray.Count - 1
        If Me.Contains(oldArray(i)) = False Then Difference.Push oldArray(i)
      Next i
    Case "a"
      For i = 0 To Count - 1
        If oldArray.Contains(Me(i)) = False Then Difference.Push Me(i)
      Next i
    Case "c"
      For i = 0 To oldArray.Count - 1
        If Me.Contains(oldArray(i)) = False Then Difference.Push oldArray(i)
      Next i
      For i = 0 To Count - 1
        If oldArray.Contains(Me(i)) = False Then Difference.Push Me(i)
      Next i
    Case Else
      err.Raise Number:=5, Description:="Unknown Difference return type attribute:" & vbCrLf & _
                                        "Allowed are 'A'dded/'D'eleted/'C'ombination of both"
  End Select
End Function


'First
' Returns value of the first element of the mainArray.
' @return Variant | Value of the first element or Empty if iArray is Empty
Public Function First() As VoiceABC
  Set First = IIf(Me.Count > 0, Me(0), Empty)
End Function

'Head
' Returns all elements of iArray, except last one.
' @return iArray | Copy of original array, without last element
Public Function head() As VoiceABCList
  Set head = Me.clone
  head.Pop
End Function

'Intersect
' Search for element that exists in both iArrays.
' @param iArray intArray | iArray to be intersected with current iArray
' @return iArray | Intersected values
Public Function Intersect(ByRef intersectedArr As VoiceABCList) As VoiceABCList
  Set Intersect = New VoiceABCList
  Dim el As Variant
  For Each el In mainArray
    If intersectedArr.Contains(el) Then
      If Not Intersect.Contains(el) Then Intersect.Push (el)
    End If
  Next el
End Function

'ContainsOnlyNumeric
' Verify that all elements are numbers or convertable to numbers
' $return Boolean | True = contains only numeric values, False = contains inconvertible values
Public Function ContainsOnlyNumeric() As Boolean
  ContainsOnlyNumeric = True
  Dim el As Variant
  For Each el In mainArray
    If Not IsNumeric(el) Then ContainsOnlyNumeric = False: Exit Function
  Next el
End Function

'Join
' Joins two iArrays.
' @param iArray jArray | iArray to be joined with current iArray
' @return iArray | Joined iArray
Public Function Join(ByRef joinArr As VoiceABCList) As VoiceABCList
  Set Join = New VoiceABCList
  Join.PushArray Me
  Join.PushArray joinArr
End Function

'Last
' Returns value of the last element of the mainArray.
' @return Variant | Value of the last element or Empty if iArray is Empty
Public Function Last() As VoiceABC
    If Me.Count > 0 Then
        If IsObject(Me(Me.Count - 1)) Then
            Set set Last = IIf(Me.Count > 0, Me(Me.Count - 1), Empty)
        Else
            Set Last = IIf(Me.Count > 0, Me(Me.Count - 1), Empty)
        End If
    Else
        Set Last = Nothing
    End If
End Function


'Pop
' Removes an element from the end of the mainArray.
' @return Variant | Removed element or Empty, if iArray is empty
Public Function Pop() As VoiceABC
  If mainArray.Count > 0 Then
    If VarType(Me(mainArray.Count - 1)) = vbObject Then
       Set Pop = Me(mainArray.Count - 1)
    Else
        Pop = Me(mainArray.Count - 1)
    End If
    mainArray.Remove mainArray.Count
  End If
End Function
  
  

'Push
' Adds an element at the end of the mainArray.
' @param Variant val | One element (String, number, ...) to add into iArray
' @return Long | Count of elements inside iArray
Public Function Push(ByVal val As VoiceABC) As Long
  mainArray.Add val
  Push = mainArray.Count
End Function

'PushArray
' Adds elements at the end of the mainArray.
' @param Variant val | Array() or iArray of elements to add into iArray
' @return Long | Count of elements inside array
Public Function PushArray(ByVal val As Variant) As Long
  If TypeOf val Is VoiceABCList Then
    For i = 0 To val.Count - 1
      Me.Push val(i)
    Next i
  Else
    For i = LBound(val) To UBound(val)
      Me.Push val(i)
    Next i
  End If
  PushArray = Me.Count
End Function


'Reverse
' Reverses the content of the iArray
' @return iArray | Reversed iArray
Public Function Reverse() As VoiceABCList
  Set Reverse = New VoiceABCList
  For i = 0 To Me.Count - 1
    Reverse.Unshift Me(i)
  Next i
End Function

'Shift
' Removes an element from the begining of the mainArray.
' @return Variant | Removed element or Empty, if iArray is empty
'轉移
' 從 iArray 的開頭刪除一個元素。
' @返回第一個元素 | 如果 iArray 為空，則刪除元素或為空
Public Function shift() As VoiceABC
  shift = Empty
  If mainArray.Count > 0 Then
    If VarType(Me(0)) = vbString Then
        shift = Me(0)
    ElseIf TypeOf Me(0) Is VoiceABCList Then
        Set shift = Me(0)
    ElseIf VarType(Me(0)) = vbArray Then
        Set shift = Me(0)
    ElseIf VarType(Me(0)) = vbObject Then
        Set shift = Me(0)
    Else
        shift = Me(0)
    End If
    
    mainArray.Remove 1
  End If
End Function

'Shuffle
' Randomly mixes content of the iArray
' @return iArray | Shuffled iArray
' 隨機播放
' 隨機混合 iArray 的內容
'@return iArray | 打亂iArray
Public Function Shuffle() As VoiceABCList
  Set Shuffle = New VoiceABCList
  Dim keys As New VoiceABCList
  For i = 0 To Me.Count - 1
    keys.Push (i)
  Next i
  Dim rndNo As Long
  Do While keys.Count > 0
    rndNo = randomFromTo(0, keys.Count - 1)
    Shuffle.Push Me(keys(rndNo))
    keys.Remove (rndNo)
  Loop
End Function



'Tail
' Returns all elements of iArray, except first one.
' @return iArray | Copy of original array, without first element
'返回陣列中除了第一個元素的剩余元素陣列
Public Function Tail() As VoiceABCList
  Set Tail = Me.clone
  Tail.Dequeue
End Function

Public Function ToList()
  If Me.Count = 0 Then ToList = Null: Exit Function
  Dim tarr()
  ReDim tarr(Me.Count - 1)
  For i = 0 To Me.Count - 1
    If VarType(Me(i)) = vbString Then
        tarr(i) = Me(i)
    ElseIf TypeOf Me(i) Is VoiceABCList Then
        Set tarr(i) = Me(i)
    ElseIf VarType(Me(i)) = vbObject Then
        Set tarr(i) = Me(i)
    Else
        tarr(i) = Me(i)
    End If
  Next i
  ToList = tarr
End Function

'ToString
' Creates string representation of the mainArray.
' @param String delimiter | Optional character to separate the iArray's elements (default = " ")
' @return String | Formated representation of tha iArray
Public Function ToString(Optional ByVal delimiter As String = " ") As String
  If Me.Count = 0 Then ToString = "{}": Exit Function
  ToString = vbNullString
  For i = 0 To Me.Count - 1
    If i = 0 Then ToString = ToString + "{"
    If i > 0 Then ToString = ToString + delimiter
    If VarType(Me(i)) = vbString Then
        ToString = ToString + Chr$(34)
        ToString = ToString + CStr(Me(i))
        ToString = ToString + Chr$(34)
    ElseIf TypeOf Me(i) Is VoiceABCList Then
        ToString = ToString + Me(i).ToString(delimiter)
    ElseIf (VarType(Me(i)) And vbArray) = vbArray Then
        ToString = ToString + "[Array]"
    ElseIf VarType(Me(i)) = vbObject Then
        ToString = ToString + "[Object]"
    Else
        ToString = ToString + CStr(Me(i))
    End If
    
    If i = mainArray.Count - 1 Then ToString = ToString + "}"
  Next i
End Function

'Union
' Combines both iArrays and removes duplicities
' @param iArray uArray | iArray to be unioned with current iArray
' @return iArray | Combined values without duplicities
Public Function Union(ByRef uArr As VoiceABCList) As VoiceABCList
  Set Union = Me.clone
  Union.PushArray uArr
  Union.RemoveDuplicates
End Function

'Unique
' Returns copy of iArray without duplicated values. Original array is not affected
' @return iArray | iArray with unique values
Public Function Unique() As VoiceABCList
  Set Unique = New VoiceABCList
  Dim el As Variant
  For Each el In mainArray
    If Not Unique.Contains(el) Then Unique.Push (el)
  Next el
End Function

'Unshift
' Add an element at the begining of the mainArray.
' @param Variant val | One element (String, number, ...) to add into iArray
' @return Long | Count of elements inside iArray
Public Function Unshift(ByVal val As Variant) As Long
  If mainArray.Count = 0 Then
    Unshift = Push(val)
  Else
    mainArray.Add val, before:=1
    Unshift = mainArray.Count
  End If
End Function




' #####################
' # PRIVATE FUNCTIONS #
' #####################
Sub Inc(ByRef i)
   i = i + 1
End Sub



'比對 兩個陣列是否一樣
Private Function ArrayDifference(arr1 As Variant, arr2 As Variant) As Boolean

    Dim i As Integer
    If UBound(arr1) = UBound(arr2) Then
        For i = 0 To UBound(arr1)
            If arr1(i) = arr2(i) Then
                ArrayDifference = True
            Else
                ArrayDifference = False
                Exit Function
            End If
        Next
    Else
        ArrayDifference = False
    End If

End Function

'@Description("changes the contents of the array by removing or replacing existing elements and/or adding new elements in place.")
Public Function Splice( _
        ByVal StartIndex As Long, _
        ParamArray Args() As Variant _
    ) As Variant()
    'Dim LocalItems() As Variant
    Dim ActualStart As Long
    Dim ActualDeleteCount As Long
    Dim ArgsCount As Long
    Dim LocalLength As Long
    Dim LocalArgs() As Variant
    Dim result() As Variant
    Dim i As Long
    Dim TempArray() As Variant
    Dim ItemCount As Long
    Dim TempItems() As Variant
    
    LocalArgs = Args
    'LocalItems = mainArray
    LocalLength = Me.Count
    If StartIndex < LocalLength Then
        ActualStart = StartIndex
    Else
        ActualStart = min(StartIndex, LocalLength)
    End If
    
    ArgsCount = UBound(LocalArgs) + 1
    If ArgsCount = 0 Then
        ' only a start index has been supplied
        ' we're gonna delete everything
        ' 僅提供了起始索引
         '我們要刪除所有內容
        ItemCount = 0
        ActualDeleteCount = LocalLength - ActualStart
    Else
        ' first arg in args is delete count, second onwards are insertion items
        ' args 中的第一個參數是刪除計數，第二個之後是插入項
        ItemCount = ArgsCount - 1
        'deleteCount is first element in args.
        'deleteCount 是 args 中的第一個元素。
        ActualDeleteCount = min(max(Args(LBound(Args)), 0), LocalLength - ActualStart)
    End If
    

    ' get items to be deleted for return val
    ' 取得和刪除
    If ActualDeleteCount > 0 Then
        ReDim result(0 To ActualDeleteCount - 1)
        i = 0
        Do While i < ActualDeleteCount
            If IsObject(Me(ActualStart)) Then
                Set result(i) = Me(ActualStart)
                Me.Remove ActualStart
            Else
                result(i) = Me(ActualStart)
                Me.Remove ActualStart
            End If
            Inc i
        Loop
    Else
        ' return empty array if nothing to be deleted
        ReDim result(0)
    End If
    
    '取得要插入的陣列資料
    If ItemCount > 0 Then
        ReDim TempItems(0 To ItemCount - 1)
        For i = 0 To ItemCount - 1
            If IsObject(LocalArgs(i + 1)) Then
                Set TempItems(i) = LocalArgs(i + 1)
            Else
                TempItems(i) = LocalArgs(i + 1)
            End If
        Next
    Me.AddArrayBefore ActualStart, TempItems
    End If
    
    
    Splice = result
End Function

Attribute VB_Name = "VoiceElement"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public i As Double                  ''站存設定現在要作用的子元素
Public durationIndex As Double      ''累記 現在已經讀取每音符長度總合
Public barDurationIndex As Double   ''累記 每小節內的音符長度總合
Public startX As Double             ''樂器名後 的 x 為開始位置
Public minX As Double
Public nextX As Double              ''下一個子元素的位置，是用子元素的時長(duration)*8 開跟號 * spacing
     ''如子元素 (bar) 沒時長則用 前一次取到的 (note) 時長 spacingduration
Public spacingduration As Double
Public header As String     ''每段頭的樂器名

Public children As MusicItemList  'AbsoluteElementList
Public beams As BeamElemList
Public otherchildren As iArray 'voiceItem[] '' ties, slurs, triplets
     '' "GlissandoElem" as    ''滑音
     '' "CrescendoElem" as    ''漸強
     '' "DynamicDecoration" as ''動態裝飾
     '' "TripletElem" as  ''三連音
     '' "EndingElem" as   ''結尾
     '' "TieElem" as      ''圓滑線
Public w As Double
Public duplicate As Boolean
Public voicenumber As Double
Public voicetotal As Double
Public bottom As Double
Public top As Double
Public specialY As Dictionary  ' SpecialYProperties
Public barfrom As Boolean
Public barto As Boolean
Public headerPosition As Double
Public staffInfo As vStaffInfo
'{
' top As Integer
' bottom As Integer
' lines As Integer
' voices As Integer[]
' specialY As SpecialYProperties
' absoluteY As Integer
' bottomLine As Integer
' topLine As Integer
'     }

     ''engraver 加的
Public isPercussion As Boolean  '' 是否是打擊樂
Public isJianpu As Boolean      '' 是否是簡譜
Public meteA As Integer         '記錄現在小節的拍號
Public meteB As Integer         '記錄現在小節的拍號




Public Sub init(voicenumber As Integer, voicetotal As Integer)

        Set Me.children = New MusicItemList 'AbsoluteElementList
        Set Me.beams = New BeamElemList
        Set Me.otherchildren = New iArray '[]  '' ties, slurs, triplets
        Me.i = 0
        Me.w = 0
        Me.duplicate = False
        Me.voicenumber = voicenumber  ''number of the voice on a given stave (not staffgroup)
        Me.voicetotal = voicetotal
        Me.bottom = 7
        Me.top = 7
        Dim spY As Dictionary
        Set spY = New Dictionary
        Me.meteA = 4
        Me.meteB = 4
        
        spY("tempoHeightAbove") = 0
        spY("partHeightAbove") = 0
        spY("volumeHeightAbove") = 0
        spY("dynamicHeightAbove") = 0
        spY("endingHeightAbove") = 0
        spY("chordHeightAbove") = 0
        spY("lyricHeightAbove") = 0
        spY("lyricHeightBelow") = 0
        spY("chordHeightBelow") = 0
        spY("volumeHeightBelow") = 0
        spY("dynamicHeightBelow") = 0
        Set Me.specialY = spY
        
End Sub

Public Sub addChild(abselem As AbsoluteElement)
        Dim firstItem As Boolean
        Dim i As Integer
        '' This is always passed an AbsoluteElement
        
        If (abselem.typs = "bar") Then
            firstItem = True
            For i = 0 To Me.children.Count
                If (InStr(1, Me.children(i).typs, "staff-extra") < 0 And Me.children(i).typs <> "tempo") Then
                    firstItem = False
                End If
            Next
            
            If (firstItem = False) Then
                Me.beams.Push abselem '("bar")
                Me.otherchildren.Push abselem '("bar")
            End If
        End If
        Me.children.Push abselem
        Me.setRange abselem
End Sub

Public Sub setLimit(member As String, child)
        '' Sometimes we get an absolute element in here and sometimes we get some type of relative element.
        '' If there is a "specialY" element, then assume it is an absolute element. If that doesn't exist, look for the
        '' same members at the top level, because that's where they are in relative elements.
        Dim specialY As Dictionary
        Set specialY = child.specialY
        If Not (specialY Is Nothing) Then Set specialY = child.specialY
        If (specialY(member) <> 0) Then Exit Sub
        If (Me.specialY(member) = 0) Then
            'line Me.specialY(member) = specialY(member)
        Else
            Dim aa1, aa2
            aa1 = Math.max(Me.specialY(member), specialY(member))
            Set Me.specialY(member) = aa1 ' Math.max(aa1, aa2)
        End If
End Sub

Public Sub adjustRange(child)
        If (child.bottom <> 0) Then
            Me.bottom = Math.min(Me.bottom, child.bottom)
        End If
        If (child.top <> 0) Then Me.top = Math.max(Me.top, child.top)
End Sub

Public Sub setRange(child)
        Call Me.adjustRange(child)
        Call Me.setLimit("tempoHeightAbove", child)
        Call Me.setLimit("partHeightAbove", child)
        Call Me.setLimit("volumeHeightAbove", child)
        Call Me.setLimit("dynamicHeightAbove", child)
        Call Me.setLimit("endingHeightAbove", child)
        Call Me.setLimit("chordHeightAbove", child)
        Call Me.setLimit("lyricHeightAbove", child)
        Call Me.setLimit("lyricHeightBelow", child)
        Call Me.setLimit("chordHeightBelow", child)
        Call Me.setLimit("volumeHeightBelow", child)
        Call Me.setLimit("dynamicHeightBelow", child)
End Sub

Public Sub addOther(child)
        Me.otherchildren.Push child
        Me.setRange child
End Sub

Public Sub addBeam(child As BeamElem)
        Me.beams.Push child
End Sub

Public Sub setWidth(width As Double)
        Me.w = width
End Sub
Public Function insterBar(barId As Integer, barCalNumber As Integer) As MusicItem
    
    Dim barEle As New MusicItem
    barEle.typs = Cg.bar
    barEle.w = amt.wBar * G.fontsize
    barEle.barNumber = barId + barCalNumber
    Me.children.Push barEle
    Set insterBar = barEle
End Function

Public Function insterMete(mete As Integer, mete2 As Integer) As MusicItem

    '還要插入一個 mete
    Dim meteObj As New MusicItem
    meteObj.typs = Cg.meter
    meteObj.mete = mete
    meteObj.mete2 = mete2
    meteObj.w = amt.wMete * G.fontsize
    Me.children.Push meteObj

    Set insterMete = meteObj
End Function

Attribute VB_Name = "VoiceElementList"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
'MIT License
'
'Copyright (c) 2019-2021 Petr Katerinak
'
'Permission is hereby granted, free of charge, to any person obtaining a copy
'of this software and associated documentation files (the "Software"), to deal
'in the Software without restriction, including without limitation the rights
'to use, copy, modify, merge, publish, distribute, sublicense, and/or sell
'copies of the Software, and to permit persons to whom the Software is
'furnished to do so, subject to the following conditions:
'
'The above copyright notice and this permission notice shall be included in all
'copies or substantial portions of the Software.
'
'THE SOFTWARE IS PROVIDED "AS IS", WITHOUT WARRANTY OF ANY KIND, EXPRESS OR
'IMPLIED, INCLUDING BUT NOT LIMITED TO THE WARRANTIES OF MERCHANTABILITY,
'FITNESS FOR A PARTICULAR PURPOSE AND NONINFRINGEMENT. IN NO EVENT SHALL THE
'AUTHORS OR COPYRIGHT HOLDERS BE LIABLE FOR ANY CLAIM, DAMAGES OR OTHER
'LIABILITY, WHETHER IN AN ACTION OF CONTRACT, TORT OR OTHERWISE, ARISING FROM,
'OUT OF OR IN CONNECTION WITH THE SOFTWARE OR THE USE OR OTHER DEALINGS IN THE
'SOFTWARE.
'
' Version of iArray: 1.0
''修正 元素從 0 開始

Private mainArray As New Collection
Private i As Long ' Counter

' #####################
' #    CONSTRUCTOR    #
' #####################
'Private Sub Class_Initialize()
'  Set mainArray = New Collection
'End Sub

' #####################
' #  Getter / Setter  #
' #####################
'Attribute Element.VB_UserMemId = 0 saved in both procedures

'@DefaultMember
Public Property Get element(ByVal index As Long) As VoiceElement
Attribute element.VB_UserMemId = 0
    If index + 1 < 1 Or index + 1 > mainArray.Count Then
        Set element = Nothing
        Exit Property
    End If
    If IsObject(mainArray(index + 1)) = True Then
        Set element = mainArray(index + 1)
    Else
        element = mainArray(index + 1)
    End If

 
End Property

'@DefaultMember
Public Property Let element(ByVal index As Long, ByVal val As VoiceElement)
Attribute element.VB_UserMemId = 0
  If index = 0 And mainArray.Count = 0 Then
    Me.Push val
    Exit Property
  End If
  If index + 1 > mainArray.Count Then
    Dim eMsg As String
    eMsg = IIf(mainArray.Count > 0, _
               "Index (" & index + 1 & ") out of iArray bounds (1-" & mainArray.Count & ")", _
               "iArray doesn't have any indexes")
    err.Raise Number:=9, Description:=eMsg
    Exit Property
  End If
  mainArray.Add val, after:=index + 1
  mainArray.Remove index + 1
End Property

' #############################
' # COMMON COLLECTION METHODS #
' #############################
Public Function Count() As Long
  Count = mainArray.Count
End Function
Public Sub Add(ByVal val As VoiceElement, Optional ByVal bef As Variant = Empty, Optional ByVal aft As Variant = Empty)
  If IsEmpty(bef) And IsEmpty(aft) Then
    mainArray.Add val
  ElseIf IsEmpty(bef) Then
    mainArray.Add val, , , aft
  ElseIf IsEmpty(aft) Then
    mainArray.Add val, , bef
  Else
    mainArray.Add val, , bef, aft
  End If
End Sub
Public Sub Remove(index As Long)
  mainArray.Remove index + 1
End Sub

' ####################
' #  PUBLIC METHODS  #
' ####################

'AddAfter
' Adds element after given index.
' {1,2,3} -> index >= 3 -> Push val
' {1,2,3} -> index < 1 -> Unshift val
' {} -> index = any -> Push val
' @param Long index | Index after which will be added an element
' @param Variant val | One element (String, number, ...) to add into iArray
' @return Long | Count of elements inside iArray
Public Function AddAfter(ByVal index As Long, ByVal val As VoiceElement) As Long
  If Me.Count < 1 Or index + 1 >= Me.Count Then
    Me.Push val
  ElseIf index + 1 < 1 Then
    Me.Unshift val
  Else
    Me.Add val, aft:=index + 1
  End If
  AddAfter = Me.Count
End Function

'AddArrayAfter
' Adds elements after given index.
' {1,2,3} -> index >= 3 -> PushArray val
' {1,2,3} -> index < 1 -> UnshiftArray val
' {} -> index = any -> PushArray val
' @param Long index | Index after which will be added an element
' @param Variant val | Array() or iArray of elements to add into iArray
' @return Long | Count of elements inside iArray
Public Function AddArrayAfter(ByVal index As Long, ByVal val As Variant) As Long
  If Me.Count < 1 Or index + 1 >= Me.Count Then
    Me.PushArray val
  ElseIf index + 1 < 1 Then
    Me.UnshiftArray val
  Else
    If TypeOf val Is VoiceElementList Then
      For i = 0 To val.Count - 1
        Me.Add val(i), aft:=index + 1
        Inc index
      Next i
    Else
      For i = LBound(val) To UBound(val)
        Me.Add val(i), aft:=index + 1
        Inc index
      Next i
    End If
  End If
  AddArrayAfter = Me.Count
End Function

'AddArrayBefore
' Adds elements before given index.
' {1,2,3} -> index > 3 -> PushArray val
' {1,2,3} -> index <= 1 -> UnshiftArray val
' {} -> index = any -> PushArray val
' @param Long index | Index after which will be added an element
' @param Variant val | Array() or iArray of elements to add into iArray
' @return Long | Count of elements inside iArray
Public Function AddArrayBefore(ByVal index As Long, ByVal val As Variant) As Long
  If Me.Count < 1 Or index + 1 > Me.Count Then
    Me.PushArray val
  ElseIf index <= 0 Then
    Me.UnshiftArray val
  Else
    If TypeOf val Is VoiceElementList Then
      For i = val.Count - 1 To 0 Step -1
        Me.Add val(i), bef:=index + 1
      Next i
    Else
      For i = UBound(val) To LBound(val) Step -1
        Me.Add val(i), bef:=index + 1
      Next i
    End If
  End If
  AddArrayBefore = Me.Count
End Function

'AddBefore
' Adds element before given index.
' {1,2,3} -> index > 3 -> Push val
' {1,2,3} -> index <= 1 -> Unshift val
' {} -> index = any -> Push val
' @param Long index | Index before which will be added an element
' @param Variant val | One element (String, number, ...) to add into iArray
' @return Long | Count of elements inside iArray
Public Function AddBefore(ByVal index As Long, ByVal val As VoiceElement) As Long
  If Me.Count < 1 Or index + 1 > Me.Count Then
    Me.Push val
  ElseIf index + 1 <= 1 Then
    Me.Unshift val
  Else
    Me.Add val, bef:=index + 1
  End If
  AddBefore = Me.Count
End Function

'Avg
' Calculates the average of the numeric mainArray.
' @return Variant | Average value / "NaN" if iArray contains non-numeric value(s)
Public Function Avg() As Variant
  If Not Me.ContainsOnlyNumeric Then Avg = "NaN": Exit Function
  Avg = Me.sum / Me.Count
End Function

'Clear
' Empties iArray
Public Function Clear() As Boolean
  For i = mainArray.Count - 1 To 0 Step -1
    mainArray.Remove i + 1
  Next i
  Clear = IIf(mainArray.Count = 0, True, False)
End Function

'Clone
' Makes a hard copy of the mainArray
' @return mainArray | Return exact copy of itself
Public Function clone() As VoiceElementList
  Set clone = New VoiceElementList
  For i = 0 To Me.Count - 1
    clone.Push Me(i)
  Next i
End Function

'Contains
' Checks if given value is used inside mainArray.
' @param Variant val | One element (String, number, ...) to by checked if it exists in iArray
' $return Boolean | True = exists, False = doesn't exists
Public Function Contains(ByVal val As VoiceElement) As Boolean
  Contains = False
  Dim el As Variant
  For Each el In mainArray
    If IsObject(val) = True Or VarType(val) And 8192 Then
        If (VarType(el) And 8192) And (VarType(val) And 8192) Then
            If ArrayDifference(el, val) Then
                Contains = True: Exit Function
            End If
        ElseIf IsObject(el) = True And IsObject(val) = True Then
            If el Is val Then
                Contains = True: Exit Function
            End If
        End If
    Else
        If IsObject(el) = False And (VarType(el) And 8192) <> 8192 Then
            If el = val Then
            Contains = True: Exit Function
            End If
        End If
    End If
  Next el
End Function

'ContainsAll
' Checks if all given values are used inside mainArray.
' @param Variant val | values to by checked if it exists in iArray
' $return Boolean | True = all exists, False = one ore more values doesn't exists
Public Function ContainsAll(ByVal val As VoiceElementList) As Boolean
  ContainsAll = False
  Dim foundOccurrences As Integer: foundOccurrences = 0
  Dim values As New VoiceElementList
  If Not TypeOf val Is VoiceElementList Then
    If IsArray(val) Then
      values.PushArray (val)
    Else
      values.Push (val)
    End If
  Else
    Set values = val
  End If
  For i = 0 To values.Count - 1
    If Me.Contains(values(i)) Then Inc foundOccurrences
  Next i
  If foundOccurrences = values.Count Then ContainsAll = True
End Function

'CountOccurrences
' Checks how many times is given value used inside mainArray.
' @param Variant val | One element (String, number, ...) to by checked
' @return Long | Count of matched occurrences
Public Function CountOccurrences(val As Variant) As Long
  CountOccurrences = 0
  Dim el As Variant
  For Each el In mainArray
  
    If IsObject(val) = True Or VarType(val) And 8192 Then
        If VarType(el) And 8192 And VarType(val) And 8192 Then
            If ArrayDifference(el, val) Then
                Inc CountOccurrences
                Exit Function
            End If
        ElseIf IsObject(el) = True And IsObject(val) = True Then
            If el Is val Then
                Inc CountOccurrences
                Exit Function
            End If
        End If
    Else
        If IsObject(el) = False And Not (VarType(el) And 8192) Then
            If el = val Then
                Inc CountOccurrences
                Exit Function
            End If
        End If
    End If
  
     'If el = val Then Inc CountOccurrences
  Next el
End Function

'Dequeue
' Removes an element from the begining of the mainArray.
' @return Variant | Removed element or Empty, if iArray is empty
'刪除開頭一個元素。
Public Function Dequeue() As VoiceElement
  Dequeue = Empty
  If mainArray.Count > 0 Then
    If VarType(Me(0)) = vbString Then
        Dequeue = Me(0)
    ElseIf TypeOf Me(0) Is VoiceElementList Then
        Set Dequeue = Me(0)
    ElseIf VarType(Me(0)) = vbArray Then
        Set Dequeue = Me(0)
    ElseIf VarType(Me(0)) = vbObject Then
        Set Dequeue = Me(0)
    Else
        Dequeue = Me(0)
    End If
    
    mainArray.Remove 1
  End If
End Function

'Difference
' Checks for number of differences between two arrays, what was added/deleted or combination.
' @param iArray oldArray | Old iArray to be compared with current iArray
' @param String retType | �dd= deleted from old iArray, �aa= added in current iArray, �cc= combination of both (default)
' @return iArray | iArray with differences found
Public Function Difference(ByRef oldArray As VoiceElementList, Optional ByVal retType As String = "c") As VoiceElementList
  Set Difference = New VoiceElementList
  Select Case LCase(retType)
    Case "d"
      For i = 0 To oldArray.Count - 1
        If Me.Contains(oldArray(i)) = False Then Difference.Push oldArray(i)
      Next i
    Case "a"
      For i = 0 To Count - 1
        If oldArray.Contains(Me(i)) = False Then Difference.Push Me(i)
      Next i
    Case "c"
      For i = 0 To oldArray.Count - 1
        If Me.Contains(oldArray(i)) = False Then Difference.Push oldArray(i)
      Next i
      For i = 0 To Count - 1
        If oldArray.Contains(Me(i)) = False Then Difference.Push Me(i)
      Next i
    Case Else
      err.Raise Number:=5, Description:="Unknown Difference return type attribute:" & vbCrLf & _
                                        "Allowed are 'A'dded/'D'eleted/'C'ombination of both"
  End Select
End Function

'DropLeft
' Remove n elements from the beginning of the mainArray. If n > count of iArray elements, all elements are removed.
' @param Long n | Number of elements to be removed
' @return iArray | Array of the removed elements
Public Function DropLeft(ByRef N As Long) As VoiceElementList
  Set DropLeft = New VoiceElementList
  If N > Me.Count Then N = Me.Count
  For i = 0 To N - 1
    DropLeft.Push Me(i)
  Next i
  For i = N - 1 To 0 Step -1
    Me.Remove (i)
  Next i
End Function

'DropRight
' Remove n elements from the end of the mainArray. If n > count of iArray elements, all elements are removed.
' @param Long n | Number of elements to be removed
' @return iArray | Array of the removed elements
Public Function DropRight(ByRef N As Long) As VoiceElementList
  Set DropRight = New VoiceElementList
  If N > Me.Count Then N = Me.Count
  For i = Me.Count - N To Me.Count - 1
    DropRight.Push Me(i)
  Next i
  For i = Me.Count - 1 To Me.Count - N Step -1
    Me.Remove (i)
  Next i
End Function

'Enqueue
' Adds an element at the end of the mainArray.
' @param Variant val | One element (String, number, ...) to add into iArray
' @return Long | Count of elements inside iArray
Public Function Enqueue(ByVal val As Variant) As Long
  Enqueue = Push(val)
End Function

'EnqueueArray
' Adds elements at the end of the iArray
' @param Variant val | Array() or iArray of elements to add into iArray
' @return Long | Count of elements inside array
Public Function EnqueueArray(ByVal val As Variant) As Long
  EnqueueArray = PushArray(val)
End Function

'First
' Returns value of the first element of the mainArray.
' @return Variant | Value of the first element or Empty if iArray is Empty
Public Function First() As VoiceElement
  Set First = IIf(Me.Count > 0, Me(0), Empty)
End Function

'Head
' Returns all elements of iArray, except last one.
' @return iArray | Copy of original array, without last element
Public Function head() As VoiceElementList
  Set head = Me.clone
  head.Pop
End Function

'Intersect
' Search for element that exists in both iArrays.
' @param iArray intArray | iArray to be intersected with current iArray
' @return iArray | Intersected values
Public Function Intersect(ByRef intersectedArr As VoiceElementList) As VoiceElementList
  Set Intersect = New VoiceElementList
  Dim el As Variant
  For Each el In mainArray
    If intersectedArr.Contains(el) Then
      If Not Intersect.Contains(el) Then Intersect.Push (el)
    End If
  Next el
End Function

'ContainsOnlyNumeric
' Verify that all elements are numbers or convertable to numbers
' $return Boolean | True = contains only numeric values, False = contains inconvertible values
Public Function ContainsOnlyNumeric() As Boolean
  ContainsOnlyNumeric = True
  Dim el As Variant
  For Each el In mainArray
    If Not IsNumeric(el) Then ContainsOnlyNumeric = False: Exit Function
  Next el
End Function

'Join
' Joins two iArrays.
' @param iArray jArray | iArray to be joined with current iArray
' @return iArray | Joined iArray
Public Function Join(ByRef joinArr As VoiceElementList) As VoiceElementList
  Set Join = New VoiceElementList
  Join.PushArray Me
  Join.PushArray joinArr
End Function

'Last
' Returns value of the last element of the mainArray.
' @return Variant | Value of the last element or Empty if iArray is Empty
Public Function Last() As VoiceElement
  Set Last = IIf(Me.Count > 0, Me(Me.Count - 1), Empty)
End Function

'OccurrenceIndexes
' Returns all indexes of a value in mainArray.
' @return iArray | iArray containing indexes of occurrence
Public Function OccurenceIndexes(val As Variant) As VoiceElementList
  Set OccurenceIndexes = New VoiceElementList
  For i = 0 To Me.Count - 1
    If Me(i) = val Then
        OccurenceIndexes.Push (i)
    End If
  Next i
End Function

'Pop
' Removes an element from the end of the mainArray.
' @return Variant | Removed element or Empty, if iArray is empty
Public Function Pop() As VoiceElement
  If mainArray.Count > 0 Then
    If VarType(Me(mainArray.Count - 1)) = vbObject Then
       Set Pop = Me(mainArray.Count - 1)
    Else
        Pop = Me(mainArray.Count - 1)
    End If
    mainArray.Remove mainArray.Count
  End If
End Function
  
  

'Push
' Adds an element at the end of the mainArray.
' @param Variant val | One element (String, number, ...) to add into iArray
' @return Long | Count of elements inside iArray
Public Function Push(ByVal val As VoiceElement) As Long
  mainArray.Add val
  Push = mainArray.Count
End Function

'PushArray
' Adds elements at the end of the mainArray.
' @param Variant val | Array() or iArray of elements to add into iArray
' @return Long | Count of elements inside array
Public Function PushArray(ByVal val As Variant) As Long
  If TypeOf val Is VoiceElementList Then
    For i = 0 To val.Count - 1
      Me.Push val(i)
    Next i
  Else
    For i = LBound(val) To UBound(val)
      Me.Push val(i)
    Next i
  End If
  PushArray = Me.Count
End Function

'RemoveDuplicates
' Keeps only the first occurrence of the value. Affects original array
' @return Long | Count of the removed elements
Public Function RemoveDuplicates() As Long
  RemoveDuplicates = 0
  For i = Me.Count - 1 To 0 Step -1
    If Me.CountOccurrences(Me(i)) > 1 Then
      Me.Remove i
      Inc RemoveDuplicates
    End If
  Next i
End Function

'Reverse
' Reverses the content of the iArray
' @return iArray | Reversed iArray
Public Function Reverse() As VoiceElementList
  Set Reverse = New VoiceElementList
  For i = 0 To Me.Count - 1
    Reverse.Unshift Me(i)
  Next i
End Function

'Shift
' Removes an element from the begining of the mainArray.
' @return Variant | Removed element or Empty, if iArray is empty
'轉移
' 從 iArray 的開頭刪除一個元素。
' @返回第一個元素 | 如果 iArray 為空，則刪除元素或為空
Public Function shift() As VoiceElement
  shift = Empty
  If mainArray.Count > 0 Then
    If VarType(Me(0)) = vbString Then
        shift = Me(0)
    ElseIf TypeOf Me(0) Is VoiceElementList Then
        Set shift = Me(0)
    ElseIf VarType(Me(0)) = vbArray Then
        Set shift = Me(0)
    ElseIf VarType(Me(0)) = vbObject Then
        Set shift = Me(0)
    Else
        shift = Me(0)
    End If
    
    mainArray.Remove 1
  End If
End Function

'Shuffle
' Randomly mixes content of the iArray
' @return iArray | Shuffled iArray
' 隨機播放
' 隨機混合 iArray 的內容
'@return iArray | 打亂iArray
Public Function Shuffle() As VoiceElementList
  Set Shuffle = New VoiceElementList
  Dim keys As New VoiceElementList
  For i = 0 To Me.Count - 1
    keys.Push (i)
  Next i
  Dim rndNo As Long
  Do While keys.Count > 0
    rndNo = randomFromTo(0, keys.Count - 1)
    Shuffle.Push Me(keys(rndNo))
    keys.Remove (rndNo)
  Loop
End Function

'Sum
' Calculates the sum of the numeric mainArray.
' @return Variant | Sum value / "NaN" if iArray contains non-numeric value(s)
Public Function sum() As Variant
  If Not Me.ContainsOnlyNumeric Then sum = "NaN": Exit Function
  sum = 0
  Dim el As Variant
  For Each el In mainArray
    sum = sum + el
  Next el
End Function

'Tail
' Returns all elements of iArray, except first one.
' @return iArray | Copy of original array, without first element
'返回陣列中除了第一個元素的剩余元素陣列
Public Function Tail() As VoiceElementList
  Set Tail = Me.clone
  Tail.Dequeue
End Function

Public Function ToList()
  If Me.Count = 0 Then ToList = Null: Exit Function
  Dim tarr()
  ReDim tarr(Me.Count - 1)
  For i = 0 To Me.Count - 1
    If VarType(Me(i)) = vbString Then
        tarr(i) = Me(i)
    ElseIf TypeOf Me(i) Is VoiceElementList Then
        Set tarr(i) = Me(i)
    ElseIf VarType(Me(i)) = vbObject Then
        Set tarr(i) = Me(i)
    Else
        tarr(i) = Me(i)
    End If
  Next i
  ToList = tarr
End Function

'ToString
' Creates string representation of the mainArray.
' @param String delimiter | Optional character to separate the iArray's elements (default = " ")
' @return String | Formated representation of tha iArray
Public Function ToString(Optional ByVal delimiter As String = " ") As String
  If Me.Count = 0 Then ToString = "{}": Exit Function
  ToString = vbNullString
  For i = 0 To Me.Count - 1
    If i = 0 Then ToString = ToString + "{"
    If i > 0 Then ToString = ToString + delimiter
    If VarType(Me(i)) = vbString Then
        ToString = ToString + Chr$(34)
        ToString = ToString + CStr(Me(i))
        ToString = ToString + Chr$(34)
    ElseIf TypeOf Me(i) Is VoiceElementList Then
        ToString = ToString + Me(i).ToString(delimiter)
    ElseIf (VarType(Me(i)) And vbArray) = vbArray Then
        ToString = ToString + "[Array]"
    ElseIf VarType(Me(i)) = vbObject Then
        ToString = ToString + "[Object]"
    Else
        ToString = ToString + CStr(Me(i))
    End If
    
    If i = mainArray.Count - 1 Then ToString = ToString + "}"
  Next i
End Function

'Union
' Combines both iArrays and removes duplicities
' @param iArray uArray | iArray to be unioned with current iArray
' @return iArray | Combined values without duplicities
Public Function Union(ByRef uArr As VoiceElementList) As VoiceElementList
  Set Union = Me.clone
  Union.PushArray uArr
  Union.RemoveDuplicates
End Function

'Unique
' Returns copy of iArray without duplicated values. Original array is not affected
' @return iArray | iArray with unique values
Public Function Unique() As VoiceElementList
  Set Unique = New VoiceElementList
  Dim el As Variant
  For Each el In mainArray
    If Not Unique.Contains(el) Then Unique.Push (el)
  Next el
End Function

'Unshift
' Add an element at the begining of the mainArray.
' @param Variant val | One element (String, number, ...) to add into iArray
' @return Long | Count of elements inside iArray
Public Function Unshift(ByVal val As Variant) As Long
  If mainArray.Count = 0 Then
    Unshift = Push(val)
  Else
    mainArray.Add val, before:=1
    Unshift = mainArray.Count
  End If
End Function

'UnshiftArray
' Add elements at the begining of the mainArray.
' @param Variant val | Array() or iArray of elements to add into iArray
' @return Long | Count of elements inside iArray
Public Function UnshiftArray(ByVal val As Variant) As Long
  If TypeOf val Is VoiceElementList Then
    For i = val.Count - 1 To 0 Step -1
      Unshift val(i)
    Next i
  Else
    For i = UBound(val) To LBound(val) Step -1
      Unshift val(i)
    Next i
  End If
  UnshiftArray = mainArray.Count
End Function


' #####################
' # PRIVATE FUNCTIONS #
' #####################
Sub Inc(ByRef i)
   i = i + 1
End Sub

'Private Function rangeToArray(ByVal rng As Range) As Variant
'  rangeToArray = rng.Value
'End Function

Private Function randomFromTo(ByVal from As Long, ByVal upTo As Long) As Long
  Randomize
  randomFromTo = Int(from + Rnd() * (upTo - from + 1))
End Function

'比對 兩個陣列是否一樣
Private Function ArrayDifference(arr1 As Variant, arr2 As Variant) As Boolean

    Dim i As Integer
    If UBound(arr1) = UBound(arr2) Then
        For i = 0 To UBound(arr1)
            If arr1(i) = arr2(i) Then
                ArrayDifference = True
            Else
                ArrayDifference = False
                Exit Function
            End If
        Next
    Else
        ArrayDifference = False
    End If

End Function

'@Description("changes the contents of the array by removing or replacing existing elements and/or adding new elements in place.")
Public Function Splice( _
        ByVal StartIndex As Long, _
        ParamArray Args() As Variant _
    ) As Variant()
    'Dim LocalItems() As Variant
    Dim ActualStart As Long
    Dim ActualDeleteCount As Long
    Dim ArgsCount As Long
    Dim LocalLength As Long
    Dim LocalArgs() As Variant
    Dim result() As Variant
    Dim i As Long
    Dim TempArray() As Variant
    Dim ItemCount As Long
    Dim TempItems() As Variant
    
    LocalArgs = Args
    'LocalItems = mainArray
    LocalLength = Me.Count
    If StartIndex < LocalLength Then
        ActualStart = StartIndex
    Else
        ActualStart = min(StartIndex, LocalLength)
    End If
    
    ArgsCount = UBound(LocalArgs) + 1
    If ArgsCount = 0 Then
        ' only a start index has been supplied
        ' we're gonna delete everything
        ' 僅提供了起始索引
         '我們要刪除所有內容
        ItemCount = 0
        ActualDeleteCount = LocalLength - ActualStart
    Else
        ' first arg in args is delete count, second onwards are insertion items
        ' args 中的第一個參數是刪除計數，第二個之後是插入項
        ItemCount = ArgsCount - 1
        'deleteCount is first element in args.
        'deleteCount 是 args 中的第一個元素。
        ActualDeleteCount = min(max(Args(LBound(Args)), 0), LocalLength - ActualStart)
    End If
    

    ' get items to be deleted for return val
    ' 取得和刪除
    If ActualDeleteCount > 0 Then
        ReDim result(0 To ActualDeleteCount - 1)
        i = 0
        Do While i < ActualDeleteCount
            If IsObject(Me(ActualStart)) Then
                Set result(i) = Me(ActualStart)
                Me.Remove ActualStart
            Else
                result(i) = Me(ActualStart)
                Me.Remove ActualStart
            End If
            Inc i
        Loop
    Else
        ' return empty array if nothing to be deleted
        ReDim result(0)
    End If
    
    '取得要插入的陣列資料
    If ItemCount > 0 Then
        ReDim TempItems(0 To ItemCount - 1)
        For i = 0 To ItemCount - 1
            If IsObject(LocalArgs(i + 1)) Then
                Set TempItems(i) = LocalArgs(i + 1)
            Else
                TempItems(i) = LocalArgs(i + 1)
            End If
        Next
    Me.AddArrayBefore ActualStart, TempItems
    End If
    
    
    Splice = result
End Function

Attribute VB_Name = "aBarConfig"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public barId As Integer     '實既小節數
Public barNumber As Integer '小節數修改號碼
Public mete As Integer
Public mete2 As Integer
Public keyMain As String
Public barLineQuantity As Integer '一行的小節數量
Public barlinebreak As Boolean  'true 小節後換行
Public barpagebreak As Boolean

Attribute VB_Name = "aDecorationItem"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public Name As String
Public func
Public glyph As String
Public h
Public hd
Public wl
Public wr
Public str As String
Public dd_st As aDecorationItem
Public dd_en As aDecorationItem

Public Sub ConvertVarName(key, value)
        Select Case key    ' Evaluate Number.
            ''一般
            Case "name":    Me.Name = value
            Case "func":    Me.func = value
            Case "glyph":   Me.glyph = value
            Case "h":       Me.h = value
            Case "hd":      Me.hd = value
            Case "wl":      Me.wl = value
            Case "wr":      Me.wr = value
            Case "str":     Me.str = value
            Case "dd_st": Set Me.dd_st = value
            Case "dd_st": Set Me.dd_st = value
            Case Else
                Debug.Print "沒有變數 " & key & "名"
        End Select
End Sub

Attribute VB_Name = "aFontItem"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit


Public box As Boolean
Public pad
Public Name As String
Public weight As String
Public size
Public used As Boolean
Public fid
Public swfac
Public fname As String
Public style As String
Public src As String
Public Sub ConvertVarName(key, value)
        Select Case key    ' Evaluate Number.
            ''一般
            Case "box":    Me.box = value
            Case "pad":    Me.pad = value
            Case "name":   Me.Name = value
            Case "weight": Me.weight = value
            Case "size":   Me.size = value
            Case "used":   Me.used = value
            Case "fid":    Me.fid = value
            Case "swfac":  Me.swfac = value
            Case "fname":  Me.fname = value
            Case "style":  Me.style = value
            Case "src":    Me.src = value
            Case Else
                Debug.Print "沒有變數 " & key & "名"
        End Select
End Sub

Attribute VB_Name = "aGchordItem"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False

Public typs As String
Public text As String
Public x
Public pos
Public otext As String
Public iStart
Public iend
Public font As aFontItem

Public Sub ConvertVarName(key, value)
        Select Case key    ' Evaluate Number.
            ''一般
            Case "type":    Me.typs = value
            Case "text":    Me.text = value
            Case "name":    Me.Name = value
            Case "x":       Me.x = value
            Case "pos":     Me.pos = value
            Case "used":    Me.used = value
            Case "otext":   Me.otext = value
            Case "istart":  Me.iStart = value
            Case "iend":  Me.iend = value
            Case "font":  Set Me.font = value
            Case Else
                Debug.Print "沒有變數 " & key & "名"
        End Select
End Sub

Attribute VB_Name = "aKMap"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public typs As String
Public font As String
Public wh As Double
Public x As Double
Public y As Double
Public text As String

Attribute VB_Name = "aLyricsItem"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False

Public t As String
Public font As aFontItem
Public iStart
Public iend
Public ln
Public shift


Public Sub ConvertVarName(key, value)
        Select Case key    ' Evaluate Number.
            ''一般
            Case "t":        Me.t = value
            Case "font":  Set Me.font = value
            Case "istart":   Me.iStart = value
            Case "iend":     Me.iend = value
            Case "ln":       Me.ln = value
            Case "shift":    Me.shift = value
            Case Else
                Debug.Print "沒有變數 " & key & "名"
        End Select
End Sub

Attribute VB_Name = "aNoteItem"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public pit
Public shhd
Public shac
Public dur
Public midi
Public jn
Public jo
Public opit
Public acc
Public a_dd As iArray

Public Sub ConvertVarName(key, value)
        Select Case key    ' Evaluate Number.
            ''一般
            Case "pit":   Me.pit = value
            Case "shhd":  Me.shhd = value
            Case "shac":  Me.shac = value
            Case "dur":   Me.dur = value
            Case "midi":  Me.midi = value
            Case "jn":    Me.jn = value
            Case "jo":    Me.jo = value
            Case "acc":   Me.acc = value
            Case "a_dd":  Me.a_dd = value
            Case Else
                Debug.Print "沒有變數 " & key & "名"
        End Select
End Sub

Attribute VB_Name = "aRestItem"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public typs As String
Public text As String
Public barNumber As Integer

Attribute VB_Name = "constructTuneElements"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False

Option Explicit

Public line As Integer
Public startX As Double
Public w As Double
Public height As Double
Public gTextSize As getTextSize
Public groupVoices123 As New VoiceElementList    '這是每行的 voices
Public staffInfos As vStaffInfoList
Public brace As BraceElemList
Public bracket As BraceElemList
Private sa_(100) As size
Private saIs As New Dictionary
Private igroup As Integer
Private ich As Integer
Private mBuf As DataBuffer
Private barConfig() As aBarConfig
    'ReDim barConfig(200)



Function translate2Staffs(mBuf As DataBuffer) As TuneLineList
 
    Dim abcLines As TuneLineList
    Dim rr As runTime
    Set rr = rTime
    
    rr ("tidyDataToRow")
    Set groupVoices123 = tidyDataToRow(mBuf)
    rr ("tidyDataToRow")
    Dim i As Integer

    rr ("create2TuneLines")
    Set abcLines = create2TuneLines(groupVoices123)
    rr ("create2TuneLines")
    'layoutxy abcLines, 30
    
    
    Set translate2Staffs = abcLines
End Function
'' call when spacingduration has been updated
Sub updateNextX(x As Double, spacing As Double, voice As VoiceElement)
    voice.nextX = x + (spacing * Math.Sqrt(voice.spacingduration / 1000 * 8))
End Sub
Function layoutxy(abcLines As TuneLineList, spaceing As Double)
    Dim aLine As TuneLine
    Dim vo As VoiceElement
    Dim mus As MusicItem
    Dim i As Integer
    Dim j As Integer
    Dim num As Integer
    Dim currSpace As Double
    Dim spaceUnit As Double
    Dim parentWidth As Double
    Dim calW As Double
    For i = 0 To abcLines.Count - 1
        Set aLine = abcLines(i)
        For j = 0 To aLine.staffGroup.voices.Count - 1
            Set vo = aLine.staffGroup.voices(j)
            currSpace = spaceing
            For num = 0 To 7
                spaceUnit = layoutOneItem(vo, currSpace)
                '計算寬度
                parentWidth = 210 - G.RightSpace + G.LeftSpace
                
                If (vo.w >= parentWidth) Then
                    calW = vo.w - parentWidth
                    currSpace = calW / spaceUnit
                Else
                    Exit For
                End If
            Next
            
           
        Next
        
    Next

End Function
Function layoutOneItem(vele As VoiceElement, spacing As Double) As Double
    Dim k As Integer
    Dim mus As MusicItem
    Dim spaceCurr As Double
    Dim spaceUnit As Double
    spaceUnit = 0
    vele.nextX = 0
    For k = 0 To vele.children.Count - 1
        Set mus = vele.children(k)
                    
        If (mus Is Nothing) Then
            Exit For
        End If
        
        Select Case mus.typs
           Case Cg.bar:
                mus.x = vele.nextX
                mus.w = amt.wBar * G.fontName
           Case Cg.meter:
                mus.x = vele.nextX
                mus.w = amt.wMete * G.fontName
           Case Cg.rest, Cg.note:
                mus.x = vele.nextX
                mus.w = amt.wNote * G.fontName
                calExtraw mus   '計算前綴元素
           Case Else
                mus.x = vele.nextX
                mus.w = amt.wOther * G.fontName
        End Select
        vele.w = vele.nextX
        If (mus.duration > 0) Then
            spaceCurr = (spacing * Math.Sqrt(mus.duration / 1000 * 8))
        Else
            spaceCurr = (spacing * Math.Sqrt(1 / 1000 * 8))
        End If
            vele.nextX = mus.x + mus.w + spaceCurr
            vele.minX = mus.x + mus.w + 0.1
            vele.nextX = Math.max(vele.nextX, vele.minX)
            spaceUnit = spaceUnit + spaceCurr
        
    Next
    layoutOneItem = spaceUnit

End Function
Function create2TuneLines(groupVoices As VoiceElementList) As TuneLineList
    On Error Resume Next
    Dim abcLines As TuneLineList
    Dim abcStaffs As StaffList
    Dim tmpTL As TuneLine
    Dim vo As VoiceElement
    Dim sff As Staff
    Dim i As Integer
    Dim N As Integer
    Dim posLine As Integer
    Dim currVoiceNumber As Integer
       
    Set abcLines = New TuneLineList
    
    ''寫入 abcLines.staffs
    For i = 0 To groupVoices.Count - 1
        Set vo = groupVoices(i)
        
        If (vo.voicenumber > currVoiceNumber) Then
            posLine = 0
            currVoiceNumber = vo.voicenumber
        End If
        If (abcLines(posLine) Is Nothing) Then
             abcLines.Push New TuneLine
        End If
        If (abcLines(posLine).Staffs Is Nothing) Then
            Set abcLines(posLine).Staffs = New StaffList
        End If
        
        ''寫入 abcLines.staffs
        Set sff = New Staff
        Set sff.voices = vo.children
        abcLines(posLine).Staffs.Push sff

        
        ''寫入 abcLines.StaffGroup
        If (abcLines(posLine).staffGroup Is Nothing) Then
            Set abcLines(posLine).staffGroup = New StaffGroupElement
            Set abcLines(posLine).staffGroup.voices = New VoiceElementList
        End If
        abcLines(posLine).staffGroup.voices.Push vo
        posLine = posLine + 1
        

    Next
    
    posLine = 0

    
    
    Set create2TuneLines = abcLines
End Function
Function tidyDataToRow(mBuf As DataBuffer) As VoiceElementList
'資料整理成小節數 一行一行的array


    Dim tmp_track As Integer
    Dim tmp_track_item As Long

    Dim s1 As MusicItem
    Dim s2 As MusicItem
    
    
     Call mBuf.init
     
    Dim i As Long
    Dim voiceList As New VoiceElementList
    Dim vo As VoiceElement
    Dim trackIndex As Integer
    Dim barId As Integer
    Dim barEle As MusicItem
    Dim isMeasureOne As Boolean  '是否小節第一個
    Dim barCalNumber As Integer
    ReDim barConfig(2000)
    barCalNumber = 0
        For tmp_track = 0 To mBuf.GetTrackSize() - 1

            Call mBuf.init
            
            G.durationIndex = 0
            G.currLine = 0
            G.currMeasure = 0
            
            barId = 0
            Set vo = New VoiceElement
            Call vo.init(tmp_track, mBuf.GetTrackSize() - 1)
            isMeasureOne = True
                        

            
            For tmp_track_item = 0 To mBuf.GetTrackBufferSize(tmp_track) - 1
   
                
                Set s1 = mBuf.GetData(tmp_track, tmp_track_item)
                If (s1 Is Nothing) Then
                    Exit For
                End If
                

                If (G.durationIndex >= (Cg.BLEN / G.mete2) * G.mete) Then
                    '是否以到小節長度
                    Dim barAddNum As Integer
                    barAddNum = G.durationIndex / ((Cg.BLEN / G.mete2) * G.mete)
                    G.currMeasure = G.currMeasure + 1
                    G.durationIndex = 0
                        
                    If s1.typs <> Cg.bar Then vo.insterBar barId, barCalNumber
                    
                    barId = barId + barAddNum
                    If barConfig(barId) Is Nothing Then
                        Set barConfig(barId) = New aBarConfig
                        barConfig(barId).barId = barId
                    ElseIf barConfig(barId).barLineQuantity > 1 Then
                        G.barsperstaff = barConfig(barId).barLineQuantity
                    End If


                    
                    If G.currMeasure >= G.barsperstaff _
                    Or barConfig(barId).barlinebreak _
                    Or barConfig(barId).barpagebreak Then  '看是否以到一行小節個數了
                        isMeasureOne = True
                        G.currMeasure = 0
                        G.currLine = G.currLine + 1
                        voiceList.Push vo
                        
                        If barConfig(barId).barpagebreak Then
                            barCalNumber = -barId
                        End If
                        
                        Set vo = New VoiceElement
                        Call vo.init(tmp_track, mBuf.GetTrackSize() - 1)
                    End If
                End If

                If isMeasureOne = True Then
                    '這是看第一小節 ，是否要加入小節元素
                    If (G.durationIndex = 0 And (s1.typs = Cg.note Or s1.typs = Cg.rest Or s1.typs = Cg.meter)) Then
                        Set s2 = vo.insterBar(barId, barCalNumber)
                        s2.remark = "t" & tmp_track & "_i" & tmp_track_item
                        isMeasureOne = False
                    End If
                End If
                
                If (isMeasureOne = False And tmp_track > 0 And G.durationIndex = 0) Then
                    If Not barConfig(barId) Is Nothing Then
                        '取得第一軌的 第 barId 小節設定
                        If barConfig(barId).mete > 0 Then
                            Set s2 = vo.insterMete(barConfig(barId).mete, barConfig(barId).mete2)
                            s2.remark = "t" & tmp_track & "_i" & tmp_track_item
                            G.mete = barConfig(barId).mete
                            G.mete2 = barConfig(barId).mete2
                            G.durationIndex = G.durationIndex + 0.000005
                        End If
                        If barConfig(barId).barLineQuantity > 0 Then
                            G.barsperstaff = barConfig(barId).barLineQuantity
                        End If
                    End If
                End If

                Select Case s1.typs
                    Case Cg.Config:
                        If (s1.barsperstaff >= 1 And tmp_track = 0) Then
                            G.barsperstaff = s1.barsperstaff
                            If barConfig(barId) Is Nothing Then
                                Set barConfig(barId) = New aBarConfig
                            End If
                            barConfig(barId).barId = barId
                            barConfig(barId).barLineQuantity = s1.barsperstaff
                        End If
                        If (s1.setbarstaffid > 1) Then
                            If barConfig(s1.setbarstaffid) Is Nothing Then
                                Set barConfig(s1.setbarstaffid) = New aBarConfig
                            End If
                            barConfig(s1.setbarstaffid).barId = s1.setbarstaffid
                            barConfig(s1.setbarstaffid).barLineQuantity = s1.setbarstaff
                        End If
                        
                        If (s1.barlinebreak > 1) Then
                            If barConfig(s1.barlinebreak) Is Nothing Then
                                Set barConfig(s1.barlinebreak) = New aBarConfig
                            End If
                            barConfig(s1.barlinebreak).barlinebreak = True
                        End If
                        
                        If (s1.barpagebreak > 1) Then
                            If barConfig(s1.barpagebreak) Is Nothing Then
                                Set barConfig(s1.barpagebreak) = New aBarConfig
                            End If
                            barConfig(s1.barpagebreak).barpagebreak = True
                        End If
                    Case Cg.bar:
                        s1.w = amt.wBar * G.fontsize
                        s1.barNumber = barId + barCalNumber
                        s1.remark = "t" & tmp_track & "_i" & tmp_track_item
                        vo.children.Push s1
                        isMeasureOne = False
                        
                    Case Cg.meter:
                        
                        
                        If (tmp_track = 0) Then
                            G.mete = s1.mete
                            G.mete2 = s1.mete2
                            Set s2 = vo.insterMete(s1.mete, s1.mete2)
                            s2.remark = "t" & tmp_track & "_i" & tmp_track_item
                            Set barConfig(barId) = New aBarConfig
                            barConfig(barId).barId = barId
                            barConfig(barId).mete = s1.mete
                            barConfig(barId).mete2 = s1.mete2
                        End If
                   Case Cg.rest:
                        If s1.rest.typs = "multimeasure" Then
                            '合併小節計算
                            s1.w = amt.wNote * G.fontsize * G.mete
                            Dim tolen As Integer
                            tolen = Cg.BLEN / G.mete2
                            tolen = tolen * G.mete * s1.rest.barNumber
                            s1.duration = (Cg.BLEN / G.mete2) * G.mete * 0.7 '只要畫出 1 小節的寬度 *.7
                            vo.children.Push s1
                            G.durationIndex = G.durationIndex + tolen
                        End If
                   Case Cg.note:
                        s1.w = amt.wNote * G.fontsize
                        If s1.dots > 0 Then
                            s1.w = 2 * amt.wNote * G.fontsize
                        End If
                        calExtraw s1 '計算前綴元素
                        s1.remark = "t" & tmp_track & "_i" & tmp_track_item
                        vo.children.Push s1
                        G.durationIndex = G.durationIndex + s1.duration
                        
                   Case Else
                End Select
                

                
            Next
            If vo.children.Count >= 1 Then '看有無資料
                G.currMeasure = 0
                G.currLine = G.currLine + 1
                
                If (vo.children.Last.typs <> bar) Then
                    '看最後一個是否是 bar
                    '如不是增加
                    vo.insterBar barId, barCalNumber
                End If
                voiceList.Push vo
                
                Set vo = New VoiceElement
                Call vo.init(tmp_track, mBuf.GetTrackSize() - 1)
            End If
            
        Next
    Set tidyDataToRow = voiceList
End Function
'Public Sub read2BarGold(measure As Integer, voice As VoiceElement)
'    '取得第 0 軌的 第 measure 小節設定
'    Dim staffn As Integer
'    Dim m1 As Integer
'    Dim m2 As Integer
'    staffn = barConfig(measure).barLineQuantity
'    m1 = barConfig(measure).mete
'    m2 = barConfig(measure).mete2
'    G.barsperstaff = IIf(staffn > 0, staffn, G.barsperstaff)
'    If (m1 >= 1 And m2 >= 1) Then
'        G.mete = m1
'        G.mete2 = m2
'
'        '還要插入一個 mete
'        voice.insterMete m1, m2
'    End If
'
'End Sub
'
'

Attribute VB_Name = "createABCModule"
'Option Explicit
'
'''    abc_create_clef.js
'
'import AbsoluteElement from './elements/absolute-element'
'import glyphs from './glyphs'
'import RelativeElement from './elements/relative-element'

Public N As New newABCModule
Private glyphs As New GlyphsModule
Function createClef(elem As vClefProperties, tuneNumber As Integer) As AbsoluteElement
    Dim clef As String
    Dim octave As Integer
    Dim abselem As AbsoluteElement
    octave = 0
    elem.el_typs = "clef"
    Set abselem = N.AbsoluteElem(elem, 0, 10, "staff-extra clef", tuneNumber)
    abselem.isClef = True
    Select Case elem.typs
        Case "treble": clef = "clefs.G"
        Case "tenor": clef = "clefs.C"
        Case "alto": clef = "clefs.C"
        Case "bass": clef = "clefs.F"
        Case "treble+8": clef = "clefs.G": octave = 1
        Case "tenor+8": clef = "clefs.C": octave = 1
        Case "bass+8": clef = "clefs.F": octave = 1
        Case "alto+8": clef = "clefs.C": octave = 1
        Case "treble-8": clef = "clefs.G": octave = -1
        Case "tenor-8": clef = "clefs.C": octave = -1
        Case "bass-8": clef = "clefs.F": octave = -1
        Case "alto-8": clef = "clefs.C": octave = -1
        Case "none": Set createClef = Nothing: Exit Function
        Case "perc": clef = "clefs.perc"
        Case "jianpu": clef = "clefs.none"
        Case Else:
        Dim rElem As New RelativeElement
        Dim opt As oRelativeOptions
        opt.typs = "debug"
        abselem.addFixed N.RelativeElem("clef=" + elem.typs, 0, 0, 0, opt)
        
        
    End Select

    '' if (elem.verticalPos) {
    '' pitch = elem.verticalPos
    '' }
    Dim dx As Double
    dx = 5
    If (clef <> "") Then
        Dim height As Double
        Dim ofs As Double
        Dim scale_ As Double, adjustspacing As Double, pitch As Double
        Dim top As Double, bottom As Double
        
        height = glyphs.symbolHeightInPitches(clef)
        ofs = clefOffsets(clef)
        Dim opt2  As New oRelativeOptions
        opt2.top = height + elem.clefPos + ofs
        opt2.bottom = elem.clefPos + ofs
        
        abselem.addRight N.RelativeElem(clef, dx, glyphs.getSymbolWidth(clef), elem.clefPos, opt2)
        
        If (octave <> 0) Then
            scale_ = 2 / 3
            adjustspacing = (glyphs.getSymbolWidth(clef) - glyphs.getSymbolWidth("8") * scale_) / 2
            pitch = IIf(octave > 0, abselem.top + 3, abselem.bottom - 1)
            top = IIf(octave > 0, abselem.top + 3, abselem.bottom - 3)
            bottom = top - 2
            If (elem.typs = "bass-8") Then
                '' The placement for bass octave is a little different. It should hug the clef.
                pitch = 3
                adjustspacing = 0
            End If
            Dim opt3 As oRelativeOptions
            opt3.scalex = scale_
            opt3.scaley = scale_
            opt3.top = top
            opt3.bottom = bottom
            abselem.addRight N.RelativeElem("8", dx + adjustspacing, glyphs.getSymbolWidth("8") * scale_, pitch, opt3)
            ''abselem.top += 2
        End If
    End If
    Set createClef = abselem
End Function

Public Function clefOffsets(clef As String) As Integer

    Select Case clef
        Case "clefs.G": clefOffsets = -5: Exit Function
        Case "clefs.C": clefOffsets = -4: Exit Function
        Case "clefs.F": clefOffsets = -4: Exit Function
        Case "clefs.perc": clefOffsets = -2: Exit Function
        Case Else: clefOffsets = 0: Exit Function
    End Select
End Function



Function createKeySignature(elem As vKeySignature, tuneNumber As Integer) As AbsoluteElement
    Dim abselem As AbsoluteElement
    Dim dx As Double, i As Long
    Dim symbol As String
    Dim fudge As Double
    Dim acc As vAccidental
        
    elem.el_typs = "keySignature"
    If Not (elem.accidentals Is Nothing) Then
        If (elem.accidentals.Count = 0) Then
            Exit Function
        End If
    End If
    Set abselem = N.AbsoluteElem(elem, 0, 10, "staff-extra key-signature", tuneNumber)
    abselem.isKeySig = True
    dx = 0
    For i = 0 To elem.accidentals.Count - 1
        Set acc = elem.accidentals(i)
        symbol = ""
        fudge = 0
        Select Case acc.acc
            Case "sharp": symbol = "accidentals.sharp": fudge = -3
            Case "natural": symbol = "accidentals.nat"
            Case "flat": symbol = "accidentals.flat": fudge = -1.2
            Case "quartersharp": symbol = "accidentals.halfsharp": fudge = -2.5
            Case "quarterflat": symbol = "accidentals.halfflat": fudge = -1.2
            Case Else: symbol = "accidentals.flat"
        End Select
        Dim opt As New oRelativeOptions
        opt.thickness = glyphs.symbolHeightInPitches(symbol)
        opt.top = acc.verticalPos + glyphs.symbolHeightInPitches(symbol) + fudge
        opt.bottom = acc.verticalPos + fudge
        
        abselem.addRight N.RelativeElem(symbol, dx, glyphs.getSymbolWidth(symbol), acc.verticalPos, opt)
        dx = dx + glyphs.getSymbolWidth(symbol) + 2
    Next
    Set createKeySignature = abselem
End Function




Function createTimeSignature(elem As vMeter, tuneNumber As Integer) As AbsoluteElement
    Dim abselem As AbsoluteElement
    Dim rElem As RelativeElement
    Dim opt As oRelativeOptions
    Dim x As Double
    Dim i As Integer, i2 As Integer, i3 As Integer
    Dim numWidth As Double, denWidth As Double
    Dim maxWidth As Double, thisWidth As Double
    Dim optO As oRelativeOptions
    
    elem.el_typs = "timeSignature"
    Set abselem = N.AbsoluteElem(elem, 0, 10, "staff-extra time-signature", tuneNumber)
    If (elem.typs = "specified") Then
        x = 0
        For i = 0 To elem.value.Count - 1
            If (i <> 0) Then
                opt.thickness = glyphs.symbolHeightInPitches("+")
                abselem.addRight N.RelativeElem("+", x + 1, glyphs.getSymbolWidth("+"), 6, opt)
                x = x + glyphs.getSymbolWidth("+") + 2
            End If
            If (elem.value(i).den) Then
                numWidth = 0
                Dim ss As String
                ss = CStr(elem.value(i).num)
                For i2 = 0 To Len(ss) - 1
                    numWidth = numWidth + glyphs.getSymbolWidth(Mid(ss, i2 + 1, 1))
                Next
                denWidth = 0
                ss = CStr(elem.value(i).den)
                For i2 = 0 To Len(ss) - 1
                    denWidth = denWidth + glyphs.getSymbolWidth(Mid(ss, i2 + 1, 1))
                Next
                maxWidth = Math.max(numWidth, denWidth)
                Set opt = New oRelativeOptions
                opt.thickness = glyphs.symbolHeightInPitches(elem.value(i).num)
                abselem.addRight N.RelativeElem(elem.value(i).num, x + (maxWidth - numWidth) / 2, numWidth, 8, opt)
                opt.thickness = glyphs.symbolHeightInPitches(elem.value(i).den)
                abselem.addRight N.RelativeElem(elem.value(i).den, x + (maxWidth - denWidth) / 2, denWidth, 4, opt)
                x = x + maxWidth
            Else
                thisWidth = 0
                ss = elem.value(i).num
                For i3 = 0 To Len(ss) - 1
                    thisWidth = thisWidth + glyphs.getSymbolWidth(Mid(ss, i3 + 1, 1))
                Next
                opt.thickness = glyphs.symbolHeightInPitches(elem.value(i).num)
                abselem.addRight N.RelativeElem(elem.value(i).num, x, thisWidth, 6, opt)
                x = x + thisWidth
            End If
        Next
     ElseIf (elem.typs = "common_time") Then
        opt.thickness = glyphs.symbolHeightInPitches("timesig.common")
        abselem.addRight N.RelativeElem("timesig.common", 0, glyphs.getSymbolWidth("timesig.common"), 6, opt)

     ElseIf (elem.typs = "cut_time") Then
        opt.thickness = glyphs.symbolHeightInPitches("timesig.cut")
        abselem.addRight N.RelativeElem("timesig.cut", 0, glyphs.getSymbolWidth("timesig.cut"), 6, opt)
     ElseIf (elem.typs = "tempus_imperfectum") Then
        opt.thickness = glyphs.symbolHeightInPitches("timesig.imperfectum")
        abselem.addRight N.RelativeElem("timesig.imperfectum", 0, glyphs.getSymbolWidth("timesig.imperfectum"), 6, opt)
     ElseIf (elem.typs = "tempus_imperfectum_prolatio") Then
        opt.thickness = glyphs.symbolHeightInPitches("timesig.imperfectum2")
        abselem.addRight N.RelativeElem("timesig.imperfectum2", 0, glyphs.getSymbolWidth("timesig.imperfectum2"), 6, opt)
     ElseIf (elem.typs = "tempus_perfectum") Then
        opt.thickness = glyphs.symbolHeightInPitches("timesig.perfectum")
        abselem.addRight N.RelativeElem("timesig.perfectum", 0, glyphs.getSymbolWidth("timesig.perfectum"), 6, opt)
     ElseIf (elem.typs = "tempus_perfectum_prolatio") Then
        opt.thickness = glyphs.symbolHeightInPitches("timesig.perfectum2")
        abselem.addRight N.RelativeElem("timesig.perfectum2", 0, glyphs.getSymbolWidth("timesig.perfectum2"), 6, opt)
     Else
       Debug.Print ("time signature:" + elem)
    End If
    Set createTimeSignature = abselem
End Function
Function germanNote(note As String) As String
    Dim gn As String
    Select Case (note)
        Case "B#": gn = "H#"
        Case "B＃": gn = "H＃"
        Case "B": gn = "H"
        Case "Bb": gn = "B"
        Case "Bｂ": gn = "B"
        Case eles: gn = note
    End Select
    germanNote = gn

End Function




Function translateChord(chordString, jazzchords, germanAlphabet) As String
    Dim lines
    Dim i As Integer
    Dim chord As String
    Dim baseChord As String
    Dim modifier As String
    Dim bassNote As String
    Dim marker As String
    Dim bass As String
    
    Dim reg
    Dim regEx As New RegExp, matches
    Dim str, MatchContent As String

    strDatePattern = "^((ABCDEFG)(??)?)?((^\/)+)?(\/((ABCDEFG)(#b??)?))?"

    With regEx
        .Global = True      ' 搜索字符串中的全部字符，如果?假，?找到匹配的字符就停止搜索！
        .MultiLine = False  ' 是否指定多行搜索
        .IgnoreCase = True  ' 指定大小寫敏感（True）
        .Pattern = strDatePattern   ' 所匹配的正則
    End With
    lines = Split(chordString, "\n")
    For i = 0 To UBound(lines) - 1
        chord = lines(i)
        '' If the chord isn"t in a recognizable format then just skip it.
        Set reg = regEx.Execute(chord)
        ''reg = chord.match(/^((ABCDEFG)(??)?)?((^\/)+)?(\/((ABCDEFG)(#b??)?))?/)
        If (UBound(reg) >= 4) Then
            baseChord = reg(1).value
            modifier = reg(2).value
            bassNote = reg(4).value
            If (germanAlphabet) Then
                baseChord = germanNote(baseChord)
                bassNote = germanNote(bassNote)
            End If
            '' This puts markers in the pieces of the chord that are read by the svg creator.
            '' After the main part of the chord (the letter, a sharp or flat, and "m") a marker is added. Before a slash a marker is added.
            marker = IIf(jazzchords, "0x03", "")
            bass = IIf(bassNote, "/" + bassNote, "")
            lines(i) = Join(Array(baseChord, modifier, bass), marker)
        End If
    Next
   translateChord = Join(lines, vbCrLf)

End Function

Public Function addChord(gTextSize As getTextSize, abselem As AbsoluteElement, elem As VoiceABC, roomTaken, roomTakenRight, noteheadWidth, jazzchords, germanAlphabet) As Dictionary
    Dim i As Integer, j As Integer
    Dim pos As Double
    Dim rel_position As Double
    Dim chords 'As Array
    Dim chord As String
    Dim x As Double, y As Double
    Dim font As vFont
    Dim klass As String
    Dim attr As Double
    Dim dime As Double
    Dim chordWidth As Double
    Dim chordHeight As Double
    Dim rOpt As oRelativeOptions
    
    
    For i = 0 To elem.chord.Count - 1
        pos = elem.chord(i).position
        rel_position = elem.chord(i).rel_position
        chords = elem.chord(i).Name.Split("\n")
        For j = UBound(chords) - 1 To 0 Step -1    '' parse these in opposite order because we place them from bottom to top.
            chord = chords(j)
            x = 0
            If (pos = "left" Or pos = "right" Or pos = "below" Or pos = "above" Or Not Not (rel_position)) Then
                font = "annotationfont"
                klass = "annotation"
            Else
                font = "gchordfont"
                klass = "chord"
                chord = translateChord(chord, jazzchords, germanAlphabet)
            End If
            attr = gTextSize.attr(font, klass)
            dime = gTextSize.calc(chord, font, klass)
            chordWidth = dime.width
            chordHeight = dime.height / spacing.Step
            Select Case (pos)
                Case "left":
                    roomTaken = roomTaken + chordWidth + 7
                    x = -roomTaken         '' TODO-PER: This is just a guess from trial and error
                    y = elem.averagepitch
                    Set rOpt = New oRelativeOptions
                    rOpt.typs = "text"
                    rOpt.height = chordHeight
                    rOpt.dime = attr
                    rOpt.position = "left"
                    
                    abselem.addExtra N.RelativeElem(chord, x, chordWidth + 4, y, rOpt)
                    break
                Case "right":
                    roomTakenRight = roomTakenRight + 4
                    x = roomTakenRight '' TODO-PER: This is just a guess from trial and error
                    y = elem.averagepitch
                    Set rOpt = New oRelativeOptions
                    rOpt.typs = "text"
                    rOpt.height = chordHeight
                    rOpt.dime = attr
                    rOpt.position = "right"
                    abselem.addRight N.RelativeElem(chord, x, chordWidth + 4, y, rOpt)
                Case "below":
                    '' setting the y-coordinate to undefined for now: it will be overwritten later on, after we figure out what the highest element on the line is.
                    Set rOpt = New oRelativeOptions
                    rOpt.typs = "text"
                    rOpt.height = chordHeight
                    rOpt.dime = attr
                    rOpt.position = "below"
                    rOpt.realWidth = chordWidth
                    
                    abselem.addRight N.RelativeElem(chord, 0, 0, 0, rOpt)

                Case "above":
                    '' setting the y-coordinate to undefined for now: it will be overwritten later on, after we figure out what the highest element on the line is.
                    Set rOpt = New oRelativeOptions
                    rOpt.typs = "text"
                    rOpt.height = chordHeight
                    rOpt.dime = attr
                    rOpt.position = "above"
                    rOpt.realWidth = chordWidth
                    abselem.addRight N.RelativeElem(chord, 0, 0, 0, rOpt)
                Case Else:
                    If (rel_position) Then
                        Dim relPositionY As Double
                        relPositionY = rel_position.y + 3 * spacing.Step  '' TODO-PER: this is a fudge factor to make it line up with abcm2ps
                        Set rOpt = New oRelativeOptions
                        rOpt.typs = "text"
                        rOpt.height = chordHeight
                        rOpt.dime = attr
                        rOpt.position = "relative"
                        abselem.addRight N.RelativeElem(chord, x + rel_position.x, 0, elem.minPitch + relPositionY / spacing.Step, rOpt)
                     Else
                        '' setting the y-coordinate to undefined for now: it will be overwritten later on, after we figure out what the highest element on the line is.
                        Dim pos2 As String
                        pos2 = "above"
                        If Not (elem.positioning Is Nothing) Then
                            If (elem.positioning.chordPosition) Then pos2 = elem.positioning.chordPosition
                        End If
                        If (pos2 <> "hidden") Then
                            Set rOpt = New oRelativeOptions
                            rOpt.typs = "chord"
                            rOpt.height = chordHeight
                            rOpt.dime = attr
                            rOpt.position = pos2
                            rOpt.realWidth = chordWidth
                            abselem.addCentered N.RelativeElem(chord, noteheadWidth / 2, chordWidth, 0, rOpt)
                        End If
                    End If
            End Select
        Next
    Next
    Dim ret As New Dictionary
    ret("roomTaken") = roomTaken
    ret("roomTakenRight") = roomTakenRight
    
    Set addChord = ret
End Function


Function createNoteHead(abselem As AbsoluteElement, c As String, pitchelem, options As oNoteHeadOptions) As Dictionary
    If (options Is Nothing) Then Set options = New oNoteHeadOptions
    Dim dir, headx, extrax, dot, dotshiftx, scale_, accidentalSlot, shouldExtendStem, printAccidentals
    Dim flag As String
    
    dir = IIf(options.dir <> "", options.dir, "")
    headx = IIf(options.headx, options.headx, 0)
    extrax = IIf(options.extrax, options.extrax, 0)
    flag = IIf(options.flag <> "", options.flag, "")
    dot = IIf(options.dot, options.dot, 0)
    dotshiftx = IIf(options.dotshiftx, options.dotshiftx, 0)
    scale_ = IIf(options.scale_, options.scale_, 1)
    Set accidentalSlot = IIf(Not (options.accidentalSlot Is Nothing), options.accidentalSlot, New iArray)
    shouldExtendStem = IIf(options.shouldExtendStem, options.shouldExtendStem, False)
    printAccidentals = IIf(options.printAccidentals, options.printAccidentals, True)

    '' TODO scale the dot as well
    Dim pitch As Double
    Dim notehead As RelativeElement
    Dim accidentalshiftx As Double
    Dim newDotShiftX As Double
    Dim extraLeft As Double
    Dim adjust As Double
    Dim shiftheadx As Double
    Dim pos As Double
    Dim xdelta As Double
    Dim dotadjusty As Double
    Dim rOpt As oRelativeOptions
    Dim opts As oRelativeOptions
    
    pitch = pitchelem.verticalPos
    accidentalshiftx = 0
    newDotShiftX = 0
    extraLeft = 0
    If c = Empty Then
        Set rOpt = New oRelativeOptions
        rOpt.typs = "debug"
        abselem.addFixed N.RelativeElem("pitch is undefined", 0, 0, 0, rOpt)
    
    ElseIf (c = "") Then
        Set notehead = N.RelativeElem(Empty, 0, 0, pitch)
    Else
        shiftheadx = headx
'line        If (pitchelem.printer_shift) Then
'            adjust = IIf(pitchelem.printer_shift = "same", 1, 0)
'            shiftheadx = IIf(dir = "down", -glyphs.getSymbolWidth(c) * scale_ + adjust, glyphs.getSymbolWidth(c) * scale_ - adjust)
'        End If
        Set opts = New oRelativeOptions
        opts.scalex = scale_
        opts.scaley = scale_
        opts.thickness = glyphs.symbolHeightInPitches(c) * scale_
        opts.Name = pitchelem.Name
        Set notehead = N.RelativeElem(c, shiftheadx, glyphs.getSymbolWidth(c) * scale_, pitch, opts)
        notehead.stemdir = dir
        ''這邊是看是否要加入單個 1/4 1/8 1/16 的符桿符號
        If (flag <> "") Then
            pos = pitch + IIf(dir = "down", -7, 7) * scale_
            '' if this is a regular note, (not grace or tempo indicator) then the stem will have been stretched to the middle line if it is far from the center.
            If (shouldExtendStem) Then
                If (dir = "down" And pos > 6) Then pos = 6
                If (dir = "up" And pos < 6) Then pos = 6
            End If
            ''if (scale=1 && (dir="down")?(pos>6):(pos<6)) pos=6
            xdelta = IIf(dir = "down", headx, headx + notehead.w - 0.6)
            Set opts = New oRelativeOptions
            opts.scalex = scale_
            opts.scaley = scale_
            abselem.addRight N.RelativeElem(flag, xdelta, glyphs.getSymbolWidth(flag) * scale_, pos, opts)
        End If
        newDotShiftX = notehead.w + dotshiftx - 2 + 5 * dot
        For dot = dot To 0 Step -1
            dotadjusty = (1 - Abs(pitch) Mod 2)  ''PER: take abs value of the pitch. And the shift still happens on ledger lines.
            abselem.addRight N.RelativeElem("dots.dot", notehead.w + dotshiftx - 2 + 5 * dot, glyphs.getSymbolWidth("dots.dot"), pitch + dotadjusty)
        Next
    End If
    If Not (notehead Is Nothing) Then
        notehead.highestVert = pitchelem.highestVert
    End If
    ''加入升降記號
    If (printAccidentals And pitchelem.accidental <> "") Then
        Dim symb As String
        Select Case (pitchelem.accidental)
            Case "quartersharp":    symb = "accidentals.halfsharp"
            Case "dblsharp":        symb = "accidentals.dblsharp"
            Case "sharp":           symb = "accidentals.sharp"
            Case "quarterflat":     symb = "accidentals.halfflat"
            Case "flat":            symb = "accidentals.flat"
            Case "dblflat":         symb = "accidentals.dblflat"
            Case "natural":         symb = "accidentals.nat"
        End Select
        '' if a note is at least a sixth away, it can share a slot with another accidental
        Dim accSlotFound As Boolean
        Dim accPlace  As Double
        Dim j As Integer
        Dim h As Double
        Dim opt3 As oRelativeOptions
        
        accSlotFound = False
        accPlace = extrax
        For j = 0 To UBound(accidentalSlot) - 1
            If (pitch - accidentalSlot(j, 0) >= 6) Then
                accidentalSlot(j, 0) = pitch
                accPlace = accidentalSlot(j, 1)
                accSlotFound = True
                Exit For
            End If
        Next
        If (accSlotFound = False) Then
            accPlace = accPlace - (glyphs.getSymbolWidth(symb) * scale_ + 2)
            accidentalSlot.Push ([pitch, accPlace])
            accidentalshiftx = (glyphs.getSymbolWidth(symb) * scale_ + 2)
        End If
        Set opt3 = New oRelativeOptions
        h = glyphs.symbolHeightInPitches(symb)
         opt3.scalex = scale_
         opt3.scaley = scale_
         opt3.top = pitch + h / 2
         opt3.bottom = pitch - h / 2
        
        abselem.addExtra N.RelativeElem(symb, accPlace, glyphs.getSymbolWidth(symb), pitch + 3, opt3)
        extraLeft = glyphs.getSymbolWidth(symb) / 2  '' TODO-PER: We need a little extra width if there is an accidental, but I'm not sure why it isn't the full width of the accidental.
    End If
    Dim retDict As New Dictionary
    Set retDict("notehead") = notehead
    retDict("accidentalshiftx") = accidentalshiftx
    retDict("dotshiftx") = dotshiftx
    retDict("extraLeft") = extraLeft
    
    Set createNoteHead = retDict
End Function

'export var createNoteHeadJianpu = function (abselem: AbsoluteElement, c, pitchelem, options) {
'    if (!options) options = {}
'    var dir = (options.dir !== undefined) ? options.dir : null
'    '' dx 軸的位移
'    var headx = (options.headx !== undefined) ? options.headx : 0
'    var extrax = (options.extrax !== undefined) ? options.extrax : 0
'    var flag = (options.flag !== undefined) ? options.flag : null
'    var dot = (options.dot !== undefined) ? options.dot : 0
'    var dotshiftx = (options.dotshiftx !== undefined) ? options.dotshiftx : 0
'    var scale = (options.scale !== undefined) ? options.scale : 1
'    var accidentalSlot = (options.accidentalSlot !== undefined) ? options.accidentalSlot : []
'    var shouldExtendStem = (options.shouldExtendStem !== undefined) ? options.shouldExtendStem : false
'    var printAccidentals = (options.printAccidentals !== undefined) ? options.printAccidentals : true
'
'    '' TODO scale the dot as well
'    var pitch = pitchelem.verticalPos
'    var notehead: RelativeElement
'    var accidentalshiftx = 0
'    var newDotShiftX = 0
'    var extraLeft = 0
'    if (c === undefined) {
'        abselem.addFixed(new RelativeElement("pitch is undefined", 0, 0, 0, { type: "debug" }))
'    }
'    elseif (c === "") {
'        notehead = new RelativeElement(null, 0, 0, pitch)
'    } else {
'        var shiftheadx = headx
'        '' jianpu 不用這個
'        ''if (pitchelem.printer_shift) {
'        ''  var adjust = (pitchelem.printer_shift === "same") ? 1 : 0
'        ''  shiftheadx = (dir === "down") ? -glyphs.getSymbolWidth(c) * scale + adjust : glyphs.getSymbolWidth(c) * scale - adjust
'        ''}
'        shiftheadx = -glyphs.getSymbolWidth(c) * scale
'        var opts = { scalex: scale, scaley: scale, thickness: glyphs.symbolHeightInPitches(c) * scale, name: pitchelem.name }
'
'        notehead = new RelativeElement(c, 0, glyphs.getSymbolWidth(c) * scale, pitch, opts)
'        notehead.stemDir = dir
'        ''這邊是看是否要加入單個 1/4 1/8 1/16 的符桿符號
'        '' jianpu 不用
'        ''if (flag) {
'        ''  var pos = pitch + ((dir === "down") ? -7 : 7) * scale
'        ''  '' if this is a regular note, (not grace or tempo indicator) then the stem will have been stretched to the middle line if it is far from the center.
'        ''  if (shouldExtendStem) {
'        ''      if (dir === "down" && pos > 6)
'        ''          pos = 6
'        ''      if (dir === "up" && pos < 6)
'        ''          pos = 6
'        ''  }
'        ''  ''if (scale===1 && (dir==="down")?(pos>6):(pos<6)) pos=6
'        ''  var xdelta = (dir === "down") ? headx : headx + notehead.w - 0.6
'        ''  abselem.addRight(new RelativeElement(flag, xdelta, glyphs.getSymbolWidth(flag) * scale, pos, { scalex: scale, scaley: scale }))
'        ''}
'        var getDurlog = function (duration) {
'            '' TODO-PER: This is a hack to prevent a Chrome lockup. Duration should have been defined already,
'            '' but there's definitely a case where it isn't. [Probably something to do with triplets.]
'            if (duration === undefined) {
'                return 0
'            }
'            ''        console.log("getDurlog: " + duration)
'            return Math.floor(Math.log(duration) / Math.log(2))
'        }
'        '' 加入 jianpu 的節拍線
'        if (flag) {
'            var duration = abselem.duration  '' get the duration via abcelem because of triplets
'            if (duration === 0) duration = 0.25  '' if this is stemless, then we use quarter note as the duration.
'            for (var durlog = getDurlog(duration)  durlog < -2  durlog++) {
'                var index = -durlog - 3
'                abselem.addFixed(new RelativeElement(null, 0, glyphs.getSymbolWidth(c) * scale, 1.5 - index * 0.8, { type: "beatline", pitch2: 1, linewidth: 1.2, bottom: 1 }))
'            }
'        }
'        ''abselem.addRight(new RelativeElement(null, dx, 0, p1, { type: "stem", pitch2: p2, linewidth: width, bottom: p1 - 1 }))
'        newDotShiftX = notehead.w + dotshiftx - 2 + 5 * dot
'        for (  dot > 0  dot--) {
'            ''PER: take abs value of the pitch. And the shift still happens on ledger lines.
'            ''PER：取音高的絕對值。 這種轉變仍然發生在帳本上。
'            var dotadjusty = (1 - Math.abs(pitch) % 2)
'            abselem.addRight(new RelativeElement("dots.dot", notehead.w + dotshiftx - 2 + 5 * dot, glyphs.getSymbolWidth("dots.dot"), pitch + dotadjusty))
'        }
'    }
'    if (notehead)
'        notehead.highestVert = pitchelem.highestVert
'    ''加入升降記號
'    if (printAccidentals && pitchelem.accidental) {
'        var symb
'        switch (pitchelem.accidental) {
'            Case "quartersharp":
'                symb = "accidentals.halfsharp"
'                break
'            Case "dblsharp":
'                symb = "accidentals.dblsharp"
'                break
'            Case "sharp":
'                symb = "accidentals.sharp"
'                break
'            Case "quarterflat":
'                symb = "accidentals.halfflat"
'                break
'            Case "flat":
'                symb = "accidentals.flat"
'                break
'            Case "dblflat":
'                symb = "accidentals.dblflat"
'                break
'            Case "natural":
'                symb = "accidentals.nat"
'        }
'        '' if a note is at least a sixth away, it can share a slot with another accidental
'        var accSlotFound = false
'        '' jianpu 不用 var accPlace = extrax
'        var accPlace = 0
'        for (var j = 0  j < accidentalSlot.length  j++) {
'            if (pitch - accidentalSlot[j][0] >= 6) {
'                accidentalSlot[j][0] = pitch
'                accPlace = accidentalSlot[j][1]
'                accSlotFound = true
'                break
'            }
'        }
'        if (accSlotFound === false) {
'            accPlace -= (glyphs.getSymbolWidth(symb) * scale + 2)
'            accidentalSlot.push([pitch, accPlace])
'            accidentalshiftx = (glyphs.getSymbolWidth(symb) * scale + 2)
'        }
'        var h = glyphs.symbolHeightInPitches(symb)
'        abselem.addExtra(new RelativeElement(symb, accPlace, glyphs.getSymbolWidth(symb), pitch + 3, { scalex: scale, scaley: scale, top: pitch + h / 2, bottom: pitch - h / 2 }))
'        extraLeft = glyphs.getSymbolWidth(symb) / 2  '' TODO-PER: We need a little extra width if there is an accidental, but I'm not sure why it isn't the full width of the accidental.
'    }
'
'    return { notehead: notehead, accidentalshiftx: accidentalshiftx, dotshiftx: newDotShiftX, extraLeft: extraLeft }
'
'}
'export default createNoteHead


Public Function pitchesToPerc(pitchObj) As String
    Dim pitchDict As New Dictionary
    pitchDict("f0") = "_C":  pitchDict("s8") = "^d":
    pitchDict("n0") = "=C":  pitchDict("x8") = "d":
    pitchDict("s0") = "^C":  pitchDict("f9") = "_e":
    pitchDict("x0") = "C":   pitchDict("n9") = "=e":
    pitchDict("f1") = "_D":  pitchDict("s9") = "^e":
    pitchDict("n1") = "=D":  pitchDict("x9") = "e":
    pitchDict("s1") = "^D":  pitchDict("f10") = "_f":
    pitchDict("x1") = "D":   pitchDict("n10") = "=f":
    pitchDict("f2") = "_E":  pitchDict("s10") = "^f":
    pitchDict("n2") = "=E":  pitchDict("x10") = "f":
    pitchDict("s2") = "^E":  pitchDict("f11") = "_g":
    pitchDict("x2") = "E":   pitchDict("n11") = "=g":
    pitchDict("f3") = "_F":  pitchDict("s11") = "^g":
    pitchDict("n3") = "=F":  pitchDict("x11") = "g":
    pitchDict("s3") = "^F":  pitchDict("f12") = "_a":
    pitchDict("x3") = "F":   pitchDict("n12") = "=a":
    pitchDict("f4") = "_G":  pitchDict("s12") = "^a":
    pitchDict("n4") = "=G":  pitchDict("x12") = "a":
    pitchDict("s4") = "^G":  pitchDict("f13") = "_b":
    pitchDict("x4") = "G":   pitchDict("n13") = "=b":
    pitchDict("f5") = "_A":  pitchDict("s13") = "^b":
    pitchDict("n5") = "=A":  pitchDict("x13") = "b":
    pitchDict("s5") = "^A":  pitchDict("f14") = "_c'":
    pitchDict("x5") = "A":   pitchDict("n14") = "=c'":
    pitchDict("f6") = "_B":  pitchDict("s14") = "^c'":
    pitchDict("n6") = "=B":  pitchDict("x14") = "c'":
    pitchDict("s6") = "^B":  pitchDict("f15") = "_d'":
    pitchDict("x6") = "B":   pitchDict("n15") = "=d'":
    pitchDict("f7") = "_c":  pitchDict("s15") = "^d'":
    pitchDict("n7") = "=c":  pitchDict("x15") = "d'":
    pitchDict("s7") = "^c":  pitchDict("f16") = "_e'":
    pitchDict("x7") = "c":   pitchDict("n16") = "=e'":
    pitchDict("f8") = "_d":  pitchDict("s16") = "^e'":
    pitchDict("n8") = "=d":  pitchDict("x16") = "e'":
    
    Dim pitch As String

    pitch = IIf(Not pitchObj.accidental Is Nothing, pitchObj.accidental(0), "x") & pitchObj.verticalPos
    pitchesToPerc = pitchDict(pitch)
End Function

Attribute VB_Name = "frmEDIT"
Attribute VB_Base = "0{9CA5FF98-9AB1-4A29-AB31-22686FFA2A4D}{96B7F615-8392-4538-8932-5AFA8BE0FD70}"
Attribute VB_GlobalNameSpace = False
Attribute VB_Creatable = False
Attribute VB_PredeclaredId = True
Attribute VB_Exposed = False
Attribute VB_TemplateDerived = False
Attribute VB_Customizable = False


Option Explicit
'2025.11.26  v2.14 加入 rest{ type: "multimeasure"} 合併小節 (Z4)
'2025.04.25  加入 I:pagebreak 44 '設定第 x 小節強制換頁，小節數重 1 開始
'2025.04.25  加入 I:linebreak 44 '設定第 x 小節強制換行
'2024.11.28  isVirtualChar As Boolean '設定空心字符  v2.13
'2024.11.28  加入 I:setbar 5/3 在台頭設定 "第幾小節開始/每行幾小節"
'2024.11.27  v2.12 tuplet "{" "}" 加入 3 5 6 7 連音的功能
'2024.08.27  修改 疊音的高底音點位置
'2024.08.23  "v2.1" 加入 前綴元素 '>'  後綴元素 '<'
'2024.03.30  "v2.0" 要加入 拍號 M:3/8 M:4/4 ，大改音符排序方式
'2024.03.29  修改 4/4 3/8 拍數對位問題
'2013.11.21  修改 DataBuffer 為元素
'            多加 iAdd 合音行
'2013.03.17  V3 正要修改 二胡的版本，因程式之前是用古箏的指法圖，現在改成二胡的指法圖

Const version  As String = "v2.14" '軟體號碼
Const c1 As Integer = 60   'C調1的鍵名值
'Const FOURPAINUM   As Integer = 64 '1/4音符計數
'Const MIDICLOCK As Integer = 24   '每1/64音符的MIDICLOCK數
'Const TEMPO_DEF As Integer = 90   '預設每分鐘90拍
Const PARTITION_DEF As Integer = 384   '預設每拍分割為384計時單元
Const VOLUME_DEF As Integer = 64
Const MAINLAYER As String = "MAIN"    '主要的圖層
Dim partLayer As String     '記錄現在第幾部



'二胡指法 狀態
Private Type ErhuFing
    fing1 As Integer    'Ⅰ Ⅱ Ⅲ Ⅳ "b空絃"
    fing2 As String  'Ⅰ Ⅱ Ⅲ Ⅳ "b空絃"
    Push As String      '拉∩ 推V
    InOut As String     '內   外
End Type

Dim m_buf As New DataBuffer
Dim TuneLines As New TuneLineList
Private constTE As New constructTuneElements


Private acadapp As AcadApplication
Private acadDoc As AcadDocument

'--------------------------------------------------------------
'連接Cad
'-------------------------------------------------------------
Private Function AcadConnect() As Boolean
Dim flag As Boolean
On Error Resume Next
    Set acadapp = GetObject(, "AutoCAD.Application")
    flag = True
    If err Then
       err.Clear
       Set acadapp = CreateObject("AutoCAD.Application")
       flag = True
       If err Then
          flag = False
          MsgBox "不能運行AutoCAD,請檢查是否安�E！", vbOKCancel, "警告！"
          Exit Function
       End If
    End If
    AcadConnect = flag
    Set acadDoc = acadapp.ActiveDocument
    'acadDoc.Close False
End Function


Private Sub cbCANCLE_Click()
    Me.Hide
End Sub


Private Sub init()
    G.fontName = Me.cobFontName.text
    G.fontsize = Me.cobFontSize.text
    
    Dim mete_mete As Variant
    mete_mete = Split(Me.cobMete, "/")
    G.mete = mete_mete(0)
    G.mete2 = mete_mete(1)
    
    G.Many = Me.cobMany
    G.bar = Me.cobBar.text
    G.barsperstaff = Me.cobBar.text
    
    G.pagewidth = Me.tbPageWidth '寬度
    G.LeftSpace = Me.tbLeftSpace  '左空白
    G.RightSpace = Me.tbRightSpace  '右空白
    G.BarToNoteSpace = Me.tbBarToNote    '小節到音符
    G.TrackToTrack = Me.tbTrackToTrack  '聲部間距
    G.LineToLine = Me.tbLineToLine      '每行間距
    G.check1 = True
    G.MIN_X = Me.tbMIN_X            '微調
    G.Beat_MIN_X = Me.tbBeat_min_x  '拍微調
    G.IsBarAlign = Me.cbIsBarAlign
    G.isVirtualChar = Me.cbVirtualChar  '空心字
End Sub

Private Sub cmOK_Click()

    Call init

    database
    Set m_buf = New DataBuffer '.Clear
    
    Dim rr As runTime
    Set rr = rTime
    rr ("LoadDataToBuf")
    Call m_buf.LoadDataToBuf(Me.TextBox8.text)
    rr ("LoadDataToBuf")
    'MsgBox Me.TextBox8.text
    Me.Hide

    '整理 拍號及小節數 分成一行一行的 TuneLines
    Set TuneLines = constTE.translate2Staffs(m_buf)
    
    'layout 將 x 坐標調整到其絕對位置
    rr ("layout")
    Call layout(TuneLines, 210#, 30)
    rr ("layout")
    
    rr ("drawLayoutStaff")
    Call drawLayoutStaff(TuneLines)
    rr ("drawLayoutStaff")
    'Call draw_many_text1
    'Call setLayoutMusicItem
    
    rr.ToList
End Sub


Private Sub CommandButton2_Click()
    'abc 測試

    Call init

    database
    Set m_buf = New DataBuffer '.Clear
    Call m_buf.LoadDataToBuf(Me.TextBox8.text)
    'MsgBox Me.TextBox8.text
    Me.Hide
    
    Set tune = New TuneData
    Set gTuneLine = New TuneLine
    Set gTuneLine.staffGroup = New StaffGroupElement
    Set gTuneLine.Staffs = getToStaffList(m_buf)
    ''GTuneLine..Staffs getInitABCElement
    
    Dim v As VoiceABCList
    Set v = gTuneLine.Staffs(0).voices(0)
    
    ''v.AddArrayAfter , m_Buf.getToVoiceABCs
    Dim eg As New EngraverController
    eg.init Nothing, Nothing
    'getToStaff m_Buf
    
    Set tune.engraver = eg
    If (tune.lines Is Nothing) Then
        Set tune.lines = New TuneLineList
        tune.lines.Push gTuneLine
    Else
        tune.lines.Push gTuneLine
    End If
    tune.version = "1.0.0"
    
    eg.engraveABC tune
    
    Call draw_many_text1

    
End Sub



Private Function getInitABCElement() As Staff
'設定調號 音位 拍號
    Dim staffEle As New Staff
    Dim cl As vClefProperties
    Dim ky As vKeySignature
    Dim mf As vMeter
    
    '存 調號
    Set cl = New vClefProperties
    cl.el_typs = "clef"
    cl.typs = "treble"
    cl.verticalPos = 0
    
    
    '存 音位
    Dim vAcc As New vAccidental
    vAcc.acc = "sharp"
    vAcc.note = "f"
    vAcc.verticalPos = 10
    Set ky = New vKeySignature
    Set ky.accidentals = New iArray
    ky.el_typs = "keySignature"
    ky.root = "E"
    ky.accidentals.Push vAcc
    
    
    '拍號
    Dim mFrac As New vMeterFraction
    mFrac.num = 4
    mFrac.den = 4
    Set mf = New vMeter
    Set mf.value = New vMeterFractionList
    mf.el_typs = "timeSignature"
    mf.typs = "specified"
    mf.value.Push mFrac
    
    
    Set staffEle.clef = cl
    Set staffEle.key = ky
    Set staffEle.meter = mf
    
    Set staffEle.voices = New iArray
    Set getInitABCElement = staffEle
End Function
Private Function getToStaffList(buf As DataBuffer) As StaffList
    Dim trkCount As Long
    Dim noteCount As Long
    Dim i As Integer, j As Integer
    Dim staffElem As Staff
    Dim currVoice As VoiceABCList
    
    Set getToStaffList = New StaffList
    trkCount = buf.GetTrackSize
    For i = 0 To trkCount - 1
        Set staffElem = getInitABCElement()
        staffElem.voices.Push buf.getVoiceListData(i)
        getToStaffList.Push staffElem
'        buf.ConverToVoiceABCList i
'        If (staffEle.voices Is Nothing) Then
'            ReDim staffEle.voices(trkCount)
'        End If
'        noteCount = buf.GetTrackBufferSize(i)
'        Set currVoice = staffEle.voices(i)
'        For j = 0 To noteCount
'            buf.ConverToVoiceABCList i
'        Next
    
    Next
    


End Function
Private Sub database()
    ' Create new layer
    Dim i As Integer
    Dim color As AcadAcCmColor
    Dim layerObj As AcadLayer
    Dim sarr() As String
    Dim datalayer As New iArray
    '設定 --> "圖層名字 顏色"
    datalayer.PushArray Array( _
    "FIGE 6", _
    "TEXT 2", _
    "bar 181", _
    "裝飾符號 4", _
    "自繪線 1", _
    "main 7", _
    "SimpErhu符號 151")

    
    '新建圖層
    For i = 0 To datalayer.Count - 1
        sarr = Split(datalayer(i), " ")
        Set layerObj = ThisDrawing.Layers.Add(sarr(0))
        Set color = AcadApplication.GetInterfaceObject("AutoCAD.AcCmColor." & ACAD_Ver)
        color.ColorIndex = sarr(1)
        layerObj.TrueColor = color
    Next


   
    ' Create a Text style named "TEST" in the current drawing
    Dim textStyle As AcadTextStyle
    Dim dataStyles(20, 3) As String
    dataStyles(0, 1) = "Standard"
    dataStyles(0, 2) = "txt.shx"
    dataStyles(0, 3) = "chineset.shx"
    dataStyles(1, 1) = "EUDC"
    dataStyles(1, 2) = "EUDC.TTE"
    dataStyles(1, 3) = ""
    dataStyles(2, 1) = "標體"
    dataStyles(2, 2) = "KAIU.TTF"
    dataStyles(2, 3) = ""
    dataStyles(3, 1) = "MMP2005"
    dataStyles(3, 2) = ""
    dataStyles(3, 3) = ""
    dataStyles(4, 1) = "音符_數字"
    dataStyles(4, 2) = "SimSun.ttc"
    dataStyles(4, 3) = ""
    dataStyles(5, 1) = "型式_細明體"
    dataStyles(5, 2) = "MingLiU.ttc"
    'dataStyles(5, 2) = "PMingLiU.ttf"
    dataStyles(5, 3) = ""
    dataStyles(6, 1) = "字符"
    dataStyles(6, 2) = "MAESTRO.TTF"
    dataStyles(6, 3) = ""
    dataStyles(7, 1) = "華康粗黑"
    dataStyles(7, 2) = "DFFT_C7.ttc"
    'dataStyles(7, 2) = "DFLiHeiBold.ttf"
    dataStyles(7, 3) = ""
    dataStyles(8, 1) = "文字"
    dataStyles(8, 2) = "KAIU.TTF"
    dataStyles(8, 3) = ""
    dataStyles(9, 1) = "SimpErhu"
    dataStyles(9, 2) = "SimpErhuFont.ttf"
    dataStyles(9, 3) = ""

    'Dim i As Integer
'    For i = 0 To 9
'        Set textStyle = ThisDrawing.TextStyles.add(dataStyles(i, 1))
'        If dataStyles(i, 2) <> "" Then
'
'            Set textStyle = CreateTextStyle(dataStyles(i, 2), dataStyles(i, 1), FontType.BigFont)
'        End If
'        If dataStyles(i, 3) <> "" Then
'            textStyle.BigFontFile = dataStyles(i, 3)
'        End If
'    Next
End Sub
Private Sub inst_G(the_G As Glode, aPt As point)
    '插入設定資料
    Dim mtxt As AcadMText
    Dim textObj As AcadText
    Dim textString As String
    Dim insertionPt As New point
    Dim height As Double
    
    ' Define the text object
    textString = version & vbCrLf
    textString = textString & "size " & the_G.fontsize & vbCrLf
    
    textString = textString & "左空白 " & the_G.LeftSpace & "mm" & vbCrLf
    textString = textString & "右空白 " & the_G.RightSpace & "mm" & vbCrLf
    textString = textString & "小節到音符 " & the_G.BarToNoteSpace & "mm" & vbCrLf
    textString = textString & "聲部  " & the_G.TrackToTrack & "mm" & vbCrLf
    textString = textString & "每行  " & the_G.LineToLine & "mm" & vbCrLf
    textString = textString & "微調  " & the_G.MIN_X & "mm" & vbCrLf
    textString = textString & "拍微調 " & the_G.Beat_MIN_X
    
    
    insertionPt.x = aPt.x - 30
    insertionPt.y = aPt.y
    insertionPt.Z = aPt.Z
    height = 3
    
    ' Create the text object in model space
    Set mtxt = ThisDrawing.ModelSpace.AddMText(insertionPt.ToDouble, height, textString)
    mtxt.width = 40
    mtxt.styleName = "Standard"
    
    '插入資料
    insertionPt.x = insertionPt.x - 3
    Set mtxt = ThisDrawing.ModelSpace.AddMText(insertionPt.ToDouble, 25, Me.TextBox8.text)
    mtxt.height = 0.01
    
End Sub
Private Sub drawLayoutStaff(abcTuneLines As TuneLineList)
    Dim MBG As New MusicBlockGraphics
    
    '放置文字本
    Dim retPt As Variant
    Dim insPt As New point
    
    ' Return a point using a prompt
    retPt = ThisDrawing.Utility.GetPoint(, "\n選擇要插入的點 ：Enter insertion point: ")
    insPt.a retPt
    '插入設定資料文字說明
    Call inst_G(G, insPt)
'***********************************************************************************
    '畫出定位線-畫框
    Dim plineObj As AcadPolyline
    Set plineObj = MBG.insterPositionBox(insPt, G)

'*********************************************************************************
    '插入單一標題
    Dim objText As AcadText
    Dim titlePT As New point
    Dim ooPt As New point
    
    titlePT.x = insPt.x + (G.pagewidth / 2)
    titlePT.y = insPt.y + G.fontsize * 5.5
    Set objText = ThisDrawing.ModelSpace.AddText(m_buf.getTITLE, titlePT.ToDouble, 6)
    ooPt.a objText.insertionPoint
    objText.Layer = "TEXT"
    objText.Alignment = acAlignmentCenter
    objText.styleName = "文字"
    ooPt.x = ooPt.x + objText.insertionPoint(0)
    ooPt.y = ooPt.y + objText.insertionPoint(1)
    
    objText.Move objText.insertionPoint, ooPt.ToDouble

'*********************************************************************************
'建立主要 音符
    Dim layerObj As AcadLayer
    Set layerObj = ThisDrawing.Layers.Add(MAINLAYER)


    Dim tmp_joinApp As New iArray
    Dim tmp_joinIds As New iArray
    'double lastTemp
    Dim tmp_track As Integer
    Dim tmp_track_item As Long
    Dim A_TEMPO_add As Integer

    Dim tmp_delaytime As Double  '計算拍子 是要計上一個字的長度
    
    Dim tmp_xy As point
    
    Dim BNewObj As AcadBlockReference
    Dim ptlist As New PointList
    Dim tmp_pLWPoly As AcadPolyline
    Dim tmp_name As String
    
    'Dim cst As String
    'Dim cst_no_fing As String
    Dim ptGripMid As Variant
    Dim s1 As MusicItem
    
    tmp_delaytime = 0
    
    tmp_name = G.fontName
    Dim tmp_erhu_fing As ErhuFing
    Dim midDownPt(2) As Double
    Dim mt_slur_left As MusicBlockGraphics
    Dim mt_slur_right As MusicBlockGraphics
    Dim plineSlur As AcadLWPolyline
    Dim mt_tuplet_left As MusicBlockGraphics
    Dim mt_tuplet_right As MusicBlockGraphics
    Dim plineTuplet As AcadLWPolyline
    
    Dim barConfig(1000) As aBarConfig
    Dim barId As Integer
    Dim currStaffGroup As StaffGroupElement
    Dim vo As VoiceElement
    Dim trackY As Double
    Dim iLineToLine As Integer
    Dim iTrackToTrack As Integer
    Dim currX As Double
    Dim currY As Double
    Dim i As Integer
    Dim j As Integer
    Dim k As Integer
    Dim startPt As New point
    Dim endPt As New point
    'Dim sumLine As Integer  '計算第幾行
    'Dim sumMeasure As Integer  '計算每行的第幾行
    
''******繪製下拍線 變數
    Dim durationIndex   As Double
    Dim nlast As Integer
    Dim s2 As MusicItem
    Dim Temo1 As Double
    Dim Temo2 As Double
    Dim beamMuseList As New MusicItemList
''***********************************
    trackY = 0
    iLineToLine = -1
    iTrackToTrack = 0
    MBG.setVirtualChar G.isVirtualChar
    For i = 0 To abcTuneLines.Count - 1
        Set currStaffGroup = abcTuneLines(i).staffGroup
        
        
        For j = 0 To abcTuneLines(i).staffGroup.voices.Count - 1
'            If j = 0 Or j = 2 Then
'                G.FONTSIZE = 3.6
'            Else
'                G.FONTSIZE = 3.4
'            End If
            partLayer = j
            
            
            Set vo = abcTuneLines(i).staffGroup.voices(j)
            startPt.c 0, 0
            endPt.c 0, 0
            If j = 0 Then
                iLineToLine = iLineToLine + 1
            Else
                iTrackToTrack = iTrackToTrack + 1
            End If
            'currY = (G.TrackToTrack * j) + (G.LineToLine * i) + (G.TrackToTrack * (abcTuneLines(i).StaffGroup.voices.Count - 1)) * i
            currY = G.TrackToTrack * iTrackToTrack + G.LineToLine * iLineToLine
            currY = insPt.y - currY
            currX = insPt.x + G.LeftSpace
            
            durationIndex = 0
            Temo1 = 0
            nlast = 0
            For k = 0 To vo.children.Count - 1
                Set s1 = vo.children(k)
                Select Case s1.typs
                   Case Cg.bar:
                        '繪製小節線  ********************************
                        If j > 0 And k < 3 Then
                            '第二部的第一個小節線要拉長
                            startPt.x = currX + s1.x + s1.w / 2
                            startPt.y = G.TrackToTrack + currY
                            endPt.x = startPt.x
                            endPt.y = currY
                        Else
                            startPt.x = currX + s1.x + s1.w / 2
                            startPt.y = ((amt.LINE_PASE + amt.DROP_UP) * G.fontsize) + currY
                            endPt.x = startPt.x
                            endPt.y = currY
                        
                        End If
                        
                        ptlist.Clear
                        ptlist.Add startPt
                        ptlist.Add endPt
                        
                        s1.oX = startPt.x
                        s1.oY = startPt.y
                        Set tmp_pLWPoly = ThisDrawing.ModelSpace.AddPolyline(ptlist.ToXYZList)
                        tmp_pLWPoly.ConstantWidth = amt.BAR_WITCH * G.fontsize / 4.6
                        tmp_pLWPoly.Layer = "bar"
                        
                        '繪小節號 ***********************************
                        If j = 0 And durationIndex = 0 Then
                            Dim ipt(3) As point
                            Dim objT As AcadText
                            Dim txtmidPT As New point
                            Set ipt(0) = New point: Set ipt(1) = New point: Set ipt(2) = New point: Set ipt(3) = New point
                            ipt(0).x = startPt.x
                            ipt(0).y = startPt.y + 0.2 * G.fontsize
                            ipt(1).x = startPt.x: ipt(1).y = startPt.y + (0.2 + amt.barInsterNumberSize * 1.3) * G.fontsize
                            ipt(2).x = ipt(0).x - amt.barInsterNumberSize * (Len(CStr(s1.barNumber + 1)) * 1.1) * G.fontsize
                            ipt(2).y = ipt(1).y
                            ipt(3).x = ipt(2).x
                            ipt(3).y = ipt(0).y
                            ptlist.Clear
                            ptlist.Add ipt(0)
                            ptlist.Add ipt(1)
                            ptlist.Add ipt(2)
                            ptlist.Add ipt(3)
                            ptlist.Add ipt(0)
                            Set tmp_pLWPoly = ThisDrawing.ModelSpace.AddPolyline(ptlist.ToXYZList)
                            tmp_pLWPoly.Layer = "TEXT"
                            
                            txtmidPT.x = ipt(1).x - Abs(ipt(1).x - ipt(2).x) / 2
                            txtmidPT.y = ipt(0).y + Abs(ipt(1).y - ipt(0).y) / 2
                            Set objT = ThisDrawing.ModelSpace.AddText(CStr(s1.barNumber + 1), txtmidPT.ToDouble, amt.barInsterNumberSize * G.fontsize)
                            objT.Layer = "Text"
                            objT.styleName = "txt"
                            ooPt.a objT.insertionPoint
                            objT.Alignment = acAlignmentMiddleCenter
                            
                            ooPt.x = ooPt.x + objT.insertionPoint(0)
                            ooPt.y = ooPt.y + objT.insertionPoint(1)
                            
                            objT.Move objT.insertionPoint, ooPt.ToDouble
                            If s1.barNumber + 1 = 37 Then
                                Debug.Print 37
                            End If
                            
                        End If
                   Case Cg.meter:
                        '繪製拍號  ********************************
                        Dim metePt1 As New point
                        Dim metePt2 As New point
                        metePt2.x = currX + s1.x
                        metePt2.y = currY + 0.3 * G.fontsize
                        
                        metePt1.x = currX + s1.x
                        metePt1.y = currY + 1.3 * G.fontsize
                        
                        Set objText = ThisDrawing.ModelSpace.AddText(s1.mete2, metePt2.ToDouble, G.fontsize * 0.7)
                        objText.Layer = "裝飾符號":         objText.styleName = "音符_數字"
                        
                        Set objText = ThisDrawing.ModelSpace.AddText(s1.mete, metePt1.ToDouble, G.fontsize * 0.7)
                        objText.Layer = "裝飾符號":         objText.styleName = "音符_數字"
                        s1.oX = metePt2.x
                        s1.oY = metePt2.y
                        G.mete = s1.mete
                        G.mete2 = s1.mete2
                   Case Cg.rest:
                        
                        startPt.x = currX + s1.x
                        startPt.y = currY
                        s1.oX = startPt.x
                        s1.oY = startPt.y
                        MBG.setDataText startPt, s1, G.fontsize
                        MBG.nowPartLayer = partLayer
                        Set BNewObj = MBG.InsterRest '插入音符及指法
                   Case Cg.note:
                        '繪製音符********************************
                        Dim N As Integer
                        startPt.x = currX + s1.x
                        startPt.y = currY
                        s1.oX = startPt.x
                        s1.oY = startPt.y
                        MBG.setDataText startPt, s1, G.fontsize
                        MBG.nowPartLayer = partLayer
                        Set BNewObj = MBG.InsterEnt '插入音符及指法
                        
                        ''** 拍線計算 ***********************
                        nlast = s1.nflags
                        Temo1 = Fix(durationIndex / (Cg.BLEN / G.mete2)) ''取得未總加之前
                        durationIndex = durationIndex + s1.duration
                        
                        If (nlast > 0) Then
                            beamMuseList.Push s1
                             '這是要連結線的，以 m_Mete2 為時值
                            Temo2 = durationIndex - (Temo1 * (Cg.BLEN / G.mete2))
                            
                            If Temo2 Mod (Cg.BLEN / G.mete2) = 0 Or Temo2 > (Cg.BLEN / G.mete2) Then
                                MBG.draw_dur beamMuseList
                                beamMuseList.Clear
                            End If
                         ElseIf beamMuseList.Count >= 1 Then
                            MBG.draw_dur beamMuseList
                            beamMuseList.Clear
                        End If
                        
                        '*******繪製圓滑線'**************************************************************************************'
                        'AMT.iSlur = 7        ' 連音符行    (3456)
                        If s1.slurStart = True Then
                            Set mt_slur_left = New MusicBlockGraphics
                            Set mt_slur_left = MBG.copy
        
                        ElseIf s1.slurEnd = True Then
                        
                            If mt_slur_left Is Nothing Then
                                Set plineSlur = MBG.drawSlurStarTo(vo.children(0).oX, MBG)
                            Else
                                Set plineSlur = MBG.drawSlur(mt_slur_left, MBG)
                                Set mt_slur_left = Nothing
                            End If
                        End If
                        '*****************************************************************
                               
                                        
                
                        If s1.tupletStart = True Then
                            'Set mt_Tuplet_left = New MusicBlockGraphics
                            Set mt_tuplet_left = MBG.copy
        
                        ElseIf s1.tupletEnd = True Then
        
                            Set plineTuplet = MBG.drawTuplet(mt_tuplet_left, MBG, s1.tupletCount)
        
                        End If
                
                               
                   Case Else
                End Select
                
                
            Next
            
            If Not mt_slur_left Is Nothing Then
                '圓滑線是否未畫完
                Set plineSlur = MBG.drawSlurToEnd(mt_slur_left, s1.oX + s1.w)
                Set mt_slur_left = Nothing
            End If
        

        Next
    Next
  


End Sub

Private Sub draw_many_text1()
  
  
    Dim MBG As New MusicBlockGraphics
    
    '放置文字本
    Dim insPt As Variant
    Dim ipt As New point
    
    ' Return a point using a prompt
    insPt = ThisDrawing.Utility.GetPoint(, "\n選擇要插入的點 ：Enter insertion point: ")
    '插入設定資料文字說明
    Call inst_G(G, insPt)
'***********************************************************************************
    '畫出定位線-畫框
    Dim plineObj As AcadPolyline
    ipt = insPt
    Set plineObj = MBG.insterPositionBox(ipt, G)

'*********************************************************************************
    '插入單一標題
    Dim objText As AcadText
    Dim titlePT As Variant
    Dim ooPt As Variant
    titlePT = insPt
    titlePT(0) = titlePT(0) + (G.pagewidth / 2)
    titlePT(1) = titlePT(1) + G.fontsize * 5.5
    Set objText = ThisDrawing.ModelSpace.AddText(m_buf.getTITLE, titlePT, 6)
    ooPt = objText.insertionPoint
    objText.Layer = "TEXT"
    objText.Alignment = acAlignmentCenter
    objText.styleName = "文字"
    ooPt(0) = ooPt(0) + objText.insertionPoint(0)
    ooPt(1) = ooPt(1) + objText.insertionPoint(1)
    
    objText.Move objText.insertionPoint, ooPt
    
'*********************************************************************************
'建立主要的圖層
    Dim layerObj As AcadLayer
    Set layerObj = ThisDrawing.Layers.Add(MAINLAYER)


    Dim tmp_joinApp As New iArray
    Dim tmp_joinIds As New iArray
    'double lastTemp
    Dim tmp_track As Integer
    Dim tmp_track_item As Long
    Dim A_TEMPO_add As Integer

    Dim tmp_delaytime As Double  '計算拍子 是要計上一個字的長度
    
    Dim tmp_xy As point
    
    Dim BNewObj As AcadBlockReference
    Dim tmp_name As String
    
    'Dim cst As String
    'Dim cst_no_fing As String
    Dim ptGripMid As Variant
    Dim s1 As MusicItem
    
    tmp_delaytime = 0
    
    tmp_name = G.fontName
    Dim tmp_erhu_fing As ErhuFing
    Dim midDownPt(2) As Double
    Dim mt_slur_left As MusicBlockGraphics
    Dim mt_slur_right As MusicBlockGraphics
    Dim mt_trip_left As MusicBlockGraphics
    Dim mt_trip_right As MusicBlockGraphics
    Dim plineSlur As AcadLWPolyline
    Dim plineTuplet As AcadLWPolyline
    Dim barConfig(1000) As aBarConfig
    Dim barId As Integer
    
    'Dim sumLine As Integer  '計算第幾行
    'Dim sumMeasure As Integer  '計算每行的第幾行
    
  
        For tmp_track = 0 To m_buf.GetTrackSize() - 1
            'NewObj = Nothing
'lin            tmp_joinApp.clear()
            tmp_delaytime = 0
            A_TEMPO_add = 1
            tmp_joinApp.Clear
            tmp_joinIds.Clear
            
            G.durationIndex = 0
            G.currLine = 0
            G.currMeasure = 0
            For tmp_track_item = 0 To m_buf.GetTrackBufferSize(tmp_track) - 1

                '這是要連結線的，以 m_Mete2 為時值
                If G.durationIndex >= (Cg.BLEN / G.mete2 * A_TEMPO_add) Then
                    If A_TEMPO_add = G.mete Then
                        A_TEMPO_add = 1
                    Else
                        A_TEMPO_add = A_TEMPO_add + 1
                    End If

                    If tmp_joinIds.Count >= 1 Then
                        Dim pp As Long
                        'ReDim tmp_joinApp(tmp_joinIds.Count - 1)
'                        For pp = 0 To tmp_joinIds.Count - 1
'                            Set tmp_joinApp(pp) = tmp_joinIds(pp)
'                        Next
                        tmp_joinApp.PushArray tmp_joinIds
                        MBG.addMusicJoin tmp_joinApp
                        tmp_joinApp.Clear
                    End If
                    tmp_joinIds.Clear

                End If

                If (G.durationIndex >= (Cg.BLEN / G.mete2) * G.mete) Then
                    G.currMeasure = G.currMeasure + 1
                    G.durationIndex = 0

                    If G.currMeasure >= G.barsperstaff Then  '看每行小節數有沒有超過
                        G.currMeasure = 0
                        G.currLine = G.currLine + 1
                    End If
                End If


                Set s1 = m_buf.GetData(tmp_track, tmp_track_item)
                If (s1 Is Nothing) Then GoTo CallBackFor
                Select Case s1.typs
                   Case Cg.Config:
                        If (s1.barsperstaff >= 1 And tmp_track = 0) Then
                            G.barsperstaff = s1.barsperstaff
                            Set barConfig(barId) = New aBarConfig
                            barConfig(barId).barId = barId
                            barConfig(barId).barLineQuantity = s1.barsperstaff
                        If (s1.setbarstaffid > 1) Then
                            Set barConfig(setbarstaffid) = New aBarConfig
                            barConfig(setbarstaffid).barId = setbarstaffid
                            barConfig(setbarstaffid).barLineQuantity = s1.setbarstaff
                        End If
                        

                        
                        GoTo CallBackFor
                   Case Cg.meter:
                        If (tmp_track = 0) Then
                            G.mete = s1.mete
                            G.mete2 = s1.mete2
                            barConfig(barId).barId = barId
                            barConfig(barId).mete = s1.mete
                            barConfig(barId).mete2 = s1.mete2
                            
                        End If
                        
                        GoTo CallBackFor
                   Case Cg.rest, Cg.note:
                   Case Else
                End Select


                If s1.notes(0).mnote = " " Or s1.notes(0).mnote = "" Then
                    GoTo CallBackFor
                End If

'*******插入每行的小節線'**************************************************************************************'

                Dim ppnt As New point
                Dim bbo As Boolean
                ppnt.a insPt
                Call atDraw_BarLine(ppnt, tmp_track, G.currLine, G.currMeasure, G.durationIndex)

                
                If s1.notes(0).mnote = "." Then
                    Set tmp_xy = atBarXYpos(ppnt, tmp_track, G.currLine, G.currMeasure, G.durationIndex, True)
                Else
                    Set tmp_xy = atBarXYpos(ppnt, tmp_track, G.currLine, G.currMeasure, G.durationIndex, False)
                    'Set tmp_xy = atTableDraw(ppnt, tmp_track, tmp_AllTempo, False)
                End If



                Dim atPt As Variant
                atPt = tmp_xy.at
'**************************************************************************************'
'  插入MusicText 物件
'**************************************************************************************'
                If Me.chkOption1 = True Then
                    '(古箏用)
                    '圖塊用附號)
                    ppnt.a atPt
                    MBG.setDataText ppnt, s1, G.fontsize
                    Set BNewObj = MBG.InsterEnt '插入音符及指法



                ElseIf Me.chkOption2 = True Then

                '(二胡用)
                '這是沒有指法的
'                    AMT.iTONE = 1        ' * 行
'                    AMT.iFinge = 2    '這是指法行     _+)(*&
'                    AMT.iScale = 3    '這是高低音行   .,:
'                    AMT.iNote = 4     '這為主行       1234567.|l
'                    AMT.iTempo = 5    '這是拍子       -=368acefz
'                    AMT.iTowFinge = 6    '這是指法行第二行  _+)(*&
'                    AMT.iSlur = 7        ' 連音符行    (3456)


                    'Call NewObj.setData(atPt, cst_no_fing, G.fontName, G.FontSize)
                    'NewObj.Layer = "main"
                    tmp_erhu_fing.fing1 = 0

                    tmp_erhu_fing.Push = ""
                    tmp_erhu_fing.InOut = ""

                    '取得關鍵字 -指法1
                    Select Case s1.notes(0).mfingering
                       Case "0": tmp_erhu_fing.fing1 = tmp_erhu_fing.fing1 + amt.f空弦 '空弦
                       Case "1": tmp_erhu_fing.fing1 = tmp_erhu_fing.fing1 + amt.f一指
                       Case "2": tmp_erhu_fing.fing1 = tmp_erhu_fing.fing1 + amt.f二指
                       Case "3": tmp_erhu_fing.fing1 = tmp_erhu_fing.fing1 + amt.f三指
                       Case "4": tmp_erhu_fing.fing1 = tmp_erhu_fing.fing1 + amt.f四指
                       Case "W", "w": tmp_erhu_fing.fing1 = tmp_erhu_fing.fing1 + amt.f揉弦

                       Case "E", "e": tmp_erhu_fing.Push = "拉"
                       Case "V", "v": tmp_erhu_fing.Push = "推"
                       Case "Q", "q": tmp_erhu_fing.InOut = "內"
                       Case "A", "a": tmp_erhu_fing.InOut = "外"
                       Case Else
                    End Select

                    '取得關鍵字 -指法2
                    Select Case s1.notes(0).mtow_fingering
                       Case "0": tmp_erhu_fing.fing1 = tmp_erhu_fing.fing1 + amt.f空弦 '空弦
                       Case "1": tmp_erhu_fing.fing1 = tmp_erhu_fing.fing1 + amt.f一指
                       Case "2": tmp_erhu_fing.fing1 = tmp_erhu_fing.fing1 + amt.f二指
                       Case "3": tmp_erhu_fing.fing1 = tmp_erhu_fing.fing1 + amt.f三指
                       Case "4": tmp_erhu_fing.fing1 = tmp_erhu_fing.fing1 + amt.f四指
                       Case "W", "w": tmp_erhu_fing.fing1 = tmp_erhu_fing.fing1 + amt.f揉弦

                       Case "E", "e": tmp_erhu_fing.Push = "拉"
                       Case "V", "v": tmp_erhu_fing.Push = "推"
                       Case "Q", "q": tmp_erhu_fing.InOut = "內"
                       Case "A", "a": tmp_erhu_fing.InOut = "外"

                       Case Else
                    End Select

                    ppnt.x = atPt(0)
                    ppnt.y = atPt(1)
                    ppnt.Z = atPt(2)
                    MBG.setDataText ppnt, s1, G.fontsize
                    Set BNewObj = MBG.InsterEnt '插入音符及指法


                    '插入指法 附號(二胡用)
                    InsertErhuFinge ppnt, tmp_erhu_fing, G.fontsize

                End If

'*******插入圓滑線'**************************************************************************************'


                'AMT.iSlur = 7        ' 連音符行    (3456)
                If s1.slurStart = True Then
                    'Set mt_slur_left = New MusicBlockGraphics
                    Set mt_slur_left = MBG.copy

                ElseIf s1.slurEnd = True Then

                    Set plineSlur = MBG.drawSlur(mt_slur_left, MBG)

                End If
                
                
'*****************************************************************
                '連結線用

                tmp_joinIds.Push BNewObj
                Set BNewObj = Nothing

                Select Case (s1.notes(0).mnote)
                Case "|"
                    tmp_delaytime = 0
                Case "-"
                    tmp_delaytime = PARTITION_DEF
                Case "."
                    tmp_delaytime = tmp_delaytime / 2
                Case " "

                Case Else

                    Dim tempo_hj As String
                    Dim tempo_ll As Variant

                    tempo_hj = " -2=45368aAcCfFgGzZ"
                    tempo_ll = Array(1, 2, 2, 4, 4, 5, 3, 6, 8, 10, 10, 12, 12, 15, 15, 16, 16, 32, 32)

                    Dim ii As Integer
                    Dim cn As String
                    For ii = 0 To Len(tempo_hj) - 1
                        cn = Mid(tempo_hj, ii + 1, 1)
                        If cn = s1.notes(0).mtempo Then
                            tmp_delaytime = PARTITION_DEF / tempo_ll(ii)
                            Exit For
                        ElseIf s1.notes(0).mtempo = "" Then
                            tmp_delaytime = PARTITION_DEF
                            Exit For
                        Else
                            tmp_delaytime = 0
                        End If
                    Next ii
                End Select


                G.durationIndex = G.durationIndex + CInt(Fix(tmp_delaytime))
                
CallBackFor:
            Next
        Next

End Sub

Private Function InsertMusicText(insertionPoint() As Double, cst As String, size As Double)
'插入音附
    Dim textObj As AcadText
    Dim blockRefObj  As AcadBlockReference
    Dim textString As String
    Dim alignmentPoint(0 To 2) As Double
    Dim height As Double
    Dim midDownPt(0 To 2) As Double
    
    
    insertionPoint (0)
    insertionPoint (1)
    insertionPoint (2)
    
    Dim ipos As Integer
    Dim yAdd As Double
        '取得關鍵字  主音 AMT.iNote
    Select Case Mid(cst, amt.iNote, 1)
       Case "0": MFS.sNote = "M-NOTE0"
       Case "1": MFS.sNote = "M-NOTE1"
       Case "2": MFS.sNote = "M-NOTE2"
       Case "3": MFS.sNote = "M-NOTE3"
       Case "4": MFS.sNote = "M-NOTE4"
       Case "5": MFS.sNote = "M-NOTE5"
       Case "6": MFS.sNote = "M-NOTE6"
       Case "7": MFS.sNote = "M-NOTE7"
       Case ".": MFS.sNote = "M-NOTE."
       Case "-": MFS.sNote = "M-NOTE-"
       Case " ": MFS.sNote = ""
       Case Else
            MFS.sNote = ""
    End Select
    Dim midGirPnt(2) As Double
    
    If MFS.sNote <> "" Then
        Call ThisDrawing.ModelSpace.InsertBlock(insertionPoint, MFS.sNote, size, size, size, 0)
        

    End If

End Function

Private Sub CommandButton1_Click()
    Me.Hide
    TESTSTAR
End Sub
Public Sub TESTSTAR()
    '放置文字本
    Dim pt As Variant
    Dim insertionPoint(0 To 2) As Double
    
    ' Return a point using a prompt
    pt = ThisDrawing.Utility.GetPoint(, "\n選擇要插入的點 ：Enter insertion point: ")
    
    insertionPoint(0) = pt(0)
    insertionPoint(1) = pt(1)
    insertionPoint(2) = pt(2)
    InsertMusicStar insertionPoint, 3.5
End Sub




Private Function InsertErhuFinge(midDownPt As point, this_ef As ErhuFing, size As Double)
'插入二胡指法
    Dim textObj As AcadText
    Dim blockRefObj  As AcadBlockReference
    Dim textString As String
    Dim insertionPoint(0 To 2) As Double, alignmentPoint(0 To 2) As Double
    Dim height As Double
    

    insertionPoint(0) = midDownPt.x
    insertionPoint(1) = midDownPt.y
    insertionPoint(2) = midDownPt.Z
    
    Dim ipos As Integer
    Dim yAdd As Double
    ipos = 0
    yAdd = 0.7 '指法的向上增量
    If this_ef.fing1 <> 0 Then
        
        '看是否是圖塊
        If this_ef.fing1 And amt.f空弦 Then
            'Call ThisDrawing.ModelSpace.InsertBlock(insertionPoint, "二胡_空", 0.75, 0.75, 0.75, 0)
            textString = "\U+5B80"
            height = size * 0.47
            alignmentPoint(0) = insertionPoint(0) + (amt.A_TEXT_WIDTH * size / 2)
            alignmentPoint(1) = insertionPoint(1) + size * 2.13 + (ipos * yAdd * size)
            alignmentPoint(2) = insertionPoint(2)
            
            Set textObj = ThisDrawing.ModelSpace.AddText(textString, insertionPoint, height)
            textObj.Alignment = acAlignmentCenter
            textObj.TextAlignmentPoint = alignmentPoint
            textObj.styleName = "音符_數字"
            textObj.Layer = "裝飾符號"
        ipos = ipos + 1
        End If
        If this_ef.fing1 And amt.f揉弦 Then
            'textString = "\U+5B80"
            height = size * 0.47
            alignmentPoint(0) = insertionPoint(0) + (amt.A_TEXT_WIDTH * size / 2)
            alignmentPoint(1) = insertionPoint(1) + size * 2.13 + (ipos * yAdd * size)
            alignmentPoint(2) = insertionPoint(2)
            
            Set blockRefObj = ThisDrawing.ModelSpace.InsertBlock(alignmentPoint, "二胡_搰揉", 1#, 1#, 1#, 0)
            blockRefObj.Layer = "裝飾符號"
        ipos = ipos + 1
        End If
        '不是 就插入文字
        textString = ""
        If this_ef.fing1 And amt.f一指 Then
            textString = "Ⅰ"
        ElseIf this_ef.fing1 And amt.f二指 Then
            textString = "Ⅱ"
        ElseIf this_ef.fing1 And amt.f三指 Then
            textString = "Ⅲ"
        ElseIf this_ef.fing1 And amt.f四指 Then
            textString = "Ⅳ"
        End If
        If textString <> "" Then
            height = size * 0.47
            alignmentPoint(0) = insertionPoint(0) + (amt.A_TEXT_WIDTH * size / 2)
            alignmentPoint(1) = insertionPoint(1) + size * 2.13 + (ipos * yAdd * size)
            alignmentPoint(2) = insertionPoint(2)
            
            ' Create the text object in model space
            Set textObj = ThisDrawing.ModelSpace.AddText(textString, insertionPoint, height)
            textObj.Alignment = acAlignmentCenter
            textObj.TextAlignmentPoint = alignmentPoint
            textObj.styleName = "音符_數字"
            textObj.Layer = "SimpErhu符號"
            ipos = ipos + 1
        End If
        
    End If
    
    If this_ef.InOut <> "" Then
    '內外
        textString = this_ef.InOut
        height = size * 0.47
        
        alignmentPoint(0) = insertionPoint(0) + (amt.A_TEXT_WIDTH * size / 2)
        alignmentPoint(1) = insertionPoint(1) + (size * 2.13) + (ipos * yAdd * size)
        alignmentPoint(2) = insertionPoint(2)
        
        
        ' Create the text object in model space
        Set textObj = ThisDrawing.ModelSpace.AddText(textString, insertionPoint, height)
        textObj.Alignment = acAlignmentCenter
        textObj.TextAlignmentPoint = alignmentPoint
        textObj.styleName = "音符_數字"
        textObj.Layer = "裝飾符號"
        ipos = ipos + 1
    End If
    
        


    If this_ef.Push <> "" Then

        alignmentPoint(0) = insertionPoint(0) + (amt.A_TEXT_WIDTH * size / 2)
        alignmentPoint(1) = insertionPoint(1) + (size * 2.13) + (ipos * yAdd * size)
        alignmentPoint(2) = insertionPoint(2)

        If this_ef.Push = "拉" Then
            textString = "b拉"
        ElseIf this_ef.Push = "推" Then
            textString = "b推"
        End If
        
        Set blockRefObj = ThisDrawing.ModelSpace.InsertBlock(alignmentPoint, textString, size, size, size, 0)
       
        'blockRefObj.styleName = "SimpErhu"
        blockRefObj.Layer = "SimpErhu符號"
'
        ipos = ipos + 1
    End If
    
    
'    If this_ef.InOut <> "" Then
'    '內 外
'       '不是 就插入文字
'            textString = this_ef.InOut
'            height = size * 0.47
'            alignmentPoint(0) = insertionPoint(0)
'            alignmentPoint(1) = insertionPoint(1) + (size * 2.13) + (ipos * yAdd * size)
'            alignmentPoint(2) = insertionPoint(2)
'            ' Create the text object in model space
'            Set textObj = ThisDrawing.ModelSpace.AddText(textString, insertionPoint, height)
'            textObj.Alignment = acAlignmentCenter
'            textObj.TextAlignmentPoint = alignmentPoint
'            textObj.styleName = "音符_數字"
'            textObj.Layer = "裝飾符號"
''
'        ipos = ipos + 1
'    End If
'



End Function


Private Function atBarXYpos(ByVal the_pt As point, ByVal the_track As Integer, _
 ByVal the_line As Integer, ByVal the_measure As Integer, ByVal the_alltempo As Double, ByVal the_isDorp As Boolean) As point
'取得現在的物件位置
'atBarXYpos()
'*the_pt 原點
'*the_the_track 現在是第幾軌
'*the_line 現在是第幾行
'*the_measure 現在是第幾小節
'*the_allTempo 現在的拍長是多少
'*the_isDorp 現在是否是符點音符
'


    
    
    'Dim ROW_ALL_DEF As Integer
    Dim MeasureDEF As Integer
    'Dim tmp_modTempo As Integer
    'Dim row As Integer


    Dim tmp_modCol As Integer
    Dim Col As Double
    Dim col_b As Integer
    Dim tmp_barSpaceWidth As Double '一節的距離
    Dim tmp_rowspacing As Double '每行到每行的距離
    Dim tmp_NoteDist As Double   '每拍音符的相對位置
    

    tmp_barSpaceWidth = (G.pagewidth - G.LeftSpace - G.RightSpace) / G.barsperstaff   'x 軸用
    tmp_NoteDist = (tmp_barSpaceWidth - G.BarToNoteSpace * 2) / G.mete
    tmp_rowspacing = (G.TrackToTrack * (G.Many - 1) + G.LineToLine)             'y 軸用

    MeasureDEF = (G.mete * (Cg.BLEN / G.mete2))   '計算每小節有多少單位 (4拍全音符有多少單位)
    'tmp_modTempo = the_alltempo Mod MeasureDEF '全部除掉總單位時 後，看還有多少的 單位時
    '

    tmp_modCol = tmp_barSpaceWidth Mod G.mete2
    Col = the_alltempo / (Cg.BLEN / G.mete2)  '取得現在小節的第幾拍
    col_b = (Col Mod G.mete)  '取得每小節的第幾拍

    
    
    

    Static lastPoint As New point
    Dim pp As New point
    'col 是每一行的第幾拍，是以一拍為單位來數
    'tmp_modCol 是每一拍的第幾個字的位置
    pp.x = G.LeftSpace + the_measure * tmp_barSpaceWidth + G.BarToNoteSpace  '算出小節的位置 + 小節線到音符的空白
    'pp.x = pp.x + (CDbl(tmp_modCol) / CDbl(PARTITION_DEF / (4))) * (amt.LINE_LEN * G.FontSize) '除於 4分之一拍 的問題
    pp.x = pp.x + CDbl(Col) * tmp_NoteDist  '除於 4分之一拍 的問題

    pp.y = (G.TrackToTrack) * the_track + ((G.TrackToTrack) * (G.Many - 1) + G.LineToLine) * the_line
    pp.y = -pp.y


    '每節單位拍，的微調
    '例  1 5    2 6             1 5  2 6
    '    ----   ----  ->前進成  ---- ----
    '    123456789AB            123456789AB
    pp.x = pp.x + CDbl(Col) * G.Beat_MIN_X '微調
    '每一單位拍，的微調
    '例  1  5 3   2  6 4             1 53     2 64
    '    ---====  ---====  ->前進成  --==     --==
    '    123456789ABCDEF             123456789ABCDEF
    Static ismodcol As Integer
'    If tmp_modCol > 0 Then
'        ismodcol = ismodcol + 1
'        pp.x = pp.x + ismodcol * G.MIN_X  '微調
'    Else
'        ismodcol = 0
'    End If

    If the_isDorp Then '如果是符點音符，就前近一半
        pp.x = (lastPoint.x + pp.x) / 2
    End If
    
    '是否2個字太近壓到了
    '移至1個字的寬度
    If Abs(lastPoint.x - pp.x) <= amt.A_TEXT_WIDTH * G.fontsize Then
        pp.x = lastPoint.x + amt.A_TEXT_WIDTH * G.fontsize * 1.05
    End If
    
    Set lastPoint = pp  '存入最後的點
    
    
    Set atBarXYpos = New point
    atBarXYpos.x = pp.x + the_pt.x
    atBarXYpos.y = pp.y + the_pt.y
End Function

Private Function atDraw_BarLine(ByVal the_pt As point, ByVal the_track As Integer, _
 ByVal the_line As Integer, ByVal the_measure As Integer, ByVal the_alltempo As Double)
   
    Dim tmp_pLWPoly As AcadPolyline
    'Dim initPoint As New AcGePoint2d()
    Dim startPt As New point
    Dim endPt As New point
    Dim ptlist As New PointList
    
    Dim tmp_trackitem As Integer
    Dim tmp_bardist As Double '一節的距離
    Dim tmp_rowspacing As Double '每行到每行的距離
    
    If the_measure = 0 And the_alltempo = 0 Then
    '每行的第一小節，畫出每行的小節線
        tmp_bardist = (G.pagewidth - G.LeftSpace - G.RightSpace) / G.barsperstaff
        tmp_rowspacing = (G.TrackToTrack * (G.Many - 1) + G.LineToLine)
        '這是要畫小節線
        'ROW_ALL_DEF 是每行的總單位數應該多少，如 每小節2/4拍，每行有 7 個小節，則每行的 總單位時應該是 (240*2)*7=3360
        'row 第幾行
        'colunm 第幾欄(在第幾行的第幾欄)
        Dim ROW_ALL_DEF As Integer
        Dim tmp_modTempo As Integer
        'Dim row As Integer
    
        Dim tmp_modCol As Integer
        Dim Col As Integer
        Dim col_b As Integer
    
    
        ROW_ALL_DEF = (G.barsperstaff * G.mete * PARTITION_DEF / (G.mete2 / 4))
        tmp_modTempo = the_alltempo Mod ROW_ALL_DEF '全部除掉總單位時 後，看還有多少的 單位時
        'row = (the_alltempo - tmp_modTempo) \ ROW_ALL_DEF
    
        tmp_modCol = tmp_modTempo Mod (PARTITION_DEF / (G.mete2 / 4))
        Col = (tmp_modTempo - tmp_modCol) / (PARTITION_DEF / (G.mete2 / 4)) '取得每行的第幾拍
        col_b = (Col Mod G.mete)  '取得每小節的第幾拍
        
        If the_track = 0 Then '只有第一軌才要畫
            
            '這是在畫第一小節
    
            startPt.x = the_pt.x + G.LeftSpace
            startPt.y = -((amt.LINE_PASE + amt.DROP_UP) * G.fontsize) + tmp_rowspacing * the_line
            startPt.y = -startPt.y + the_pt.y

            endPt.x = the_pt.x + G.LeftSpace
            endPt.y = G.TrackToTrack * (G.Many - 1) + tmp_rowspacing * the_line
            endPt.y = -endPt.y + the_pt.y

            ptlist.Clear
            ptlist.Add startPt
            ptlist.Add endPt
            Set tmp_pLWPoly = ThisDrawing.ModelSpace.AddPolyline(ptlist.ToXYZList)
            tmp_pLWPoly.ConstantWidth = amt.BAR_WITCH * G.fontsize / 4.6
            tmp_pLWPoly.Layer = "bar"
        
            

            Dim j As Integer
            Dim barIndex As Integer
            For barIndex = 0 To G.barsperstaff - 1
                For j = 0 To G.Many - 1
    
    
                    startPt.x = the_pt.x + G.LeftSpace + tmp_bardist + barIndex * tmp_bardist
    
                    startPt.y = -((amt.LINE_PASE + amt.DROP_UP) * G.fontsize) + (G.TrackToTrack * j) + (tmp_rowspacing * the_line)
    
                    startPt.y = -startPt.y + the_pt.y
    
    
                    endPt.x = the_pt.x + G.LeftSpace + tmp_bardist + barIndex * tmp_bardist
    
                    endPt.y = (G.TrackToTrack * j) + (tmp_rowspacing * the_line)
    
                    endPt.y = -endPt.y + the_pt.y
    
                    ptlist.Clear
                    ptlist.Add startPt
                    ptlist.Add endPt
                    Set tmp_pLWPoly = ThisDrawing.ModelSpace.AddPolyline(ptlist.ToXYZList)
                    tmp_pLWPoly.ConstantWidth = amt.BAR_WITCH * G.fontsize / 4.6
                    tmp_pLWPoly.Layer = "bar"
                Next j
                'm_pLWPoly->setThickness(plineInfo.m_thick)
                'm_pLWPoly->setConstantWidth(plineInfo.m_width)

            Next barIndex
    
    
        End If
    End If
End Function





Private Function atTableDraw(ByVal the_pt As point, ByVal the_track As Integer, ByVal the_alltempo As Long, ByVal the_isDorp As Boolean) As point

'atTableDraw()
'*the_pt 原點
'*the_pt 現在是第幾軌
'*the_allTempo 現在的拍長是多少
'*the_isDorp 現在是否是符點音符
'


    atTableDraw_bar the_pt, the_track, the_alltempo
    
    Dim ROW_ALL_DEF As Integer
    Dim tmp_modTempo As Integer
    Dim row As Integer


    Dim tmp_modCol As Integer
    Dim Col As Integer
    Dim col_b As Integer


    ROW_ALL_DEF = (G.bar * G.mete * PARTITION_DEF / (G.mete2 / 4))
    tmp_modTempo = the_alltempo Mod ROW_ALL_DEF '全部除掉總單位時 後，看還有多少的 單位時
    row = (the_alltempo - tmp_modTempo) \ ROW_ALL_DEF

    tmp_modCol = tmp_modTempo Mod (PARTITION_DEF / (G.mete2 / 4))
    Col = (tmp_modTempo - tmp_modCol) / (PARTITION_DEF / (G.mete2 / 4)) '取得每行的第幾拍
    col_b = (Col Mod G.mete)  '取得每小節的第幾拍

    '傳出每節的相對位置
    Dim tmp_xbarInterval As Double
    tmp_xbarInterval = (G.pagewidth - G.LeftSpace - G.RightSpace) / ((G.bar * G.mete))

    Static lastPoint As New point
    Dim pp As New point
    'col 是每一行的第幾拍，是以一拍為單位來數
    'tmp_modCol 是每一拍的第幾個字的位置
    pp.x = G.LeftSpace + G.BarToNoteSpace + Col * tmp_xbarInterval
    pp.x = pp.x + (CDbl(tmp_modCol) / CDbl(PARTITION_DEF / (4))) * (amt.LINE_LEN * G.fontsize) '除於 4分之一拍 的問題

    pp.y = (G.TrackToTrack) * the_track + ((G.TrackToTrack) * (G.Many - 1) + G.LineToLine) * row
    pp.y = -pp.y
    pp.x = pp.x + the_pt.x

    '每節單位拍，的微調
    '例  1 5    2 6             1 5  2 6
    '    ----   ----  ->前進成  ---- ----
    '    123456789AB            123456789AB
    pp.x = pp.x + CDbl(col_b) * G.Beat_MIN_X '微調
    '每一單位拍，的微調
    '例  1  5 3   2  6 4             1 53     2 64
    '    ---====  ---====  ->前進成  --==     --==
    '    123456789ABCDEF             123456789ABCDEF
    Static ismodcol As Integer
    If tmp_modCol > 0 Then
        ismodcol = ismodcol + 1
        pp.x = pp.x + ismodcol * G.MIN_X  '微調
    Else
        ismodcol = 0
    End If
    pp.y = pp.y + the_pt.y
    If the_isDorp Then '如果是符點音符，就前近一半
        pp.x = (lastPoint.x + pp.x) / 2
    End If
    
    '是否2個字太近壓到了
    '移至1個字的寬度
    If Abs(lastPoint.x - pp.x) <= amt.A_TEXT_WIDTH * G.fontsize Then
        pp.x = lastPoint.x + amt.A_TEXT_WIDTH * G.fontsize * 1.05
    End If
    
    Set lastPoint = pp
    Set atTableDraw = pp
End Function

Private Function atTableDraw_bar(ByVal the_pt As point, ByVal the_track As Integer, ByVal the_alltempo As Long)
   
    Dim tmp_pLWPoly As AcadPolyline
    'Dim initPoint As New AcGePoint2d()
    Dim startPt As New point
    Dim endPt As New point
    Dim ptlist As New PointList
    
    Dim tmp_trackitem As Integer
    Dim tmp_bardist As Double '一節的距離
    Dim tmp_rowspacing As Double '每行到每行的距離

    tmp_bardist = (G.pagewidth - G.LeftSpace - G.RightSpace) / G.bar
    tmp_rowspacing = (G.TrackToTrack * (G.Many - 1) + G.LineToLine)
    '這是要畫小節線
    'ROW_ALL_DEF 是每行的總單位數應該多少，如 每小節2/4拍，每行有 7 個小節，則每行的 總單位時應該是 (240*2)*7=3360
    'row 第幾行
    'colunm 第幾欄(在第幾行的第幾欄)
    Dim ROW_ALL_DEF As Integer
    Dim tmp_modTempo As Integer
    Dim row As Integer

    Dim tmp_modCol As Integer
    Dim Col As Integer
    Dim col_b As Integer


    ROW_ALL_DEF = (G.bar * G.mete * PARTITION_DEF / (G.mete2 / 4))
    tmp_modTempo = the_alltempo Mod ROW_ALL_DEF '全部除掉總單位時 後，看還有多少的 單位時
    row = (the_alltempo - tmp_modTempo) \ ROW_ALL_DEF

    tmp_modCol = tmp_modTempo Mod (PARTITION_DEF / (G.mete2 / 4))
    Col = (tmp_modTempo - tmp_modCol) / (PARTITION_DEF / (G.mete2 / 4)) '取得每行的第幾拍
    col_b = (Col Mod G.mete)  '取得每小節的第幾拍
    
    If the_track = 0 Then '只有第一軌才要畫
        If Col = 0 And tmp_modCol = 0 Then '這是在第一小節

            startPt.x = the_pt.x + G.LeftSpace
            startPt.y = -((amt.LINE_PASE + amt.DROP_UP) * G.fontsize) + tmp_rowspacing * row
            startPt.y = -startPt.y + the_pt.y

            endPt.x = the_pt.x + G.LeftSpace
            endPt.y = G.TrackToTrack * (G.Many - 1) + tmp_rowspacing * row
            endPt.y = -endPt.y + the_pt.y

            ptlist.Clear
            ptlist.Add startPt
            ptlist.Add endPt
            Set tmp_pLWPoly = ThisDrawing.ModelSpace.AddPolyline(ptlist.ToXYZList)
            tmp_pLWPoly.ConstantWidth = amt.BAR_WITCH * G.fontsize / 4.6
            tmp_pLWPoly.Layer = "bar"
        End If

        If (Col Mod G.mete) = 0 And (tmp_modCol = 0) Then
            Dim j As Integer
            For j = 0 To G.Many - 1


                startPt.x = the_pt.x + G.LeftSpace + tmp_bardist + Col / G.mete * tmp_bardist

                startPt.y = -((amt.LINE_PASE + amt.DROP_UP) * G.fontsize) + (G.TrackToTrack * j) + (tmp_rowspacing * row)

                startPt.y = -startPt.y + the_pt.y


                endPt.x = the_pt.x + G.LeftSpace + tmp_bardist + Col / G.mete * tmp_bardist

                endPt.y = (G.TrackToTrack * j) + (tmp_rowspacing * row)

                endPt.y = -endPt.y + the_pt.y

                ptlist.Clear
                ptlist.Add startPt
                ptlist.Add endPt
                Set tmp_pLWPoly = ThisDrawing.ModelSpace.AddPolyline(ptlist.ToXYZList)
                tmp_pLWPoly.ConstantWidth = amt.BAR_WITCH * G.fontsize / 4.6
                tmp_pLWPoly.Layer = "bar"
            Next j
            'm_pLWPoly->setThickness(plineInfo.m_thick)
            'm_pLWPoly->setConstantWidth(plineInfo.m_width)

        End If


    End If

End Function



Private Sub UserForm_Initialize()
    Set rTime = New runTime
    AcadConnect

    Dim dd As Double
    Dim i As Integer
    '字型設定
    Me.cobFontName.AddItem "EUDC"
    Me.cobFontName.AddItem "細明體"
    Me.cobFontName.AddItem "華康行書體"
    Me.cobFontName.AddItem "標楷體"
    
    '字型大小設定
    For dd = 2 To 8 Step 0.5
        Me.cobFontSize.AddItem dd
    Next
    
    '幾聲部設定
    For i = 1 To 8
        Me.cobMany.AddItem i
    Next
    
    '幾拍設定
    Me.cobMete.AddItem "1/4"
    Me.cobMete.AddItem "2/4"
    Me.cobMete.AddItem "3/4"
    Me.cobMete.AddItem "4/4"
    Me.cobMete.AddItem "1/8"
    Me.cobMete.AddItem "3/8"
    Me.cobMete.AddItem "5/8"
    Me.cobMete.AddItem "7/8"
    
    
    
    '每行要幾小節設定
    For i = 2 To 12
        Me.cobBar.AddItem i
    Next
    
    Me.cobFontName.text = "EUDC"
    Me.cobFontSize.text = 4
    Me.cobMany.text = 1
    Me.cobMete.text = "4/4"
    Me.cobBar.text = 4

    Me.tbPageWidth = 210
    Me.tbLeftSpace = 12
    Me.tbRightSpace = 12
    Me.tbBarToNote = 2
    Me.tbTrackToTrack = 14
    Me.tbLineToLine = 19
    Me.tbMIN_X = 0.25
    
    AMT_LOAD '這個重要，設定初始資料
End Sub

Sub setLayoutMusicItem()


            G.currMeasure = 0
            For tmp_track_item = 0 To m_buf.GetTrackBufferSize(tmp_track) - 1

                '這是要連結線的，以 m_Mete2 為時值
                If G.durationIndex >= (PARTITION_DEF / (G.mete2 / 4) * A_TEMPO_add) Then
                    If A_TEMPO_add = G.mete Then
                        A_TEMPO_add = 1
                    Else
                        A_TEMPO_add = A_TEMPO_add + 1
                    End If

                    If tmp_joinIds.Count >= 1 Then
                        Dim pp As Long
                        'ReDim tmp_joinApp(tmp_joinIds.Count - 1)
'                        For pp = 0 To tmp_joinIds.Count - 1
'                            Set tmp_joinApp(pp) = tmp_joinIds(pp)
'                        Next
                        tmp_joinApp.PushArray tmp_joinIds
                        MBG.addMusicJoin tmp_joinApp
                        tmp_joinApp.Clear
                    End If
                    tmp_joinIds.Clear

                End If

                If (G.durationIndex >= PARTITION_DEF * G.mete) Then
                    G.currMeasure = G.currMeasure + 1
                    G.durationIndex = 0

                    If G.currMeasure >= G.barsperstaff Then  '看每行小節數有沒有超過
                        G.currMeasure = 0
                        G.currLine = G.currLine + 1
                    End If
                End If


                Set s1 = m_buf.GetData(tmp_track, tmp_track_item)

                Select Case s1.typs
                   Case Cg.bar:
                        G.barsperstaff = s1.barsperstaff
                        GoTo CallBackFor
                   Case Cg.meter:
                        G.mete = s1.mete
                        G.mete2 = s1.mete2
                        GoTo CallBackFor
                   Case Cg.rest, Cg.note:
                   Case Else
                End Select


End Sub

Function layoutMusicItem(spacing As Double, musicGroup()) As Double

    Dim currentduration
    Dim durationIndex   As Double
    Const Epsilon As Double = 0.0000001
    Dim spacingunit As Double
    Dim spacingUnits As Double
    Dim minSpace As Double
    Dim x As Double
    Dim i As Integer, j As Integer, k As Integer
    
    
    minSpace = 1000
    '這迴圈是設定 X 軸向
    Do While (finished(staffGroup.voices) = False)   ' Inner loop.
       Dim currVoice As VoiceElement
       Set currVoice = staffGroup.voices(1)
       Debug.Print currVoice.i
       
        
        '' 找到要在跨聲音的候選者之間佈置的第一個持續時間級別
        currentduration = Empty '' candidate smallest duration level
        For i = 0 To staffGroup.voices.Count - 1
            If currentduration = Empty Then
                currentduration = getDurationIndex(staffGroup.voices(i))
            Else
                If getDurationIndex(staffGroup.voices(i)) < currentduration Then
                    currentduration = getDurationIndex(staffGroup.voices(i))
                End If
            End If
        Next
        
        
              
        
        ''isolate voices at current duration level
        ''隔離目前持續時間等級的語音
        Dim currentvoices As New iArray ' VoiceElement[] = []
        Dim othervoices As New iArray ' VoiceElement[] = []
        currentvoices.Clear
        othervoices.Clear
        For i = 0 To staffGroup.voices.Count - 1
            durationIndex = getDurationIndex(staffGroup.voices(i))
            '' PER: Because of the inexactness of JS floating point math, we just get close.
            '' PER：由於 JS 浮點數學的不精確性，我們只是接近而已。
            If (durationIndex - currentduration > Epsilon) Then
                othervoices.Push staffGroup.voices(i)
                ''console.log("out: voice ",i)
             Else
                currentvoices.Push staffGroup.voices(i)
                ''if (debug) console.log("in: voice ",i)
            
            End If
        Next
        
         
        

        
        '' among the current duration level find the one which needs starting furthest right
        '' 在目前持續時間級別中找到需要從最右邊開始的持續時間級別
        spacingunit = 0 '' number of spacingunits coming from the previously laid out element to this one
        Dim spacingduration As Double
        For i = 0 To currentvoices.Count - 1
            
            If (layoutVoiceElement.getNextX(currentvoices(i)) > x) Then
                x = layoutVoiceElement.getNextX(currentvoices(i))
                spacingunit = layoutVoiceElement.getSpacingUnits(currentvoices(i))
                spacingduration = currentvoices(i).spacingduration
            End If
        Next
        spacingUnits = spacingUnits + spacingunit
        minSpace = Math.min(Array(minSpace, spacingunit))
        

        Dim lastTopVoice
        For i = 0 To currentvoices.Count - 1
            Dim v As VoiceElement
            Dim topVoice As VoiceElement
            Dim voicechildx As Double
            Dim dx As Double
            Set v = currentvoices(i)
            If (v.voicenumber = 0) Then lastTopVoice = i
            If lastTopVoice <> Empty And currentvoices(lastTopVoice).voicenumber <> v.voicenumber Then
                Set topVoice = currentvoices(lastTopVoice)
            Else
                Set topVoice = Nothing
            End If
            ''line 不知到 if (~isSameStaff(v, topVoice)) then   Set topVoice = Empty
            voicechildx = layoutVoiceElement.layoutOneItem(x, spacing, v, 0, topVoice)
            dx = voicechildx - x
            ''這是看是否有前倚音
            ''如果有，全部的音符就在加前倚音的距離
            If (dx > 0) Then
                x = voicechildx ''update x
                For j = 0 To i '' shift over all previously laid out elements
                    Call layoutVoiceElement.shiftRight(dx, currentvoices(j))
                Next
            End If
        Next

        '' remove the value of already counted spacing units in other voices
        '' (e.g.if a voice had planned to use up 5 spacing units but is not in line to be laid out at this duration level -
        '' where we've used 2 spacing units - then we must use up 3 spacing units, not 5)
        '' 刪除其他語音中已計算的間隔單位的值
        ''（例如，如果一個語音計劃使用 5 個間隔單位，但未在此持續時間級別上排列 -
        '' 我們使用了 2 個間隔單位 - 那麼我們必須用完3個間距單位，而非5 個）
        '' 測試後不需要
        For i = 0 To othervoices.Count - 1
            othervoices(i).spacingduration = othervoices(i).spacingduration - spacingduration
            Call layoutVoiceElement.updateNextX(x, spacing, othervoices(i))   '' adjust other voices expectations
        Next
        
                    
              
        '' 更新目前佈局元素的索引
        For i = 0 To currentvoices.Count - 1
            Dim voice As VoiceElement
            Set voice = currentvoices(i)
            '' 把每一個 voice.i 加 1 為下一個子元素
            '' 還有修改 voice.durationindex 加上現在已經讀取 的音符長度
            '' 4分音附=0.25 2分音附=0.5 全分音附=1
            '' 每一小節總長(分母)為 1
            Call layoutVoiceElement.updateIndices(voice)
        Next
    Loop
    i = i + 1
End Function

Attribute VB_Name = "frmInsText"
Attribute VB_Base = "0{0E113A70-83CE-47A6-8BB5-F23F8C66CC51}{AD2E7EE3-2E01-4EDC-BA82-9958CA9B5F14}"
Attribute VB_GlobalNameSpace = False
Attribute VB_Creatable = False
Attribute VB_PredeclaredId = True
Attribute VB_Exposed = False
Attribute VB_TemplateDerived = False
Attribute VB_Customizable = False

Option Explicit

Private Sub CommandButton1_Click()
    ' This example prompts for user input of a point. By using the
    ' InitializeUserInput method to define a keyword list, the example can also
    ' return keywords entered by the user.
    
    
    'Me.Hide
    ' Define the valid keywords
    Dim keywordList As String
    keywordList = "V Q W C 1 2 3 4 0"
    Dim strT As String
    
    Dim textObj As AcadText
    Dim textString As String
    Dim insertionPoint(0 To 2) As Double, alignmentPoint(0 To 2) As Double

    Dim height As Double
    Me.Hide
GoToLook:
'On Error GoTo ErrorHandler
On Error Resume Next

    ' Call InitializeUserInput to set up the keywords
    ThisDrawing.Utility.InitializeUserInput 128, keywordList
    ' Get the user input
    Dim returnPnt As Variant
    returnPnt = ThisDrawing.Utility.GetPoint(, "0 1 2 3 4 E(拉) V(推) Q(內) W(外) C(清除): ")
    
    If err Then
        '**Description 這個要改的
         If StrComp(err.Description, "使用者輸入的是關鍵字", 1) <> 0 Then
         ' One of the keywords was entered
             Dim inputString As String
             err.Clear
             inputString = ThisDrawing.Utility.GetInput
             '取得關鍵字
             Select Case inputString
                Case "0": strT = "b空絃"  '空弦
'                Case "1": strT = "Ⅰ"
'                Case "2": strT = "Ⅱ"
'                Case "3": strT = "Ⅲ"
'                Case "4": strT = "Ⅳ"
                Case "1": strT = "一"
                Case "2": strT = "二"
                Case "3": strT = "三"
                Case "4": strT = "四"
                Case Else
                    Dim ss As String
                    Dim data As Double
                    ss = Mid(inputString, 1, 1)
                    Select Case ss
                        Case "E", "e": lbPush_d ("拉")
                        Case "V", "v": lbPush_d ("推")
                        Case "Q", "q": lbInOut_d ("內")
                        Case "W", "w": lbInOut_d ("外")
                        Case "T", "t":
                        Case "S", "s":
                            data = Mid(inputString, 2, 10)
                            Me.tbSize = data
                        Case "X", "x":
                            data = Mid(inputString, 2, 10)
                            Me.tbX = data
                        Case "Y", "y":
                            data = Mid(inputString, 2, 10)
                            Me.tbY = data
                        Case "C", "c":
                        '清除全部
                            Me.lbInOut = ""
                            Me.lbInOut.SpecialEffect = fmSpecialEffectEtched
                            
                            Me.lbPush = ""
                            Me.lbPush.SpecialEffect = fmSpecialEffectEtched
                            
                            Me.tbT.text = ""
                            strT = ""
                        Case Else
                            Exit Sub
                    End Select
             End Select
             
             Me.tbT = strT
             
             GoTo GoToLook
         Else
             'MsgBox "Error selecting the point: " & Err.Description
             err.Clear
         End If
    Else
        ' Display point coordinates
        'MsgBox "The WCS of the point is: " & returnPnt(0) & ", " & returnPnt(1) & ", " & returnPnt(2), , "GetInput Example"
         
        ' Define the text object
        insertionPoint(0) = returnPnt(0) + Me.tbX
        insertionPoint(1) = returnPnt(1) + Me.tbY
        insertionPoint(2) = returnPnt(2)
        
        alignmentPoint(0) = insertionPoint(0)
        alignmentPoint(1) = insertionPoint(1)
        alignmentPoint(2) = insertionPoint(2)
        
        Dim ipos As Integer
        Dim yAdd As Double
        ipos = 0
        yAdd = 3 '指法的向上增量
        If Me.tbT <> "" Then
            If Mid(Me.tbT, 1, 1) = "b" Then
            '看是否是圖塊
                Select Case Me.tbT
                    Case "b空絃"
                        'Call ThisDrawing.ModelSpace.InsertBlock(insertionPoint, "二胡_空", 0.75, 0.75, 0.75, 0)
                        textString = "\U+5B80"
                        height = Me.tbSize
                        Set textObj = ThisDrawing.ModelSpace.AddText(textString, insertionPoint, height)
                        textObj.Alignment = acAlignmentCenter
                        textObj.TextAlignmentPoint = alignmentPoint
                        textObj.styleName = "音符_數字"
                        textObj.Layer = "裝飾符號"
                        

                    Case Else
                End Select
            Else
            '不是 就插入文字
                textString = Me.tbT
                height = Me.tbSize
                ' Create the text object in model space
                Set textObj = ThisDrawing.ModelSpace.AddText(textString, insertionPoint, height)
                textObj.Alignment = acAlignmentCenter
                textObj.TextAlignmentPoint = alignmentPoint
                textObj.styleName = "音符_數字"
                textObj.Layer = "裝飾符號"
            End If
            
            ipos = ipos + 1
        End If
        
        If Me.lbInOut.Caption <> "" Then
        
            textString = lbInOut.Caption
            height = Me.tbSize
            
                
            insertionPoint(0) = returnPnt(0) + Me.tbX
            insertionPoint(1) = returnPnt(1) + Me.tbY + (yAdd * ipos)
            insertionPoint(2) = returnPnt(2)
            
            alignmentPoint(0) = insertionPoint(0)
            alignmentPoint(1) = insertionPoint(1)
            alignmentPoint(2) = insertionPoint(2)
            
            
            ' Create the text object in model space
            Set textObj = ThisDrawing.ModelSpace.AddText(textString, insertionPoint, height)
            textObj.Alignment = acAlignmentCenter
            textObj.TextAlignmentPoint = alignmentPoint
            textObj.styleName = "音符_數字"
            textObj.Layer = "裝飾符號"
            ipos = ipos + 1
        End If
        
        Dim MtextObj As AcadMText
        If Me.lbPush.Caption <> "" Then

'            If Me.lbPush.Caption = "拉" Then
'                textString = "扱"
'            ElseIf Me.lbPush.Caption = "推" Then
'                textString = "憨"
'            End If
''
'            height = Me.tbSize * 2
'
'            insertionPoint(0) = returnPnt(0) + Me.tbX
'            insertionPoint(1) = returnPnt(1) + Me.tbY + (yAdd * ipos)
'            insertionPoint(2) = returnPnt(2)
'
'            alignmentPoint(0) = insertionPoint(0)
'            alignmentPoint(1) = insertionPoint(1)
'            alignmentPoint(2) = insertionPoint(2)
'
'            Set textObj = ThisDrawing.ModelSpace.AddText(textString, insertionPoint, height)
'            textObj.StyleName = "MMP2005"
'            textObj.Layer = "MMP2005符號"
'            textObj.Alignment = acAlignmentCenter
'            textObj.TextAlignmentPoint = alignmentPoint
'


            If Me.lbPush.Caption = "拉" Then
                textString = "\U+020C"
            ElseIf Me.lbPush.Caption = "推" Then
                textString = "\U+020A"
            End If
            
            height = Me.tbSize * 3.6
            
                
            insertionPoint(0) = returnPnt(0) + Me.tbX - 0.31
            insertionPoint(1) = returnPnt(1) + Me.tbY + (yAdd * ipos) - (Me.tbSize * 2.8)
            insertionPoint(2) = returnPnt(2)
            
            alignmentPoint(0) = insertionPoint(0)
            alignmentPoint(1) = insertionPoint(1)
            alignmentPoint(2) = insertionPoint(2)
            
            Set textObj = ThisDrawing.ModelSpace.AddText(textString, insertionPoint, height)
            textObj.styleName = "SimpErhu"
            textObj.Layer = "SimpErhu符號"
            textObj.Alignment = acAlignmentCenter
            textObj.TextAlignmentPoint = alignmentPoint
            
            ipos = ipos + 1
        End If
        
        
        
        'Err.clear
        GoTo GoToLook
    End If
ErrorHandler:

    
End Sub


Private Sub CommandButton2_Click()
'置換 推拉文字，改為 圖塊
On Error Resume Next
    Dim Object As Object
    Dim PickedPoint As Variant, TransMatrix As Variant, ContextData As Variant
    
        
TRYAGAIN:
        Me.Hide
While 1
    ' Get information about selected object
    ThisDrawing.Utility.GetSubEntity Object, PickedPoint, TransMatrix, ContextData


    Dim objText As AcadText
    Dim objBlock As AcadBlockReference
    Dim pt As Variant
    Dim SStr As String
    Dim insPt(2) As Double
        If (Object.objectName = "AcDbText") Then
            Set objText = Object
            
            If objText.textString = "\U+020A" Then
                insPt(0) = objText.insertionPoint(0) + 1.51
                insPt(1) = objText.insertionPoint(1) + 4.7
                insPt(2) = objText.insertionPoint(2)
                Set objBlock = ThisDrawing.ModelSpace.InsertBlock(insPt, "b推", 4, 4, 4, 0)
                objBlock.Layer = "裝飾符號"
                objText.Delete
            ElseIf objText.textString = "\U+020C" Then
                insPt(0) = objText.insertionPoint(0) + 1.51
                insPt(1) = objText.insertionPoint(1) + 4.65
                insPt(2) = objText.insertionPoint(2)
                Set objBlock = ThisDrawing.ModelSpace.InsertBlock(insPt, "b拉", 4, 4, 4, 0)
                objBlock.Layer = "裝飾符號"
                objText.Delete
            End If
        Else
            Exit Sub
        End If
Wend
    
End Sub

Private Sub lbPush_Click()
    
    
    If Me.lbPush.Caption = "拉" Then
        Me.lbPush.Caption = "推"
        Me.lbPush.SpecialEffect = fmSpecialEffectFlat
    ElseIf Me.lbPush.Caption = "推" Then
        Me.lbPush.Caption = ""
        Me.lbPush.SpecialEffect = fmSpecialEffectEtched
    Else
        Me.lbPush.Caption = "拉"
        Me.lbPush.SpecialEffect = fmSpecialEffectFlat
    End If
End Sub
Private Sub lbPush_d(data As String)
    If data = "推" Then
        Me.lbPush.Caption = "推"
        Me.lbPush.SpecialEffect = fmSpecialEffectFlat
    ElseIf data = "拉" Then
        Me.lbPush.Caption = "拉"
        Me.lbPush.SpecialEffect = fmSpecialEffectFlat
    End If
End Sub
Private Sub lbInOut_Click()
    If Me.lbInOut.Caption = "外" Then
        Me.lbInOut.Caption = "內"
        Me.lbInOut.SpecialEffect = fmSpecialEffectFlat
    ElseIf Me.lbInOut.Caption = "內" Then
        Me.lbInOut.Caption = ""
        Me.lbInOut.SpecialEffect = fmSpecialEffectEtched
    Else
        Me.lbInOut.Caption = "外"
        Me.lbInOut.SpecialEffect = fmSpecialEffectFlat
    End If
End Sub

Private Sub lbInOut_d(data As String)
    If data = "內" Then
        Me.lbInOut.Caption = "內"
        Me.lbInOut.SpecialEffect = fmSpecialEffectFlat
    ElseIf data = "外" Then
        Me.lbInOut.Caption = "外"
        Me.lbInOut.SpecialEffect = fmSpecialEffectFlat
    End If
End Sub

Attribute VB_Name = "frmMusical"
Attribute VB_Base = "0{AC271308-8FCE-429B-AD5A-2AC169648625}{F923A41B-3723-4424-A97C-44278AEC13C9}"
Attribute VB_GlobalNameSpace = False
Attribute VB_Creatable = False
Attribute VB_PredeclaredId = True
Attribute VB_Exposed = False
Attribute VB_TemplateDerived = False
Attribute VB_Customizable = False

Private Sub CommandButton1_Click()
    '插入單一Text
    Dim MusicText As NnmText
    Dim basePnt(0 To 2) As Double
    Dim cenPnt(0 To 2) As Double
    Dim returnPnt As Variant
    Dim pt As Variant
    Dim rad As Integer
    Me.Hide
    returnPnt = ThisDrawing.Utility.GetPoint(basePnt, "\n選擇要插入的點")
    

    'Set SEOBJ = New SmileyEntity
    pt = returnPnt
    Set MusicText = ThisDrawing.ModelSpace.AddCustomObject("MUSICTEXT")
    'Call MusicText.setNewObject(returnPnt, 1)
    Call MusicText.setData(pt, "ba!1=z", "MMP2005", 44)
    returnPnt(0) = returnPnt(0) + 31.83
    
End Sub

Private Sub CommandButton2_Click()
    '插入多個Text
    Dim MusicText As NnmText
    Dim basePnt(0 To 2) As Double
    Dim cenPnt(0 To 2) As Double
    Dim returnPnt As Variant
    Dim pt As Variant
    Dim rad As Integer
    Me.Hide
    returnPnt = ThisDrawing.Utility.GetPoint(basePnt, "\n選擇要插入的點")
    

    'Set SEOBJ = New SmileyEntity
    pt = returnPnt
    pt(0) = 0: pt(1) = 0: pt(2) = 0:
    Set MusicText = ThisDrawing.ModelSpace.AddCustomObject("MUSICTEXT")
    'Call MusicText.setNewObject(returnPnt, 1)
    Call MusicText.setData(returnPnt, "bf!1=z", "MMP2005", 44)
    returnPnt(0) = returnPnt(0) + 31.83
    Set MusicText = ThisDrawing.ModelSpace.AddCustomObject("MUSICTEXT")
    Call MusicText.setNewObject(returnPnt, 1)
    Call MusicText.setData(returnPnt, " A?2=c", "MMP2005", 44)
    returnPnt(0) = returnPnt(0) + 31.83
    Set MusicText = ThisDrawing.ModelSpace.AddCustomObject("MUSICTEXT")
    Call MusicText.setNewObject(returnPnt, 1)
    Call MusicText.setData(returnPnt, "#t.3=a", "MMP2005", 44)
    
End Sub

Private Sub CommandButton33_Click()
'取得物件 MusicText
'用x 軸來鏈結
On Error GoTo EndJoin

    Dim ent As Object
    Me.Hide

StartJoin:
    Dim SSetColl As AcadSelectionSets
    Set SSetColl = ThisDrawing.SelectionSets
    
    ' Create a SelectionSet named "TEST" in the current drawing
    Dim ssetObj As AcadSelectionSet
  

    If SSetColl.Count > 0 Then
        SSetColl.item(0).Delete
    End If
    Set ssetObj = SSetColl.Add("TEST")

    ssetObj.SelectOnScreen
    
    '排序陣列
    Dim TheArray As Variant
    Dim TheArrayEnt As Variant
    Dim coI As Integer
    Dim i As Long
    
    ' Add the dimstyle to the dimstyles collection
    coI = 0
  ' 找出圖面中的每一個選集
    For Each ent In ssetObj
        If (ent.objectName = "MusicText") Then
            coI = coI + 1
        End If
    Next
    
    '只有一個，不用排序了
    If coI < 1 Then
        GoTo StartJoin
    End If
    
    ReDim TheArray(coI - 1)
    ReDim TheArrayEnt(coI - 1)
    
    coI = 0
    Dim MTobj As NnmText
    Dim pt As Variant
    For Each ent In ssetObj
        If (ent.objectName = "MusicText") Then
            pt = ent.insertionPoint()
            TheArray(coI) = pt(0)
            Set TheArrayEnt(coI) = ent
            coI = coI + 1
        End If
    Next
    
    
    
    '排序開始
    SelectionSortMaxTow TheArray, TheArrayEnt
    
    For i = 0 To UBound(TheArray)
        If i = 0 Then
            TheArrayEnt(i).LeftLink = 0
            TheArrayEnt(i).RightLink = TheArrayEnt(i + 1).ObjectID
        ElseIf i = UBound(TheArray) Then
            TheArrayEnt(i).LeftLink = TheArrayEnt(i - 1).ObjectID
            TheArrayEnt(i).RightLink = 0
        Else
            TheArrayEnt(i).RightLink = TheArrayEnt(i + 1).ObjectID
        End If
        TheArrayEnt(i).Update
    Next
GoTo StartJoin

EndJoin:
End Sub

Private Sub CommandButton3_Click()

'取得物件 MusicText
'用x 軸來鏈結
On Error GoTo EndJoin

    Dim ent As Object
    Me.Hide

StartJoin:
    Dim SSetColl As AcadSelectionSets
    Set SSetColl = ThisDrawing.SelectionSets
    
    ' Create a SelectionSet named "TEST" in the current drawing
    Dim ssetObj As AcadSelectionSet
  

    If SSetColl.Count > 0 Then
        SSetColl.item(0).Delete
    End If
    Set ssetObj = SSetColl.Add("TEST")

    ssetObj.SelectOnScreen
    
    '排序陣列
    Dim TheArray As Variant
    Dim TheArrayEnt As Variant
    Dim coI As Integer
    Dim i As Long
    
    ' Add the dimstyle to the dimstyles collection
    coI = 0
  ' 找出圖面中的每一個選集
    For Each ent In ssetObj
        If (ent.objectName = "MusicText") Then
            coI = coI + 1
        End If
    Next
    
    ReDim TheArray(coI - 1)
    ReDim TheArrayEnt(coI - 1)
    
    coI = 0
    Dim MTobj As NnmText
    Dim pt As Variant
    For Each ent In ssetObj
        If (ent.objectName = "MusicText") Then
            pt = ent.insertionPoint()
            TheArray(coI) = pt(0)
            Set TheArrayEnt(coI) = ent
            coI = coI + 1
        End If
    Next
    
    Me.addMusicJoin TheArrayEnt
EndJoin:
End Sub

Private Sub CommandButton4_Click()
'清除 MusicText 的鏈結
On Error Resume Next
    Dim ent As Object

   
    Dim SSetColl As AcadSelectionSets
    Set SSetColl = ThisDrawing.SelectionSets
    
    ' Create a SelectionSet named "TEST" in the current drawing
    Dim ssetObj As AcadSelectionSet
  
    If SSetColl.Count > 0 Then
        SSetColl.item(0).Delete
    End If
    Set ssetObj = SSetColl.Add("TEST")
    Me.Hide
    ssetObj.SelectOnScreen
    
    '排序陣列
    Dim TheArray As Variant
    Dim TheArrayEnt As Variant
    Dim coI As Integer
    Dim i As Long
    
    ' Add the dimstyle to the dimstyles collection
    coI = 0
  ' 找出圖面中的每一個選集
    For Each ent In ssetObj
        If (ent.objectName = "MusicText") Then
            ent.RightLink = 0
            ent.LeftLink = 0
        End If
    Next
End Sub


Public Function addMusicJoin(ByVal the_Ids As Variant)

'取得物件 MusicText
'用x 軸來鏈結
On Error Resume Next

    Dim ent As Object
    
    '排序陣列
    Dim TheArray As Variant
    Dim TheArrayEnt As Variant
    Dim coI As Integer
    Dim i As Long
    
    ' Add the dimstyle to the dimstyles collection
    coI = 0
  ' 找出圖面中的每一個選集
    For i = 0 To UBound(the_Ids, 1)
        If the_Ids(i).objectName = "MusicText" Then
            coI = coI + 1
        End If
    Next

    
    '只有一個，不用排序了
    If coI < 1 Then
        Exit Function
    End If
    
    ReDim TheArray(coI - 1)
    ReDim TheArrayEnt(coI - 1)
    
    coI = 0
    Dim MTobj As NnmText
    Dim pt As Variant
    
    For i = 0 To UBound(the_Ids, 1)
        Set ent = the_Ids(i)
        If (ent.objectName = "MusicText") Then
            pt = ent.insertionPoint()
            TheArray(coI) = pt(0)
            Set TheArrayEnt(coI) = ent
            coI = coI + 1
            
            
            Dim minExt As Variant
            Dim maxExt As Variant
    
            ent.GetBoundingBox minExt, maxExt
            Set MTobj = ent
            minExt = MTobj.GripLeft()
            
            
        End If
    Next
    
    
    
    '排序開始
    SelectionSortMaxTow TheArray, TheArrayEnt
    
    For i = 0 To UBound(TheArray)
        If i = 0 Then
            TheArrayEnt(i).LeftLink = 0
            TheArrayEnt(i).RightLink = TheArrayEnt(i + 1).ObjectID
        ElseIf i = UBound(TheArray) Then
            TheArrayEnt(i).LeftLink = TheArrayEnt(i - 1).ObjectID
            TheArrayEnt(i).RightLink = 0
        Else
            TheArrayEnt(i).RightLink = TheArrayEnt(i + 1).ObjectID
        End If
        TheArrayEnt(i).Update
    Next


EndJoin:
End Function

Sub getGrip()

End Sub
        

Public Function eraseMTlink(ByVal the_id As Variant)
End Function

Private Sub CommandButton5_Click()

Dim ttt As NnmText
Dim minExt As Variant
    Dim maxExt As Variant
    
    
    lineObj.GetBoundingBox

    ttt.GetBoundingBox minExt, maxExt
End Sub


Private Sub CommandButton6_Click()

'取得 grip 數值

On Error Resume Next
    Dim Object As Object
    Dim PickedPoint As Variant, TransMatrix As Variant, ContextData As Variant
    
        
TRYAGAIN:
        Me.Hide

    ' Get information about selected object
    ThisDrawing.Utility.GetSubEntity Object, PickedPoint, TransMatrix, ContextData


    Dim MTobj As NnmText
    Dim pt As Variant
    Dim SStr As String
    
        If (Object.objectName = "MusicText") Then
            Set MTobj = Object
            
            pt = MTobj.GripLeft()
            SStr = "GripLeft = " & Format(pt(0), "0.00") & ", " & Format(pt(1), "0.00") & vbCrLf
            
            pt = MTobj.GripMid()
            SStr = SStr & "nGripMid = " & Format(pt(0), "0.00") & ", " & Format(pt(1), "0.00") & vbCrLf
            
            pt = MTobj.GripRight()
            SStr = SStr & "nGripRight = " & Format(pt(0), "0.00") & ", " & Format(pt(1), "0.00") & vbCrLf
             
            pt = MTobj.GripLeftDown()
            SStr = SStr & "nGripLeftDown = " & Format(pt(0), "0.00") & ", " & Format(pt(1), "0.00") & vbCrLf
            
            pt = MTobj.GripMidUp()
            SStr = SStr & "nGripMidUp = " & Format(pt(0), "0.00") & ", " & Format(pt(1), "0.00") & vbCrLf
            
            
            ThisDrawing.Utility.Prompt SStr
        End If
End Sub







Private Sub CommandButton7_Click()
    ' This example returns the current layer
    ' and then adds a new layer.
    ' Finally, it returns the layer to the previous setting.
    Dim currLayer As AcadLayer
    Dim newLayer As AcadLayer
    
    ' Return the current layer of the active document
    Set currLayer = ThisDrawing.ActiveLayer
    MsgBox "The current layer is " & currLayer.Name, vbInformation, "ActiveLayer Example"
    
    ' Create a Layer and make it the active layer
    Dim i As Integer
    For i = 0 To ThisDrawing.Layers.Count - 1
        Set newLayer = ThisDrawing.Layers(i)
        Me.TextBox1 = Me.TextBox1 & "datalayer(i,1) = """ & newLayer.Name & """ : datalayer(i,2) =  " & newLayer.TrueColor.ColorIndex & vbCrLf
        
        
    Next
    
End Sub

Private Sub CommandButton8_Click()
    Dim TextColl As AcadTextStyles
    Set TextColl = ThisDrawing.TextStyles
    
    ' Create a Text style named "TEST" in the current drawing
    Dim textStyle As AcadTextStyle
    
    Dim i As Integer
    For i = 0 To ThisDrawing.TextStyles.Count - 1
        Set textStyle = ThisDrawing.TextStyles(i)
        Me.TextBox1 = Me.TextBox1 & "dataStyles(" & i & ",1)=""" & textStyle.Name & """" & vbCrLf _
            & "dataStyles(" & i & ",2)=""" & textStyle.fontFile & """" & vbCrLf _
            & "dataStyles(" & i & ",3)=""" & textStyle.BigFontFile & """" & vbCrLf
    Next
    
    
End Sub



Private Sub CommandButton9_Click()
    Dim str As Variant
    Dim i As Integer
    str = GetWindowsFonts
    
    For i = 0 To UBound(str)
        Me.TextBox1 = Me.TextBox1 & str(i) & vbCrLf
    Next
End Sub

Attribute VB_Name = "frmPoline2Txt"
Attribute VB_Base = "0{80BB4D3A-A7D2-464E-9B74-A5183D25E0A9}{8B9C3245-ECA5-4738-9FE9-990283CBBED3}"
Attribute VB_GlobalNameSpace = False
Attribute VB_Creatable = False
Attribute VB_PredeclaredId = True
Attribute VB_Exposed = False
Attribute VB_TemplateDerived = False
Attribute VB_Customizable = False

Option Explicit


    Dim g_object As AcadLWPolyline
Function get_mulitpoint() As Integer
    Dim str As String
    Dim i As Integer
    Dim getPT As Double
    Dim ina As Integer
    str = ""
    If (g_object.objectName <> "AcDbPolyline") Then
        get_mulitpoint = 1
        Exit Function
    End If
    Dim pointWCS(2) As Double
    Dim pointUCS As Variant
    pointWCS(0) = 0#
    pointWCS(1) = 0#
    pointWCS(2) = 0#
    


    For i = 0 To UBound(g_object.Coordinates)
        getPT = g_object.Coordinates(i)
        If (i Mod 2) = 0 Then
            pointWCS(0) = getPT
            pointUCS = ThisDrawing.Utility.TranslateCoordinates(pointWCS, acWorld, acUCS, False)
            ina = pointUCS(0)
        Else
            pointWCS(1) = getPT
            pointUCS = ThisDrawing.Utility.TranslateCoordinates(pointWCS, acWorld, acUCS, False)
            ina = pointUCS(1)
        End If
        
        If i = 0 Then
            str = ina
        Else
            str = str & "," & ina
        End If
        If Len(str) > 200 Then
            ThisDrawing.Utility.Prompt (str)
            str = ""
        End If
    Next
    ThisDrawing.Utility.Prompt (str)
    Me.TextBox1 = Me.TextBox1 & str
    get_mulitpoint = 0
End Function

Sub Example_SelectOnScreen() 'AutoCAD 取得 LWPolyLine 的各點
 ' Have the user enter a point
    Dim pointG As Variant
    pointG = ThisDrawing.Utility.GetPoint(, "Enter a point to translate:")
    

    Dim ucsObj As AcadUCS
    Dim origin(0 To 2) As Double
    Dim xAxisPnt(0 To 2) As Double
    Dim yAxisPnt(0 To 2) As Double
    
    ' Define the UCS
    xAxisPnt(0) = pointG(0) + 5: xAxisPnt(1) = pointG(1): xAxisPnt(2) = pointG(2)
    yAxisPnt(0) = pointG(0): yAxisPnt(1) = pointG(1) + 5: yAxisPnt(2) = pointG(2)
    
    ' Add the UCS to the UserCoordinatesSystems collection
    Set ucsObj = ThisDrawing.UserCoordinateSystems.Add(pointG, xAxisPnt, yAxisPnt, "New_UCS")
    ThisDrawing.ActiveUCS = ucsObj


    
    ' Create the selection set
    Dim ssetObj As AcadSelectionSet
    'Set ssetObj = ThisDrawing.SelectionSets.Add("TEST_SSET")
    If ThisDrawing.SelectionSets.Count = 0 Then
        Set ssetObj = ThisDrawing.SelectionSets.Add("TEST_SSET")
    Else
        Set ssetObj = ThisDrawing.SelectionSets.item(0)
        ssetObj.Clear
    
    End If
    
    ' Add objects to a selection set by prompting user to select on the screen
    ssetObj.SelectOnScreen
    ssetObj.item (0)
    Dim returnPnt As Variant
    Dim str As String
    Dim strAll As String
    Dim i As Integer
    Dim ina As Integer
    Dim counta As Integer
    counta = ssetObj.Count()
    
    str = ""
    strAll = ""
    ThisDrawing.Utility.Prompt ("drawXY=")
    
    ' Return a point using a prompt
    ' Translate the point into UCS coordinates
    For i = 0 To counta - 1
        Set g_object = ssetObj.item(i)
        ina = get_mulitpoint
        If (i <> counta - 1) And (ina = 0) Then
            ThisDrawing.Utility.Prompt (",o,")
            
            Me.TextBox1 = Me.TextBox1 & ",o,"
        End If
    Next


End Sub



Sub scale_SelectOnScreen() 'AutoCAD 取得 LWPolyLine 的各點
 ' Have the user enter a point
    Dim pointG As Variant
    pointG = ThisDrawing.Utility.GetPoint(, "Enter a point to translate:")
    

    Dim ucsObj As AcadUCS
    Dim origin(0 To 2) As Double
    Dim xAxisPnt(0 To 2) As Double
    Dim yAxisPnt(0 To 2) As Double
    
    ' Define the UCS
    origin(0) = pointG(0): origin(1) = pointG(1): origin(2) = pointG(2)
    xAxisPnt(0) = pointG(0) + 5: xAxisPnt(1) = pointG(1): xAxisPnt(2) = pointG(2)
    yAxisPnt(0) = pointG(0): yAxisPnt(1) = pointG(1) + 5: yAxisPnt(2) = pointG(2)
    


    
    ' Create the selection set
    Dim ssetObj As AcadSelectionSet
    'Set ssetObj = ThisDrawing.SelectionSets.Add("TEST_SSET")
    If ThisDrawing.SelectionSets.Count = 0 Then
        Set ssetObj = ThisDrawing.SelectionSets.Add("TEST_SSET")
    Else
        Set ssetObj = ThisDrawing.SelectionSets.item(0)
        ssetObj.Clear
    
    End If
    
    ' Add objects to a selection set by prompting user to select on the screen
    ssetObj.SelectOnScreen
    ssetObj.item (0)
    Dim returnPnt As Variant
    Dim str As String
    Dim dd As AcadLWPolyline
    Dim i As Integer
    Dim ina As Integer
    Set dd = ssetObj.item(0)
    str = ""
    ' Return a point using a prompt
        ' Translate the point into UCS coordinates
    Dim pointWCS(2) As Double
    Dim pointUCS As Variant
    pointWCS(0) = 0#
    pointWCS(1) = 0#
    pointWCS(2) = 0#
    

    dd.ScaleEntity pointG, 1.03179

    'ThisDrawing.Utility.Prompt (str)
    Me.TextBox1 = str

End Sub



Private Sub CommandButton1_Click()
    Me.TextBox1 = ""
    Me.Hide
    Example_SelectOnScreen
    Me.Show
End Sub

Private Sub CommandButton2_Click()

'使用 VB 建立線： (工程引用'AutoCad 2004 Type Library')
     On Error Resume Next
'    Dim acadApp As AcadApplication
'    Set acadApp = GetObject(, "AutoCAD.Application.16")
'    If Err Then
'        Err.clear
'        Set acadApp = CreateObject("AutoCAD.Application.16")
'        If Err Then
'            MsgBox Err.Description
'            Exit Sub
'        End If
'    End If
'    acadApp.Visible = True
'    Dim acadDoc As AcadDocument
'    Set acadDoc = acadApp.ActiveDocument
    

    Dim plineObj As AcadPolyline
    Dim stXY() As String
    Dim ReadData() As String
    Dim pt(1000, 2) As Double
    Dim ptlist() As Double
  
    
    Dim ssst As String
    ssst = Replace(Me.TextBox1, vbCrLf, ",")
    ssst = Replace(ssst, vbTab, ",")
    ssst = Replace(ssst, ",", ",")
    ssst = Replace(ssst, "  ", ",")
    ssst = Replace(ssst, "  ", ",")
    
    ReadData = Split(ssst, ",")
    
    Dim i As Integer
    Dim posI As Integer
    Dim chkXY As Integer
    
    posI = 0
    chkXY = 0
    For i = 0 To UBound(ReadData)
        If ReadData(i) <> "" Then
            If chkXY = 0 Then
                pt(posI, 0) = ReadData(i)
                chkXY = 1
            Else
                pt(posI, 1) = ReadData(i)
                posI = posI + 1
                chkXY = 0
            End If
        End If
    Next
    If posI <= 1 Then
        Exit Sub
    End If
    ReDim ptlist((posI * 3) - 1)
    Dim iScale As Double
    iScale = tbSCALE
    If iScale = 0 Then
        iScale = 1
    End If
    
    For i = 0 To posI
        ptlist(i * 3) = pt(i, 0) * iScale
        ptlist(i * 3 + 1) = pt(i, 1) * iScale
    Next
    
    Dim pointG As Variant
    pointG = ThisDrawing.Utility.GetPoint(, "要畫的原點:")
    
    Dim ucsObj As AcadUCS
    Dim origin(0 To 2) As Double
    Dim xAxisPnt(0 To 2) As Double
    Dim yAxisPnt(0 To 2) As Double
    
    ' Define the UCS
    xAxisPnt(0) = pointG(0) + 5: xAxisPnt(1) = pointG(1): xAxisPnt(2) = pointG(2)
    yAxisPnt(0) = pointG(0): yAxisPnt(1) = pointG(1) + 5: yAxisPnt(2) = pointG(2)
    
    ' Add the UCS to the UserCoordinatesSystems collection
    Set ucsObj = ThisDrawing.UserCoordinateSystems.Add(pointG, xAxisPnt, yAxisPnt, "New_UCS")
    ThisDrawing.ActiveUCS = ucsObj
    
    
    Set plineObj = ThisDrawing.ModelSpace.AddPolyline(ptlist)
    
    
    ZoomAll
    
'    Set acadDoc = Nothing
'    Set acadApp = Nothing
   
End Sub

Attribute VB_Name = "iABetterArray"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Attribute VB_Description = "An array class for VBA providing features found in more modern languages "
'@Folder("VBABetterArray")
'@ModuleDescription("An array class for VBA providing features found in more modern languages ")
' Copyright (c) 2021 Nick Morgan. See License: https://github.com/Senipah/VBA-Better-Array/blob/master/LICENSE
'@IgnoreModule IIfSideEffect, AssignmentNotUsed, FunctionReturnValueDiscarded, ProcedureNotUsed, FunctionReturnValueNotUsed, FunctionReturnValueAlwaysDiscarded

Option Explicit

'''''''''''''''''''
' Constant Fields '
'''''''''''''''''''

Private Const DEFAULT_CAPACITY As Long = 4
' NOTE: placeholder
Private Const MAX_ARRAY_LENGTH As Long = &H7FEFFFFF
Private Const OBJECT_REPR As String = "OBJECT"
Private Const MISSING_LONG As Long = -9999
Private Const CHR_QUOTE As String = """"
Private Const CHR_COMMA As String = ","

Public Enum ArrayTypes
    BA_UNDEFINED
    BA_UNALLOCATED
    BA_ONEDIMENSION
    BA_MULTIDIMENSION
    BA_JAGGED
End Enum

' Public scope as used in unit tests
Public Enum ErrorCodes
    EC_START = vbObjectError + 512
    EC_EXPECTED_RANGE_OBJECT
    EC_EXPECTED_COLLECTION_OBJECT
    EC_MAX_DIMENSIONS_LIMIT
    EC_EXCEEDS_MAX_SORT_DEPTH
    EC_EXPECTED_JAGGED_ARRAY
    EC_EXPECTED_MULTIDIMENSION_ARRAY
    EC_EXPECTED_ARRAY
    EC_NULL_STRING
    EC_UNALLOCATED_ARRAY
    EC_UNDEFINED_ARRAY
    EC_INVALID_MULTIDIMENSIONAL_ARRAY_OPERATION
    EC_EXPECTED_VARIANT_ARRAY
    EC_EXCEEDS_MAX_ARRAY_LENGTH
    EC_STRING_TYPE_EXPECTED
    EC_CANNOT_CONVERT_TO_REQUESTED_STRUCTURE
    EC_CANNOT_SORT_OBJECTS
    EC_END
End Enum

Public Enum ComparisonType
    CT_EQUALITY
    CT_LIKENESS
End Enum

Public Enum SortMethods
    SM_TIMSORT
    SM_QUICKSORT_RECURSIVE
    SM_QUICKSORT_ITERATIVE
End Enum

Private Type ErrorDefinition
    Number As Long
    source As String
    Description As String
End Type


''''''''''
' Fields '
''''''''''

Private Type TFields
    Capacity As Long
    Length As Long
    LowerBound As Long
    Items() As Variant
    ArrayType As ArrayTypes
    ErrorDefinitions(EC_START To EC_END) As ErrorDefinition
    LowerBoundSet As Boolean
    SortMethod As SortMethods
End Type

Private Type TString
    text As String
    Length As Long
    ByteLength As Long
End Type

Private This As TFields

'@Description("Constructor")
Private Sub Class_Initialize()
Attribute Class_Initialize.VB_Description = "Constructor"
    Me.Capacity = DEFAULT_CAPACITY
    This.ArrayType = BA_UNALLOCATED
    PopulateErrorDefinitions
End Sub

'''''''''''''''''''''
' Public Properties '
'''''''''''''''''''''

'@Description("Returns the capacity of the internal array.")
Public Property Get Capacity() As Long
Attribute Capacity.VB_Description = "Returns the capacity of the internal array."
    Capacity = This.Capacity
End Property

'@Description("Sets the capacity of the internal array.")
'@Ignore ProcedureNotUsed
Public Property Let Capacity(ByVal value As Long)
Attribute Capacity.VB_Description = "Sets the capacity of the internal array."
    '@Ignore FunctionReturnValueDiscarded
    If value < 0 Then err.Raise 9
    If value <> This.Capacity Then
        If This.Capacity > 0 Then
            If GetArrayLength(This.Items) <> value Then
                Dim NewItems() As Variant
                NewItems = This.Items
                ReDim Preserve NewItems(This.LowerBound To (value + This.LowerBound - 1))
                InternalItems = NewItems
            End If
        Else
            ReDim This.Items(This.LowerBound To (DEFAULT_CAPACITY + This.LowerBound - 1))
        End If
        This.Capacity = UBound(This.Items) - This.LowerBound + 1
    End If
End Property

'@Description("Returns the number of entries stored in the array.")
Public Property Get Length() As Long
Attribute Length.VB_Description = "Returns the number of entries stored in the array."
    Length = This.Length
End Property

'@Description("Returns largest used index in the array.")
Public Property Get UpperBound() As Long
Attribute UpperBound.VB_Description = "Returns largest used index in the array."
    If This.ArrayType = BA_UNALLOCATED Then
        UpperBound = -1
    Else
        UpperBound = This.Length + This.LowerBound - 1
    End If
End Property

'@Description("Returns smallest used index in the array.")
Public Property Get LowerBound() As Long
Attribute LowerBound.VB_Description = "Returns smallest used index in the array."
    LowerBound = This.LowerBound
End Property

'@Description("Sets the starting index of the array. If an array is already stored then it will be re-indexed to match the new value")
Public Property Let LowerBound(ByVal value As Long)
Attribute LowerBound.VB_Description = "Sets the starting index of the array. If an array is already stored then it will be re-indexed to match the new value"
    This.LowerBoundSet = True
    If value <> This.LowerBound Then
        This.LowerBound = value
        InternalItems = Rebase()
        This.Capacity = GetArrayLength(This.Items)
    End If
End Property

'@DefaultMember
'@Description("Returns the element in the array stored at the specified index.")
Public Property Get item(ByVal index As Long) As Variant
Attribute item.VB_Description = "Returns the element in the array stored at the specified index."
Attribute item.VB_UserMemId = 0
    If index <= This.Length Then
        ' not using letOrSetElement here as it might try to access the Items letter
        If IsObject(This.Items(index)) Then
            Set item = This.Items(index)
        Else
            item = This.Items(index)
        End If
    Else
        '@Ignore FunctionReturnValueDiscarded
        err.Raise 9
    End If
End Property

'@Description("Assigns the passed element to the array at the specified index.")
Public Property Let item(ByVal index As Long, ByVal element As Variant)
Attribute item.VB_Description = "Assigns the passed element to the array at the specified index."
    If Me.UpperBound >= index Then
        If index < This.LowerBound Then
            '@Ignore FunctionReturnValueDiscarded
            Me.Unshift element
        Else
            LetOrSetElement This.Items(index), element
        End If
    Else
        '@Ignore FunctionReturnValueDiscarded
        Me.Push element
    End If
End Property

'@Description("Returns the stored array.")
Public Property Get Items() As Variant
Attribute Items.VB_Description = "Returns the stored array."
    Dim result() As Variant
    result = InternalItems
    If This.ArrayType = ArrayTypes.BA_MULTIDIMENSION Then
        If IsJaggedArray(result) Then result = JaggedToMulti(result)
    End If
    Items = result
End Property

'@Description("Stores the passed array.")
Public Property Let Items(ByVal values As Variant)
Attribute Items.VB_Description = "Stores the passed array."
    Const CONVERT_MD_TO_JAGGED As Boolean = True
    Const CONVERT_NESTED_JAGGED As Boolean = True
    Dim LocalLowerBound As Long
    Dim LocalValues() As Variant
    Dim TypeSet As Boolean
    
    If TypeName(values) = TypeName(Me) Then
        LocalValues = values.Items
    ElseIf IsArray(values) Then
        This.ArrayType = GetArrayType(values)
        TypeSet = True
        If This.ArrayType = BA_UNALLOCATED Then
            LocalValues = GetEmptyArray
        Else
            LocalLowerBound = LBound(values)
            If Not This.LowerBoundSet Then
                This.LowerBound = LocalLowerBound
            End If
            LocalValues = ConvertArrayForStorage( _
                values, _
                This.ArrayType, _
                CONVERT_MD_TO_JAGGED, _
                CONVERT_NESTED_JAGGED _
            )
        End If
    Else
        ' If Values is not an array then clear our internal array and push the Values arg
        ' NOTE: this possibly violates PoLA - assess for refactor
        '@Ignore FunctionReturnValueDiscarded
        If IsEmpty(values) And This.ArrayType = ArrayTypes.BA_UNDEFINED Then
            RaiseError EC_EXPECTED_ARRAY, "Items", "Values"
        Else
            Me.Clear.Push values
        End If
        Exit Property
    End If
    
    If Not TypeSet Then
        This.ArrayType = GetArrayType(LocalValues)
    End If
    
    InternalItems = LocalValues
    This.Length = GetArrayLength(LocalValues)
    This.Capacity = This.Length
    If This.Capacity < DEFAULT_CAPACITY Then
        Me.Capacity = DEFAULT_CAPACITY
    End If

End Property

'@Description("Retrieves the stored array type.")
Public Property Get ArrayType() As ArrayTypes
Attribute ArrayType.VB_Description = "Retrieves the stored array type."
    ArrayType = This.ArrayType
End Property

'@Description("Sets the stored array type.")
Public Property Let ArrayType(ByVal NewType As ArrayTypes)
Attribute ArrayType.VB_Description = "Sets the stored array type."
    Select Case NewType
    Case ArrayTypes.BA_UNDEFINED
        RaiseError EC_CANNOT_CONVERT_TO_REQUESTED_STRUCTURE, "ArrayType", "NewType"
    Case ArrayTypes.BA_UNALLOCATED
        If This.ArrayType <> BA_UNALLOCATED Then
            Me.ResetToDefault
        End If
    Case ArrayTypes.BA_ONEDIMENSION
        Select Case This.ArrayType
        Case ArrayTypes.BA_MULTIDIMENSION, ArrayTypes.BA_JAGGED
            RaiseError EC_CANNOT_CONVERT_TO_REQUESTED_STRUCTURE, "ArrayType", "NewType"
        Case Else
            This.ArrayType = NewType
        End Select
    Case Else
        This.ArrayType = NewType
    End Select
End Property

'@Description("Retrieves the sorting algorithm used by the Sort() method.")
Public Property Get SortMethod() As SortMethods
Attribute SortMethod.VB_Description = "Retrieves the sorting algorithm used by the Sort() method."
    SortMethod = This.SortMethod
End Property

'@Description("Specifies the sorting algorithm used by the Sort() method.")
Public Property Let SortMethod(ByVal Method As SortMethods)
Attribute SortMethod.VB_Description = "Specifies the sorting algorithm used by the Sort() method."
    This.SortMethod = Method
End Property


''''''''''''''''''''''
' Private Properties '
''''''''''''''''''''''

'@Description("Retrieves the stored items trimmed to the correct length. Does not change structure (i.e jagged to multi).")
Private Property Get InternalItems() As Variant()
Attribute InternalItems.VB_Description = "Retrieves the stored items trimmed to the correct length. Does not change structure (i.e jagged to multi)."
    Dim result() As Variant
    If This.ArrayType <> BA_UNALLOCATED And This.ArrayType <> BA_UNDEFINED Then
        result = This.Items
        If This.Capacity > This.Length Then
            If This.Length = 0 Then
                ReDim Preserve result(This.LowerBound To This.LowerBound)
            ElseIf This.Length > 0 Then
                ReDim Preserve result(This.LowerBound To Me.UpperBound)
            End If
        End If
    Else
        result = GetEmptyArray
    End If
    InternalItems = result
End Property

'@Description("Assigns the passed array to this.items")
'@Ignore MisleadingByRefParameter
Private Property Let InternalItems(ByRef value() As Variant)
Attribute InternalItems.VB_Description = "Assigns the passed array to this.items"
    This.Items = value
End Property


''''''''''''''''''
' Public Methods '
''''''''''''''''''

'@Description("Adds the provided argments to the array at the next available index.")
Public Function Push(ParamArray Args() As Variant) As Variant
Attribute Push.VB_Description = "Adds the provided argments to the array at the next available index."
    Dim element As Variant

    If This.ArrayType = ArrayTypes.BA_UNALLOCATED Or _
       This.ArrayType = ArrayTypes.BA_UNDEFINED Then
        This.ArrayType = ArrayTypes.BA_ONEDIMENSION
    End If

    For Each element In Args
        If This.Length = This.Capacity Then
            EnsureCapacity This.Length + 1
        End If
        If IsArray(element) Then
            Dim ArrayElement() As Variant
            Dim ArrayElementType As ArrayTypes
            ArrayElement = element
            If This.ArrayType = BA_ONEDIMENSION Then
                ArrayElementType = GetArrayType(ArrayElement)
                If ArrayElementType = BA_MULTIDIMENSION Then
                    This.ArrayType = BA_MULTIDIMENSION
                Else
                    This.ArrayType = BA_JAGGED
                End If
            End If
            If LBound(ArrayElement) <> This.LowerBound Then
                ArrayElement = Rebase(ArrayElement, ArrayElementType)
            End If
            LetOrSetElement This.Items(This.Length + This.LowerBound), ArrayElement
        Else
            LetOrSetElement This.Items(This.Length + This.LowerBound), element
        End If
        Inc This.Length
    Next
    Push = This.Length
End Function

'@Description("Removes the last element from the array and returns that element.")
Public Function Pop() As Variant
Attribute Pop.VB_Description = "Removes the last element from the array and returns that element."
    Dim result As Variant
    Dim NewItems() As Variant
    If This.Length > 0 Then
        result = This.Items(Me.UpperBound)
        NewItems = Me.Slice(This.LowerBound, Me.UpperBound)
        Me.Items = NewItems
    End If
    Pop = result
End Function

'@Description("Removes the first element from the array and returns that element.")
Public Function shift() As Variant
Attribute shift.VB_Description = "Removes the first element from the array and returns that element."
    Dim NewItems() As Variant
    Dim result As Variant
    If This.Length > 0 Then
        result = This.Items(This.LowerBound)
        NewItems = Me.Slice(This.LowerBound + 1)
        Me.Items = NewItems
    End If
    shift = result
End Function

'@Description("Adds one or more elements to the beginning of an array. Returns the new length of the array.")
Public Function Unshift(ParamArray Args() As Variant) As Long
Attribute Unshift.VB_Description = "Adds one or more elements to the beginning of an array. Returns the new length of the array."
    Dim NewItems() As Variant
    Dim OldItems() As Variant
    Dim OldType As ArrayTypes
    
    NewItems = Args
    OldType = This.ArrayType
    OldItems = InternalItems
    Me.Items = NewItems
    If OldType <> BA_UNALLOCATED And OldType <> BA_UNDEFINED Then
        '@Ignore FunctionReturnValueDiscarded
        Me.Concat OldItems
        This.ArrayType = OldType
    End If
    Unshift = This.Length
End Function

'@Description("Returns a string representing the array structure and its elements.")
Public Function ToString( _
        Optional ByVal PrettyPrint As Boolean, _
        Optional ByVal separator As String = CHR_COMMA, _
        Optional ByVal OpeningDelimiter As String = "{", _
        Optional ByVal ClosingDelimiter As String = "}", _
        Optional ByVal QuoteStrings As Boolean _
    ) As String
Attribute ToString.VB_Description = "Returns a string representing the array structure and its elements."
    Dim LocalArrayType As ArrayTypes
    Dim result As String
    Dim LocalItems() As Variant
    Dim Sep As String
    
    Sep = IIf(PrettyPrint, separator & space(1), separator)
    
    LocalItems = InternalItems
    LocalArrayType = GetArrayType(LocalItems)
    If Not LocalArrayType = ArrayTypes.BA_UNDEFINED And _
       Not LocalArrayType = ArrayTypes.BA_UNALLOCATED Then
        If LocalArrayType = ArrayTypes.BA_MULTIDIMENSION Then
            LocalItems = MultiToJagged(LocalItems)
        End If
        RecursiveToString _
            SourceArray:=LocalItems, _
            PrettyPrint:=PrettyPrint, _
            separator:=Sep, _
            OpeningDelimiter:=OpeningDelimiter, _
            ClosingDelimiter:=ClosingDelimiter, _
            QuoteStrings:=QuoteStrings
        result = StringBuilder(Final:=True)
    End If
    ToString = result
End Function

'@Description("Determines whether the array includes a certain value among its entries.")
Public Function Includes( _
        ByVal SearchElement As Variant, _
        Optional ByVal FromIndex As Long = MISSING_LONG, _
        Optional ByVal Recurse As Boolean _
    ) As Boolean
Attribute Includes.VB_Description = "Determines whether the array includes a certain value among its entries."
    Dim LocalLength As Long
    Dim CurrentIndex As Long
    Dim SearchArray() As Variant
    
    SearchArray = InternalItems
    LocalLength = This.Length
    
    If LocalLength = 0 Then
        Includes = False
        Exit Function
    End If
        
    If FromIndex > This.LowerBound Then
        CurrentIndex = FromIndex
    ElseIf FromIndex = MISSING_LONG Then
        CurrentIndex = This.LowerBound
    Else
        CurrentIndex = LocalLength + FromIndex
    End If
    
    Includes = RecursiveIncludes(SearchElement, SearchArray, CurrentIndex, Recurse:=Recurse)
End Function

'@Description("Determines whether the type of any of the elements in the array matches the typename.")
Public Function IncludesType( _
        ByVal SearchTypeName As String, _
        Optional ByVal FromIndex As Long = MISSING_LONG, _
        Optional ByVal Recurse As Boolean _
    ) As Boolean
Attribute IncludesType.VB_Description = "Determines whether the type of any of the elements in the array matches the typename."
    Dim LocalLength As Long
    Dim CurrentIndex As Long
    Dim SearchArray() As Variant
    
    SearchArray = InternalItems
    LocalLength = This.Length
    
    If LocalLength = 0 Then
        IncludesType = False
        Exit Function
    End If
        
    If FromIndex > This.LowerBound Then
        CurrentIndex = FromIndex
    ElseIf FromIndex = MISSING_LONG Then
        CurrentIndex = This.LowerBound
    Else
        CurrentIndex = LocalLength + FromIndex
    End If
    
    IncludesType = RecursiveIncludes(SearchTypeName, SearchArray, CurrentIndex, True, Recurse)
End Function

'@Description("Determines whether all elements in the array match a value.")
Public Function Every( _
        ByVal SearchElement As Variant, _
        Optional ByVal FromIndex As Long = MISSING_LONG _
    ) As Boolean
Attribute Every.VB_Description = "Determines whether all elements in the array match a value."
    
    Dim LocalLength As Long
    Dim CurrentIndex As Long
    Dim SearchArray() As Variant
    
    SearchArray = InternalItems
    LocalLength = This.Length
    
    If LocalLength = 0 Then
        Every = False
        Exit Function
    End If
        
    If FromIndex > This.LowerBound Then
        CurrentIndex = FromIndex
    ElseIf FromIndex = MISSING_LONG Then
        CurrentIndex = This.LowerBound
    Else
        CurrentIndex = LocalLength + FromIndex
    End If
    
    Every = RecursiveEvery(SearchElement, SearchArray, CurrentIndex)
End Function

'@Description("Determines whether the type of all elements match the provided typename.")
Public Function EveryType( _
        ByVal SearchTypeName As String, _
        Optional ByVal FromIndex As Long = MISSING_LONG _
    ) As Boolean
Attribute EveryType.VB_Description = "Determines whether the type of all elements match the provided typename."
    
    Dim LocalLength As Long
    Dim CurrentIndex As Long
    Dim SearchArray() As Variant
    
    SearchArray = InternalItems
    LocalLength = This.Length
    
    If LocalLength = 0 Then
        EveryType = False
        Exit Function
    End If
        
    If FromIndex > This.LowerBound Then
        CurrentIndex = FromIndex
    ElseIf FromIndex = MISSING_LONG Then
        CurrentIndex = This.LowerBound
    Else
        CurrentIndex = LocalLength + FromIndex
    End If
    
    EveryType = RecursiveEvery(SearchTypeName, SearchArray, CurrentIndex, True)
    
End Function

'@Description("Returns a new array that contains the keys for each index in the array.")
Public Function keys() As Variant()
Attribute keys.VB_Description = "Returns a new array that contains the keys for each index in the array."
    Dim i As Long
    Dim LocalLowerBound As Long
    Dim result() As Variant
    
    If This.ArrayType = BA_UNDEFINED Then
        RaiseError EC_UNDEFINED_ARRAY, "Keys"
    ElseIf This.ArrayType = BA_UNALLOCATED Then
        RaiseError EC_UNALLOCATED_ARRAY, "Keys"
    Else
        LocalLowerBound = This.LowerBound
        ReDim result(0 To This.Length - 1)
        For i = LBound(result) To UBound(result)
            result(i) = i + LocalLowerBound
        Next
    End If
    keys = result
End Function

'@Description("Returns the largest value in a list of values. If arguments are provided it will return the largest argument. If no arguments are provided it will return the largest element in the stored array")
Public Function max(ParamArray Args() As Variant) As Variant
Attribute max.VB_Description = "Returns the largest value in a list of values. If arguments are provided it will return the largest argument. If no arguments are provided it will return the largest element in the stored array"
    Dim LocalItems() As Variant
    
    If UBound(Args) < LBound(Args) Then          'Test if no args provided
        LocalItems = InternalItems
    Else
        LocalItems = Args
    End If
    
    max = RecursiveMax(LocalItems)
End Function

'@Description("Returns the smallest value in a list of values. If arguments are provided it will return the smallest argument. If no arguments are provided it will return the smallest element in the stored array")
Public Function min(ParamArray Args() As Variant) As Variant
Attribute min.VB_Description = "Returns the smallest value in a list of values. If arguments are provided it will return the smallest argument. If no arguments are provided it will return the smallest element in the stored array"
    Dim LocalItems() As Variant
    
    If UBound(Args) < LBound(Args) Then          'Test if no args provided
        LocalItems = InternalItems
    Else
        LocalItems = Args
    End If
    
    min = RecursiveMin(LocalItems)
End Function

'@Description("Returns a new array containing the portion of the stored array between the StartIndex and EndIndex")
Public Function Slice( _
        ByVal StartIndex As Long, _
        Optional ByVal EndIndex As Long = MISSING_LONG _
    ) As Variant()
Attribute Slice.VB_Description = "Returns a new array containing the portion of the stored array between the StartIndex and EndIndex"
    Dim LocalLength As Long
    Dim RelativeStart As Long
    Dim RelativeEnd As Long
    Dim OldIndex As Long
    Dim Final As Long
    Dim Count As Long
    Dim NewIndex As Long
    Dim LocalItems() As Variant
    Dim result() As Variant
    
    LocalItems = InternalItems
    LocalLength = This.Length
    RelativeStart = StartIndex
    If RelativeStart < LBound(LocalItems) Then
        If RelativeStart < 0 Then
            OldIndex = max((LocalLength + RelativeStart), LBound(LocalItems))
        Else
            OldIndex = max((LocalLength - RelativeStart), LBound(LocalItems))
        End If
    Else
        OldIndex = min(RelativeStart, LocalLength)
    End If
    If EndIndex = MISSING_LONG Then
        RelativeEnd = LocalLength + LBound(LocalItems)
    Else
        RelativeEnd = EndIndex
    End If
    If RelativeEnd < LBound(LocalItems) Then
        Final = max((LocalLength + RelativeEnd), LBound(LocalItems))
    Else
        Final = min(RelativeEnd, LocalLength + LBound(LocalItems))
    End If
    
    NewIndex = LBound(LocalItems)
    Count = max(Final - OldIndex, 0) + LBound(LocalItems)
    If Count > NewIndex Then
        ReDim result(NewIndex To Count - 1)
        Do While OldIndex < Final
            If OldIndex >= LBound(LocalItems) And OldIndex <= UBound(LocalItems) Then
                LetOrSetElement result(NewIndex), LocalItems(OldIndex)
                Inc NewIndex
                Inc OldIndex
            End If
        Loop
        If This.ArrayType = BA_MULTIDIMENSION Then
            Slice = JaggedToMulti(result)
        Else
            Slice = result
        End If
    End If
    
End Function

'@Description("Stores the values contained in an Excel range in the internal array")
Public Function FromExcelRange( _
        ByRef FromRange As Object, _
        Optional ByVal DetectLastRow As Boolean, _
        Optional ByVal DetectLastColumn As Boolean _
    ) As BetterArray
Attribute FromExcelRange.VB_Description = "Stores the values contained in an Excel range in the internal array"

    If TypeName(FromRange) = "Range" Then
        Dim StartColumn As Long
        Dim EndColumn As Long
        Dim StartRow As Long
        Dim EndRow As Long
        
        With FromRange
            StartColumn = .Column
            StartRow = .row
            EndColumn = .Column + .columns.Count - 1
            EndRow = .row + .Rows.Count - 1
        End With
        
        With FromRange.parent
            If DetectLastColumn Then
                EndColumn = .Cells.item(StartRow, .columns.Count).end(xlToLeft).Column
            End If
            
            If DetectLastRow Then
                EndRow = .Cells.item(.Rows.Count, StartColumn).end(xlUp).row
            End If
            
            Me.Items = .Range(.Cells(StartRow, StartColumn), .Cells(EndRow, EndColumn)).value
        End With
        
        ' convert arrays of single column or row to 1d
        If StartColumn = EndColumn And StartRow <> EndRow Then
            Me.Items = Me.ExtractSegment(, StartColumn)
        ElseIf StartColumn <> EndColumn And StartRow = EndRow Then
            Me.Items = Me.ExtractSegment(StartRow)
        End If
        
    Else
        RaiseError ErrorCodes.EC_EXPECTED_RANGE_OBJECT, "FromExcelRange()", "FromRange"
    End If
    
    Set FromExcelRange = Me
End Function

'@Description("Extracts the segment of the array located at the specified indices.")
Public Function ExtractSegment( _
        Optional ByVal RowIndex As Long = MISSING_LONG, _
        Optional ByVal ColumnIndex As Long = MISSING_LONG _
    ) As Variant()
Attribute ExtractSegment.VB_Description = "Extracts the segment of the array located at the specified indices."
    Dim i As Long
    Dim LocalRowIndex As Long
    Dim LocalColumnIndex As Long
    Dim NestedBounds() As Long
    Dim LocalItems() As Variant
    Dim result() As Variant
    
    LocalItems = InternalItems

    If RowIndex = MISSING_LONG Then
        If ColumnIndex = MISSING_LONG Then
            ' if no coords provided return full array
            ' calls to Me.Items instead of returning localItems to covert md from jagged
            result = Me.Items
        Else
            ' Row number missing, column number present
            Select Case This.ArrayType
            Case BA_ONEDIMENSION
                If ColumnIndex >= LBound(LocalItems) And ColumnIndex <= UBound(LocalItems) Then
                    LocalColumnIndex = ColumnIndex
                Else
                    LocalColumnIndex = LBound(LocalItems)
                End If
                result = Array(LocalItems(LocalColumnIndex))
            Case BA_JAGGED, BA_MULTIDIMENSION
                ' return full column
                NestedBounds = GetMaxBoundsAtDimension(LocalItems, 2)
                If ColumnIndex >= NestedBounds(0) And ColumnIndex <= NestedBounds(1) Then
                    LocalColumnIndex = ColumnIndex
                Else
                    LocalColumnIndex = This.LowerBound
                End If
                ReDim result(LBound(LocalItems) To UBound(LocalItems))
                For i = LBound(LocalItems) To UBound(LocalItems)
                    result(i) = LocalItems(i)(LocalColumnIndex)
                Next
            Case BA_UNALLOCATED
                result = LocalItems
            Case Else
            End Select
        End If
    Else
        ' Row Number not missing
        If RowIndex >= LBound(LocalItems) And RowIndex <= UBound(LocalItems) Then
            LocalRowIndex = RowIndex
        Else
            LocalRowIndex = LBound(LocalItems)
        End If
        If ColumnIndex = MISSING_LONG Then
            ' Row number present, column number missing
            Select Case This.ArrayType
            Case BA_ONEDIMENSION
                result = Array(LocalItems(LocalRowIndex))
            Case BA_JAGGED, BA_MULTIDIMENSION
                result = LocalItems(LocalRowIndex)
            Case BA_UNALLOCATED
                result = LocalItems
            Case Else
            End Select
        Else
            ' Row number present, column number present
            Select Case This.ArrayType
            Case BA_ONEDIMENSION
                ' ignore column number arg as array is 1d
                result = Array(LocalItems(LocalRowIndex))
            Case BA_JAGGED, BA_MULTIDIMENSION
                ' return intersection of rowIndex and column number
                NestedBounds = GetMaxBoundsAtDimension(LocalItems, 2)
                If ColumnIndex >= NestedBounds(0) And ColumnIndex <= NestedBounds(1) Then
                    LocalColumnIndex = ColumnIndex
                Else
                    LocalColumnIndex = This.LowerBound
                End If
                If IsArray(LocalItems(LocalRowIndex)(LocalColumnIndex)) Then
                    result = LocalItems(LocalRowIndex)(LocalColumnIndex)
                Else
                    result = Array(LocalItems(LocalRowIndex)(LocalColumnIndex))
                End If
            Case BA_UNALLOCATED
                result = LocalItems
            Case Else
            End Select
        End If
    End If
    
    ExtractSegment = result
End Function

'@Description("Writes the values stored in the array to an excel worksheet starting at the specified range.")
Public Function ToExcelRange( _
        ByRef Destination As Object, _
        Optional ByVal TransposeValues As Boolean _
    ) As Object
Attribute ToExcelRange.VB_Description = "Writes the values stored in the array to an excel worksheet starting at the specified range."
    Const TARGET_APPLICATION As String = "Microsoft Excel"
    Const TARGET_OBJECT As String = "Range"
    Dim LocalRange As Object
    Dim LocalItems() As Variant
    Dim Depth As Long
    Dim LengthRows As Long
    Dim LengthColumns As Long
    Dim AvailableRows As Long
    Dim AvailableColumns As Long
    Dim DestType As String
    Dim DestApplication As String
       
    On Error Resume Next
        DestType = TypeName(Destination)
        DestApplication = Destination.Application.Name
    On Error GoTo 0
    
    If DestType = TARGET_OBJECT And DestApplication = TARGET_APPLICATION Then
        AvailableRows = Destination.parent.Rows.Count - Destination.row + 1
        AvailableColumns = Destination.parent.columns.Count - Destination.Column + 1
        LocalItems = InternalItems
        Depth = GetJaggedArrayDepth(LocalItems)
        If Depth > 0 Then 'check array is allocated
            If Depth = 1 Then
                '1d array
                LocalItems = ConvertOneDimensionArrayToJagged(LocalItems)
            End If
            'jagged array - multidim arrays should also be stored as jagged internally
            Const OutputDepth As Long = 2 'need 2 dimensions for tabular representation output
            LocalItems = JaggedToMulti(LocalItems, OutputDepth, EnsureScalar:=True)
            If TransposeValues Then
                LocalItems = Transpose2DArray(LocalItems)
            End If
            
            LocalItems = TrimColumnsMultidimensionArray(LocalItems, AvailableColumns)
            LocalItems = TrimRowsMultidimensionArray(LocalItems, AvailableRows)
            LengthRows = UBound(LocalItems, 1) - LBound(LocalItems, 1) + 1
            LengthColumns = UBound(LocalItems, 2) - LBound(LocalItems, 2) + 1
                        
            Set LocalRange = Destination.Resize( _
                RowSize:=LengthRows, _
                ColumnSize:=LengthColumns _
            )
            LocalRange.value = LocalItems
        '@Ignore EmptyElseBlock
        Else
            'array must be unalloc
            'do nothing(?)
        End If
    Else
        RaiseError ErrorCodes.EC_EXPECTED_RANGE_OBJECT, "ToExcelRange()", "Destination"
    End If
    
    Set ToExcelRange = LocalRange
End Function

'@Description("Tests if the stored array is sorted in ascending order.")
Public Function IsSorted(Optional ByVal ColumnIndex As Long = MISSING_LONG) As Boolean
Attribute IsSorted.VB_Description = "Tests if the stored array is sorted in ascending order."
    Dim i As Long
    Dim LocalLowerBound As Long
    Dim LocalUpperBound As Long
    Dim LocalColumnIndex As Long
    Dim Depth As Long
    Dim result As Boolean
    Dim LocalItems() As Variant
    Dim StoredType As ArrayTypes
    
    result = True
    
    LocalItems = InternalItems
    LocalLowerBound = LBound(LocalItems)
    LocalUpperBound = UBound(LocalItems)
    StoredType = GetArrayType(LocalItems)
    If StoredType <> BA_UNDEFINED And StoredType <> BA_UNALLOCATED Then
        Select Case StoredType
        Case BA_ONEDIMENSION
            For i = LocalLowerBound To LocalUpperBound - 1
                If LocalItems(i) > LocalItems(i + 1) Then
                    result = False
                    Exit For
                End If
            Next
        Case BA_MULTIDIMENSION
            ' should never be true as all md arrays stored as jagged internally
            If ColumnIndex = MISSING_LONG Then
                LocalColumnIndex = LBound(LocalItems, 2)
            Else
                LocalColumnIndex = CLng(ColumnIndex)
            End If
            For i = LocalLowerBound To LocalUpperBound - 1
                If LocalItems(i, LocalColumnIndex) > LocalItems(i + 1, LocalColumnIndex) Then
                    result = False
                    Exit For
                End If
            Next
        Case BA_JAGGED
            Depth = GetJaggedArrayDepth(LocalItems)
            If Depth > 2 Then
                IsSorted = False
                RaiseError EC_EXCEEDS_MAX_SORT_DEPTH, "IsSorted"
            Else
                For i = LocalLowerBound To LocalUpperBound - 1
                    If i = LocalLowerBound Then
                        If ColumnIndex = MISSING_LONG Then
                            LocalColumnIndex = LBound(LocalItems(i))
                        Else
                            LocalColumnIndex = CLng(ColumnIndex)
                        End If
                    End If
                    If LocalItems(i)(LocalColumnIndex) > LocalItems(i + 1)(LocalColumnIndex) Then
                        result = False
                        Exit For
                    End If
                Next
            End If
        End Select
    End If
    IsSorted = result
End Function



'@Description("returns the first index at which a given element can be found in the array")
Public Function IndexOf( _
        ByVal SearchElement As Variant, _
        Optional ByVal FromIndex As Long = MISSING_LONG, _
        Optional ByVal CompType As ComparisonType _
    ) As Long
Attribute IndexOf.VB_Description = "returns the first index at which a given element can be found in the array"
    Dim LocalItems() As Variant
    Dim RelativeStart As Long
    Dim CurrentIndex As Long
    
    If CompType = CT_LIKENESS Then
        If TypeName(SearchElement) <> "String" Then
            RaiseError EC_STRING_TYPE_EXPECTED, "IndexOf", "searchElement"
        End If
    End If
    
    If This.Length = 0 Then
        IndexOf = MISSING_LONG
        Exit Function
    End If

    LocalItems = InternalItems

    If FromIndex = MISSING_LONG Then
        RelativeStart = LBound(LocalItems)
    Else
        RelativeStart = FromIndex
    End If
    
    If RelativeStart >= LBound(LocalItems) Then
        CurrentIndex = RelativeStart
    Else
        If RelativeStart > 0 Then
            CurrentIndex = LBound(LocalItems)
        Else
            CurrentIndex = UBound(LocalItems) + RelativeStart
        End If
        
        If CurrentIndex < LBound(LocalItems) Then
            CurrentIndex = LBound(LocalItems)
        End If
    End If
    
    Dim IsMatch As Boolean
    Do While CurrentIndex <= UBound(LocalItems)
        Select Case CompType
        Case ComparisonType.CT_LIKENESS
            IsMatch = CStr(LocalItems(CurrentIndex)) Like CStr(SearchElement)
        Case Else
            IsMatch = ElementsAreEqual(SearchElement, LocalItems(CurrentIndex))
        End Select
        If IsMatch Then
            IndexOf = CurrentIndex
            Exit Function
        End If
        Inc CurrentIndex
    Loop
    
    IndexOf = MISSING_LONG
End Function

'@Description("returns the first index at which a given element can be found in the array")
Public Function LastIndexOf( _
        ByVal SearchElement As Variant, _
        Optional ByVal FromIndex As Long = MISSING_LONG, _
        Optional ByVal CompType As ComparisonType _
    ) As Long
Attribute LastIndexOf.VB_Description = "returns the first index at which a given element can be found in the array"
    Dim LocalItems() As Variant
    Dim CurrentIndex As Long
    
    If CompType = CT_LIKENESS Then
        If TypeName(SearchElement) <> "String" Then
            RaiseError EC_STRING_TYPE_EXPECTED, "IndexOf", "searchElement"
        End If
    End If
    
    If This.Length = 0 Then
        LastIndexOf = MISSING_LONG
        Exit Function
    End If

    LocalItems = InternalItems
    
    If FromIndex = MISSING_LONG Then
        CurrentIndex = UBound(LocalItems)
    Else
        If FromIndex >= LBound(LocalItems) Then
            CurrentIndex = min(FromIndex, UBound(LocalItems))
        ElseIf FromIndex < 0 Then
            CurrentIndex = UBound(LocalItems) + FromIndex
        End If
        
    End If
    
    Dim IsMatch As Boolean
    Do While CurrentIndex >= LBound(LocalItems)
        Select Case CompType
        Case ComparisonType.CT_LIKENESS
            IsMatch = CStr(LocalItems(CurrentIndex)) Like CStr(SearchElement)
        Case Else
            IsMatch = ElementsAreEqual(SearchElement, LocalItems(CurrentIndex))
        End Select
        If IsMatch Then
            LastIndexOf = CurrentIndex
            Exit Function
        End If
        dec CurrentIndex
    Loop
    
    LastIndexOf = MISSING_LONG
End Function

'@Description("Removes the item at the specified index. Returns the new length of the array")
Public Function Remove(ByVal index As Long) As Long
Attribute Remove.VB_Description = "Removes the item at the specified index. Returns the new length of the array"
    Dim RelativeIndex As Long
    Dim LocalType As ArrayTypes
    
    RelativeIndex = MISSING_LONG
    LocalType = This.ArrayType
    
    If index >= This.LowerBound Then
        If index <= Me.UpperBound Then
            RelativeIndex = index
        End If
    Else
        If index < 0 Then
            RelativeIndex = Me.UpperBound + index
            If RelativeIndex < This.LowerBound Then RelativeIndex = MISSING_LONG
        End If
    End If
    
    If RelativeIndex <> MISSING_LONG Then
        Dim BeforeSlice() As Variant
        Dim AfterSlice() As Variant
        Dim BeforeExists As Boolean
        Dim AfterExists As Boolean
        
        If RelativeIndex > This.LowerBound Then
            BeforeSlice = Me.Slice(This.LowerBound, RelativeIndex)
            BeforeExists = True
        End If
        If RelativeIndex < Me.UpperBound Then
            AfterSlice = Me.Slice(RelativeIndex + 1)
            AfterExists = True
        End If
        If BeforeExists Then
            If AfterExists Then
                Me.Items = InternalConcat(BeforeSlice, AfterSlice)
            Else
                Me.Items = BeforeSlice
            End If
        Else
            If AfterExists Then
                Me.Items = AfterSlice
            End If
        End If
        If BeforeExists Or AfterExists Then
            If This.ArrayType = BA_JAGGED And LocalType = BA_MULTIDIMENSION Then
                This.ArrayType = LocalType
            End If
        Else
            Me.Clear
        End If
    End If
    
    Remove = This.Length
End Function

'@Description("changes the contents of the array by removing or replacing existing elements and/or adding new elements in place.")
Public Function Splice( _
        ByVal StartIndex As Long, _
        ParamArray Args() As Variant _
    ) As Variant()
Attribute Splice.VB_Description = "changes the contents of the array by removing or replacing existing elements and/or adding new elements in place."
    Dim LocalItems() As Variant
    Dim ActualStart As Long
    Dim ActualDeleteCount As Long
    Dim ArgsCount As Long
    Dim LocalLength As Long
    Dim LocalArgs() As Variant
    Dim result() As Variant
    Dim i As Long
    Dim TempArray() As Variant
    Dim ItemCount As Long
    Dim TempItems() As Variant
    
    LocalArgs = Args
    LocalItems = InternalItems
    LocalLength = UBound(LocalItems) + 1
    If StartIndex < LBound(LocalItems) Then
        ActualStart = max(LocalLength + StartIndex, LBound(LocalItems))
    Else
        ActualStart = min(StartIndex, LocalLength)
    End If
    ArgsCount = GetArrayLength(LocalArgs)
    If ArgsCount = 0 Then
        ' only a start index has been supplied
        ' we're gonna delete everything
        ItemCount = 0
        ActualDeleteCount = LocalLength - ActualStart
    Else
        ' first arg in args is delete count, second onwards are insertion items
        ItemCount = ArgsCount - 1
        'deleteCount is first element in args.
        ActualDeleteCount = min(max(Args(LBound(Args)), 0), LocalLength - ActualStart)
    End If
    
    If LocalLength + ItemCount - ActualDeleteCount > MAX_ARRAY_LENGTH Then
        RaiseError EC_EXCEEDS_MAX_ARRAY_LENGTH, "Splice"
        Exit Function
    End If

    ' get items to be deleted for return val
    If ActualDeleteCount > 0 Then
        ReDim result(0 To ActualDeleteCount - 1)
        i = 0
        Do While i < ActualDeleteCount
            LetOrSetElement result(i), LocalItems(ActualStart + i)
            Inc i
        Loop
    Else
        ' return empty array if nothing to be deleted
        ReDim result(0)
    End If
    
    If ItemCount > 0 Then
        ReDim TempItems(0 To ItemCount - 1)
        For i = LBound(TempItems) To UBound(TempItems)
            TempItems(i) = Args(i + 1)
        Next
    End If
            
    If ItemCount < ActualDeleteCount Then
        i = ActualStart
        Do While i < (LocalLength - ActualDeleteCount)
            LetOrSetElement LocalItems(i + ItemCount), LocalItems(i + ActualDeleteCount)
            Inc i
        Loop
        
        
        i = LocalLength
        Dim TempBetterArray As BetterArray
        Set TempBetterArray = New BetterArray
        TempBetterArray.Items = LocalItems
        Do While i > (LocalLength - ActualDeleteCount + ItemCount)
            TempBetterArray.Remove (i - 1)
            ' Perform ? DeletePropertyOrThrow(O, ! ToString(k - 1)).
            dec i
        Loop
        LocalItems = TempBetterArray.Items
        Set TempBetterArray = Nothing
    ElseIf ItemCount > ActualDeleteCount Then
        i = (LocalLength - ActualDeleteCount)
        TempArray = LocalItems
        ReDim Preserve TempArray(This.LowerBound To i + ItemCount - 1) As Variant
        Do While i > ActualStart
            LetOrSetElement TempArray(i + ItemCount - 1), LocalItems(i + ActualDeleteCount - 1)
            dec i
        Loop
        LocalItems = TempArray
    End If
    
    If ItemCount > 0 Then
        i = ActualStart
        Dim j As Long
        For j = LBound(TempItems) To UBound(TempItems)
            LocalItems(i) = TempItems(j)
            Inc i
        Next
    End If
    
    InternalItems = LocalItems
    
    Splice = result
End Function


''''''''''''''''''''''''''''
' Chainable Public Methods '
''''''''''''''''''''''''''''

'@Description("Recursvely fills (modifies) all the elements of an array from a start index (default zero) to an end index (default array length) with a passed value.")
Public Function Fill( _
        ByVal value As Variant, _
        Optional ByVal StartIndex As Long = MISSING_LONG, _
        Optional ByVal EndIndex As Long = MISSING_LONG _
    ) As BetterArray
Attribute Fill.VB_Description = "Recursvely fills (modifies) all the elements of an array from a start index (default zero) to an end index (default array length) with a passed value."
    Dim LocalItems() As Variant
    Dim RelativeStart As Long
    Dim RelativeEnd As Long
    
    LocalItems = InternalItems
    If StartIndex = MISSING_LONG Then
        RelativeStart = LBound(LocalItems)
    Else
        If StartIndex < 0 Then
            RelativeStart = max(Me.UpperBound + StartIndex, LBound(LocalItems))
        ElseIf StartIndex < LBound(LocalItems) Then
            RelativeStart = LBound(LocalItems)
        Else
            RelativeStart = min(StartIndex, Me.UpperBound)
        End If
    End If
    
    If EndIndex = MISSING_LONG Then
        RelativeEnd = Me.UpperBound
    Else
        If EndIndex < 0 And EndIndex < LBound(LocalItems) Then
            RelativeEnd = max(Me.UpperBound + EndIndex, LBound(LocalItems))
        ElseIf EndIndex < LBound(LocalItems) Then
            RelativeEnd = Me.UpperBound
        Else
            RelativeEnd = min(EndIndex, Me.UpperBound)
        End If
    End If
    InternalItems = RecursiveFill(LocalItems, value, RelativeStart, RelativeEnd)
    Set Fill = Me
End Function

'@Description("Parses a string representing an array and stores the outcome.")
Public Function ParseFromString( _
        ByVal SourceString As String, _
        Optional ByVal ValueSeparator As String = CHR_COMMA, _
        Optional ByVal ArrayOpenDelimiter As String, _
        Optional ByVal ArrayClosingDelimiter As String _
    ) As BetterArray
Attribute ParseFromString.VB_Description = "Parses a string representing an array and stores the outcome."
    Dim Opener As String
    Dim Closer As String
    Dim ArraysAreDelimited As Boolean
    Dim result() As Variant
    
    If Len(SourceString) > 0 Then
        If ArrayOpenDelimiter = vbNullString And ArrayClosingDelimiter = vbNullString Then
            Dim FirstChar As String
            Dim LastChar As String
            FirstChar = left$(SourceString, 1)
            LastChar = right$(SourceString, 1)
            ' no array delimiters supplied
            ' see if the diff in ascii values are for first and last chars are less than 3
            ' this covers () [] {} <>
            ' escape numbers incase array is "1,2,3"
            ' escape ucase letters incase array is "A,B,C"
            ' escape lcase letters incase array is "a,b,c"
            If (Asc(LastChar) - Asc(FirstChar) < 3) And _
                    (Asc(FirstChar) < 65 Or Asc(FirstChar) > 90) And _
                    (Asc(FirstChar) < 97 Or Asc(FirstChar) > 122) And _
                    Not IsNumeric(FirstChar) Then
                Opener = FirstChar
                Closer = LastChar
                ArraysAreDelimited = True
            End If
        Else
            ' array delimiters supplied
            Opener = ArrayOpenDelimiter
            Closer = ArrayClosingDelimiter
            ArraysAreDelimited = True
        End If
        
        If ArraysAreDelimited Then
            result = ParseDelimitedArrayString(SourceString, ValueSeparator, Opener, Closer)
        Else
            result = ParseArraySegmentFromString(SourceString, 1, 0, ValueSeparator)
        End If
    Else
        RaiseError EC_NULL_STRING, "ParseFromString", "SourceString"
    End If
    
    Me.Items = result
    Set ParseFromString = Me
End Function

'@Description("Swaps rows for columns & vice versa.")
Public Function transpose() As BetterArray
Attribute transpose.VB_Description = "Swaps rows for columns & vice versa."
    Dim result() As Variant
    Dim LocalItems() As Variant
    Dim LocalType As ArrayTypes
    Dim StoredType As ArrayTypes
    StoredType = This.ArrayType
    LocalItems = InternalItems
    LocalType = GetArrayType(LocalItems)
    Select Case LocalType
    Case ArrayTypes.BA_ONEDIMENSION
        result = Transpose1DArray(LocalItems)
    Case ArrayTypes.BA_MULTIDIMENSION
        ' Sould Never match as MD arrs stored as jagged internally
        result = Transpose2DArray(LocalItems)
    Case ArrayTypes.BA_JAGGED
        result = TransposeArrayOfArrays(LocalItems)
    Case Else
        result = LocalItems
    End Select
    Me.Items = result
    If StoredType = BA_MULTIDIMENSION Then
        LocalType = GetArrayType(result)
        If LocalType = BA_JAGGED Then
            This.ArrayType = BA_MULTIDIMENSION
        End If
    End If
    Set transpose = Me
End Function

'@Description("Returns a new BetterArray instance containing the same values as the current instance.")
Public Function clone() As BetterArray
Attribute clone.VB_Description = "Returns a new BetterArray instance containing the same values as the current instance."
    Dim result As BetterArray
    Set result = New BetterArray
    result.LowerBound = This.LowerBound
    result.Items = Me.Items
    Set clone = result
End Function

'@Description("Clears the current array and resets capacity to default value")
Public Function ResetToDefault() As BetterArray
Attribute ResetToDefault.VB_Description = "Clears the current array and resets capacity to default value"
    This.LowerBound = 0
    ReDim This.Items(This.LowerBound To DEFAULT_CAPACITY + This.LowerBound)
    This.Length = 0
    Me.Capacity = DEFAULT_CAPACITY
    This.ArrayType = BA_UNALLOCATED
    Set ResetToDefault = Me
End Function

'@Description("Clears all entries in the current array but retains existing capacity.")
Public Function Clear() As BetterArray
Attribute Clear.VB_Description = "Clears all entries in the current array but retains existing capacity."
    Dim OldCapacity As Long
    OldCapacity = This.Capacity
    ReDim This.Items(This.LowerBound To OldCapacity + This.LowerBound)
    This.ArrayType = BA_UNALLOCATED
    This.Length = 0
    Me.Capacity = OldCapacity
    Set Clear = Me
End Function

'@Description("Joins one or more arrays onto the end of the current array.")
Public Function Concat(ParamArray Args() As Variant) As BetterArray
Attribute Concat.VB_Description = "Joins one or more arrays onto the end of the current array."
    Dim i As Long
    Dim result() As Variant
    Dim Stored() As Variant
    Dim StoredType As ArrayTypes
    Dim StoredCapacity As Long
    StoredType = This.ArrayType
    StoredCapacity = This.Capacity
    If StoredType <> BA_JAGGED And StoredType <> BA_MULTIDIMENSION Then
        For i = LBound(Args) To UBound(Args)
            If IsArray(Args(i)) Then
                If IsMultidimensionalArray(Args(i)) Then
                    StoredType = BA_MULTIDIMENSION
                    Exit For
                End If
            End If
        Next
    End If
    If This.ArrayType <> BA_UNALLOCATED Then
        Stored = InternalItems
    End If
    result = ConcatDelegate(Stored, Args)
    Me.Items = result
    If StoredType = BA_MULTIDIMENSION Then
        This.ArrayType = StoredType
    End If
    If This.Capacity < StoredCapacity Then
        Me.Capacity = StoredCapacity
    End If
    Set Concat = Me
End Function

'@Description("Writes all of the elements in a Collection objet to the internal array.")
Public Function CopyFromCollection(ByVal SourceCollection As Collection) As BetterArray
Attribute CopyFromCollection.VB_Description = "Writes all of the elements in a Collection objet to the internal array."
    If SourceCollection Is Nothing Then
        RaiseError EC_EXPECTED_COLLECTION_OBJECT, "CopyFromCollection", "SourceCollection"
    End If
    Dim i As Long
    Dim NewItems() As Variant
    This.Length = SourceCollection.Count
    If This.Length = 0 Then
        NewItems = GetEmptyArray
    Else
        ReDim NewItems(This.LowerBound To (This.Length - This.LowerBound - 1))
        For i = 1 To This.Length
            NewItems(i + This.LowerBound - 1) = SourceCollection.item(i)
        Next
    End If
    Me.Items = NewItems
    Set CopyFromCollection = Me
End Function

'@Description("Sorts the stored array in ascending order.")
Public Function Sort(Optional ByVal SortColumn As Long = MISSING_LONG) As BetterArray
Attribute Sort.VB_Description = "Sorts the stored array in ascending order."
    Dim LocalItems() As Variant
    Dim SortedItems() As Variant
    Dim LocalArrayType As ArrayTypes
    Dim LocalSortColumn As Long
    Dim FirstChildLowerBound As Long
    
    Set Sort = Me
    
    If Me.IncludesType("Object") Then
        RaiseError EC_CANNOT_SORT_OBJECTS, "Sort"
        Exit Function
    End If
    
    LocalItems = InternalItems
    LocalArrayType = GetArrayType(LocalItems)
    If LocalArrayType = ArrayTypes.BA_UNALLOCATED Or _
       LocalArrayType = ArrayTypes.BA_UNDEFINED Then
        SortedItems = GetEmptyArray
    Else
        If This.Length > 0 Then
            If LocalArrayType <> BA_ONEDIMENSION Then
                If LocalArrayType = ArrayTypes.BA_MULTIDIMENSION Then
                    LocalItems = MultiToJagged(LocalItems)
                End If
                Dim Depth As Long
                Depth = GetJaggedArrayDepth(LocalItems)
                If Depth > 2 Then
                    RaiseError EC_EXCEEDS_MAX_SORT_DEPTH, "Sort"
                End If
                FirstChildLowerBound = LBound(LocalItems(LBound(LocalItems)))
                If SortColumn = MISSING_LONG Then
                    LocalSortColumn = FirstChildLowerBound
                Else
                    LocalSortColumn = SortColumn - 1 + FirstChildLowerBound
                End If
            End If
            ApplySortMethod _
                LocalItems, _
                LocalArrayType, _
                LocalSortColumn
        End If
        SortedItems = LocalItems
    End If
    Me.Items = SortedItems
End Function

'@Description("Copies a section of the stored array to another location in the same array.")
Public Function CopyWithin( _
        ByVal Target As Long, _
        Optional ByVal StartIndex As Long = MISSING_LONG, _
        Optional ByVal EndIndex As Long = MISSING_LONG _
    ) As BetterArray
Attribute CopyWithin.VB_Description = "Copies a section of the stored array to another location in the same array."
    Dim LocalLength As Long
    Dim RelativeTarget As Long
    Dim RelativeStart As Long
    Dim RelativeEnd As Long
    Dim ToIndex As Long
    Dim FromIndex As Long
    Dim Final As Long
    Dim Count As Long
    Dim Direction As Long
    Dim LocalItems() As Variant
    
    Select Case This.ArrayType
    Case ArrayTypes.BA_UNDEFINED
        RaiseError EC_EXPECTED_ARRAY, "CopyWithin"
    Case ArrayTypes.BA_UNALLOCATED
        RaiseError EC_UNALLOCATED_ARRAY, "CopyWithin"
    Case Else
        LocalItems = InternalItems
        LocalLength = This.Length
        RelativeTarget = Target
        
        If RelativeTarget < 0 Then
            ToIndex = max((LocalLength + RelativeTarget), 0)
        Else
            ToIndex = min(RelativeTarget, LocalLength)
        End If
        
        RelativeStart = IIf(StartIndex = MISSING_LONG, LBound(LocalItems), StartIndex)
        
        If RelativeStart < 0 Then
            FromIndex = max((LocalLength + RelativeStart), 0)
        Else
            FromIndex = min(RelativeStart, LocalLength)
        End If
        
        If EndIndex = MISSING_LONG Then
            RelativeEnd = LocalLength
        Else
            RelativeEnd = EndIndex
        End If
        
        If RelativeEnd < 0 Then
            Final = max((LocalLength + RelativeEnd), 0)
        Else
            Final = min(RelativeEnd, LocalLength)
        End If
        
        Count = min(Final - FromIndex, LocalLength - ToIndex)
        
        If FromIndex < ToIndex And ToIndex < FromIndex + Count Then
            Direction = -1
            Inc FromIndex, Count - 1
            Inc ToIndex, Count - 1
        Else
            Direction = 1
        End If
        
        Do While Count > 0
            If FromIndex >= LBound(LocalItems) And FromIndex <= UBound(LocalItems) Then
                LocalItems(ToIndex) = LocalItems(FromIndex)
            End If
            Inc FromIndex, Direction
            Inc ToIndex, Direction
            dec Count
        Loop
        
        Me.Items = LocalItems
    End Select
    
    Set CopyWithin = Me

End Function

'@Ignore ShadowedDeclaration
'@Description("Filters the stored array to include only values that meet the specified criteria.")
Public Function Filter( _
        ByVal Match As Variant, _
        Optional ByVal Include As Boolean, _
        Optional ByVal Recurse As Boolean, _
        Optional ByVal ColumnIndex As Long = MISSING_LONG _
        ) As BetterArray
    Dim result() As Variant
    Dim LocalItems() As Variant
    Dim LocalType As ArrayTypes
    LocalType = This.ArrayType
    Select Case LocalType
    Case ArrayTypes.BA_UNDEFINED
        RaiseError EC_EXPECTED_ARRAY, "Filter"
    Case ArrayTypes.BA_UNALLOCATED
        result = GetEmptyArray
    Case ArrayTypes.BA_ONEDIMENSION
        LocalItems = InternalItems
        result = FilterOneDimension( _
            LocalItems, _
            Match, _
            Include _
        )
    Case Else
        LocalItems = InternalItems
        If ColumnIndex <> MISSING_LONG Then
            result = FilterByColumn( _
                LocalItems, _
                Match, _
                Include, _
                ColumnIndex _
            )
        Else
            result = RecursiveFilter( _
                LocalItems, _
                Match, _
                Include, _
                Recurse _
            )

        End If
    End Select
    Me.Items = result
    If LocalType = BA_MULTIDIMENSION Then This.ArrayType = LocalType
    Set Filter = Me
End Function


'@Description("Filters the stored array to include only values of the specified type.")
Public Function FilterType( _
        ByVal SearchTypeName As String, _
        Optional ByVal Include As Boolean, _
        Optional ByVal Recurse As Boolean, _
        Optional ByVal ColumnIndex As Long = MISSING_LONG _
        ) As BetterArray
Attribute FilterType.VB_Description = "Filters the stored array to include only values of the specified type."
    Dim result() As Variant
    Dim LocalItems() As Variant
    Dim LocalType As ArrayTypes
    LocalType = This.ArrayType
    
    Select Case LocalType
    Case ArrayTypes.BA_UNDEFINED
        RaiseError EC_EXPECTED_ARRAY, "FilterType"
    Case ArrayTypes.BA_UNALLOCATED
        result = GetEmptyArray
    Case ArrayTypes.BA_ONEDIMENSION
        LocalItems = InternalItems
        result = FilterOneDimension( _
            LocalItems, _
            SearchTypeName, _
            Include, _
            True _
        )
    Case Else
        LocalItems = InternalItems
        If ColumnIndex <> MISSING_LONG Then
            result = FilterByColumn( _
                LocalItems, _
                SearchTypeName, _
                Include, _
                ColumnIndex, _
                True _
            )
        Else
            result = RecursiveFilter( _
                LocalItems, _
                SearchTypeName, _
                Include, _
                Recurse, _
                True _
            )

        End If
    End Select
      
    Me.Items = result
    If LocalType = BA_MULTIDIMENSION Then This.ArrayType = LocalType
    Set FilterType = Me
End Function

'@Description("Reverses the order of elements in the array. The first array element becomes the last, and the last array element becomes the first.")
Public Function Reverse(Optional ByVal Recurse As Boolean) As BetterArray
Attribute Reverse.VB_Description = "Reverses the order of elements in the array. The first array element becomes the last, and the last array element becomes the first."
    Dim LocalItems() As Variant
    Dim result() As Variant
    Dim CurrentType As ArrayTypes
    CurrentType = This.ArrayType
    Select Case CurrentType
    Case BA_UNDEFINED
        RaiseError EC_UNDEFINED_ARRAY, "Reverse"
    Case BA_ONEDIMENSION, BA_MULTIDIMENSION, BA_JAGGED
        LocalItems = InternalItems
        result = RecursiveReverse(LocalItems, Recurse)
        Me.Items = result
        This.ArrayType = CurrentType
    End Select
    
    Set Reverse = Me
End Function

'@Description("Flattens a Multi-Dimensional or Jagged array into One Dimension arrays.")
Public Function Flatten() As BetterArray
Attribute Flatten.VB_Description = "Flattens a Multi-Dimensional or Jagged array into One Dimension arrays."
    Dim LocalItems() As Variant
    Dim result As BetterArray
        
    ' noop on 1d or unalloc
    ' md & jagged both stored as jagged
    Select Case This.ArrayType
    Case BA_UNDEFINED
        RaiseError EC_UNDEFINED_ARRAY, "Flatten"
    Case BA_MULTIDIMENSION, BA_JAGGED
        LocalItems = InternalItems
        Set result = New BetterArray
        result.LowerBound = This.LowerBound
        RecursiveFlatten LocalItems, result
        Me.Items = result.Items
    End Select

    Set Flatten = Me
End Function

'@Description("shuffles the order of the stored array.")
Public Function Shuffle(Optional ByVal Recurse As Boolean) As BetterArray
Attribute Shuffle.VB_Description = "shuffles the order of the stored array."
    Dim LocalItems() As Variant
    Dim result() As Variant
    Dim CurrentType As ArrayTypes
    CurrentType = This.ArrayType
    Select Case CurrentType
    Case BA_UNDEFINED
        RaiseError EC_UNDEFINED_ARRAY, "Shuffle"
    Case BA_ONEDIMENSION, BA_MULTIDIMENSION, BA_JAGGED
        LocalItems = InternalItems
        result = RecursiveShuffle(LocalItems, Recurse)
        Me.Items = result
        This.ArrayType = CurrentType
    End Select
    
    Set Shuffle = Me
End Function

'@Description("filters the array to contain only unique elements")
Public Function Unique(Optional ByVal ColumnIndex As Long = MISSING_LONG) As BetterArray
Attribute Unique.VB_Description = "filters the array to contain only unique elements"
    Dim LocalItems() As Variant
    Dim LocalType As ArrayTypes
    Dim result As BetterArray
    Dim i As Long
    
    LocalItems = InternalItems
    LocalType = This.ArrayType
    Set result = New BetterArray
    result.LowerBound = Me.LowerBound
    If (LocalType = BA_JAGGED Or LocalType = BA_MULTIDIMENSION) And ColumnIndex <> MISSING_LONG Then
        Dim LocalDepth As Long
        LocalDepth = GetJaggedArrayDepth(LocalItems)
        If LocalDepth = 2 Then
            ' if array is 2d we can compare unique based on specified column
            Dim LocalColumn As Long
            Dim ComparisonValues() As Variant
            Dim Comparator As BetterArray
            Dim Bounds() As Long
            
            Set Comparator = New BetterArray
            Bounds = GetMaxBoundsAtDimension(LocalItems, 2)
            Comparator.LowerBound = Bounds(0)
            LocalColumn = ColumnIndex - 1 + Bounds(0)
            ' determine column to compare - columnIndex if valid, lbound if not
            If LocalColumn < Bounds(0) Or LocalColumn > Bounds(1) Then
                LocalColumn = Bounds(0)
            End If
            
            ' extract the column
            ComparisonValues = Me.ExtractSegment(ColumnIndex:=LocalColumn)
            ' store the extracted column in a new BetterArray instance
            Comparator.Items = ComparisonValues
            
            For i = LBound(LocalItems) To UBound(LocalItems)
                If Comparator.IndexOf(LocalItems(i)(LocalColumn)) = i Then
                    result.Push LocalItems(i)
                End If
            Next
            
        Else
            ' array has more then two dimensions
            ' just return unique in outermost array
            For i = LBound(LocalItems) To UBound(LocalItems)
                If Me.IndexOf(LocalItems(i)) = i Then
                    result.Push LocalItems(i)
                End If
            Next
        
        End If
    Else
        ' no columnIndex arg or array is one-dimension
        ' unique in outermost array
        For i = LBound(LocalItems) To UBound(LocalItems)
            If Me.IndexOf(LocalItems(i)) = i Then
                result.Push LocalItems(i)
            End If
        Next
    End If
    

    Me.Items = result.Items
    This.ArrayType = LocalType
    Set Unique = Me
End Function

'@Description("Accepts a path argument pointing to a comma-separated values (CSV) file and stores the delimited values contained within to the internal array.")
Public Function FromCSVFile( _
    ByVal path As String, _
    Optional ByVal ColumnDelimiter As String = CHR_COMMA, _
    Optional ByVal RowDelimiter As String, _
    Optional ByVal Quote As String = CHR_QUOTE, _
    Optional ByVal IgnoreFirstRow As Boolean, _
    Optional ByVal DuckType As Boolean _
) As BetterArray
Attribute FromCSVFile.VB_Description = "Accepts a path argument pointing to a comma-separated values (CSV) file and stores the delimited values contained within to the internal array."
    Dim RawData As String
    Dim LineEnding As String
    
    RawData = ReadStringFromFile(path)
    If RowDelimiter = vbNullString Then
        LineEnding = DetectLineEndings(RawData)
    Else
        LineEnding = RowDelimiter
    End If
    
    Set FromCSVFile = FromCSVString( _
        CSVString:=RawData, _
        ColumnDelimiter:=ColumnDelimiter, _
        RowDelimiter:=LineEnding, _
        Quote:=Quote, _
        IgnoreFirstRow:=IgnoreFirstRow, _
        DuckType:=DuckType _
    )
End Function

'@Description("Accepts a string argument representing the contents of a comma-separated values (CSV) file and stores the delimited values contained within to the internal array.")
Public Function FromCSVString( _
    ByVal CSVString As String, _
    Optional ByVal ColumnDelimiter As String = CHR_COMMA, _
    Optional ByVal RowDelimiter As String, _
    Optional ByVal Quote As String = CHR_QUOTE, _
    Optional ByVal IgnoreFirstRow As Boolean, _
    Optional ByVal DuckType As Boolean _
) As BetterArray
Attribute FromCSVString.VB_Description = "Accepts a string argument representing the contents of a comma-separated values (CSV) file and stores the delimited values contained within to the internal array."
    Dim LocalType As ArrayTypes
    Dim Parsed() As Variant
    Dim LineEnding As String
    
    If RowDelimiter = vbNullString Then
        LineEnding = DetectLineEndings(CSVString)
    Else
        LineEnding = RowDelimiter
    End If
    
    If This.ArrayType = BA_MULTIDIMENSION Then
        LocalType = BA_MULTIDIMENSION
    Else
        LocalType = BA_JAGGED
    End If
     
    Parsed = ParseCSV( _
        Expression:=CSVString, _
        ColumnDelimiter:=ColumnDelimiter, _
        RowDelimiter:=LineEnding, _
        Quote:=Quote, _
        IgnoreFirstRow:=IgnoreFirstRow, _
        ReturnJagged:=IIf(LocalType = BA_JAGGED, True, False), _
        Base:=This.LowerBound, _
        DuckType:=DuckType _
    )

    This.Length = GetArrayLength(Parsed)
    This.Capacity = UBound(Parsed)
    This.ArrayType = LocalType
    This.Items = Parsed

    Set FromCSVString = Me
End Function

'@Description("Returns a string representation of the stored array to use as output for a CSV file")
Public Function ToCSVString( _
    Optional ByRef Headers As Variant, _
    Optional ByVal ColumnDelimiter As String = CHR_COMMA, _
    Optional ByVal RowDelimiter As String = vbCrLf, _
    Optional ByVal Quote As String = CHR_QUOTE, _
    Optional ByVal EncloseAllInQuotes As Boolean, _
    Optional ByVal DateFormat As String, _
    Optional ByVal NumberFormat As String _
) As String
Attribute ToCSVString.VB_Description = "Returns a string representation of the stored array to use as output for a CSV file"
    Dim LocalItems() As Variant
    Dim Depth As Long
    Dim EncodedRecords() As String
    Dim result As String
    Dim HeadersArray() As Variant
    
    LocalItems = InternalItems
    Depth = GetJaggedArrayDepth(LocalItems)
    If Depth > 0 Then 'check array is allocated
        If Depth = 1 Then
            '1d array
            LocalItems = ConvertOneDimensionArrayToJagged(LocalItems)
        End If
        If Not IsMissing(Headers) Then
            If IsArray(Headers) Then
                HeadersArray = Array(Headers)
                LocalItems = InternalConcat(HeadersArray, LocalItems)
            End If
        End If
        EncodedRecords = EncodeCSVRecords(LocalItems, ColumnDelimiter, RowDelimiter, EncloseAllInQuotes, DateFormat, NumberFormat)
        result = BuildCSVString(EncodedRecords, ColumnDelimiter, RowDelimiter)
    End If
    ToCSVString = result
End Function

'@Description("Writes stored array to CSV file")
Public Function ToCSVFile( _
    ByVal path As String, _
    Optional ByRef Headers As Variant, _
    Optional ByVal ColumnDelimiter As String = CHR_COMMA, _
    Optional ByVal RowDelimiter As String = vbCrLf, _
    Optional ByVal Quote As String = CHR_QUOTE, _
    Optional ByVal EncloseAllInQuotes As Boolean, _
    Optional ByVal DateFormat As String, _
    Optional ByVal NumberFormat As String _
) As String
Attribute ToCSVFile.VB_Description = "Writes stored array to CSV file"
    Dim Content As String
    ' test if path valid - if not handle err
    
    ' get ouput string
    If IsMissing(Headers) Then
        Content = Me.ToCSVString( _
            ColumnDelimiter:=ColumnDelimiter, _
            RowDelimiter:=RowDelimiter, _
            Quote:=Quote, _
            EncloseAllInQuotes:=EncloseAllInQuotes, _
            DateFormat:=DateFormat, _
            NumberFormat:=NumberFormat _
        )
    Else
        Content = Me.ToCSVString( _
            Headers, _
            ColumnDelimiter, _
            RowDelimiter, _
            Quote, _
            EncloseAllInQuotes, _
            DateFormat, _
            NumberFormat _
        )
    End If
    
    ' write output
    PrintStringToFile path, Content
    
    ToCSVFile = Content
End Function


'''''''''''''''''''
' Private Methods '

'''''''''''''''''''
'@Description("Tries to guess line endings used in a string")
Private Function DetectLineEndings(ByVal source As String) As String
Attribute DetectLineEndings.VB_Description = "Tries to guess line endings used in a string"
    If VBA.Strings.instr(source, vbCrLf) Then
        DetectLineEndings = vbCrLf
        Exit Function
    End If
    If VBA.Strings.instr(source, vbLf) Then
        DetectLineEndings = vbLf
        Exit Function
    End If
    If VBA.Strings.instr(source, vbCr) Then
        DetectLineEndings = vbCr
        Exit Function
    End If
    ' default to CRLF
    DetectLineEndings = vbCrLf
End Function

'@Description("Reads a text file to a string from a specified path")
Private Function ReadStringFromFile(ByVal path As String) As String
Attribute ReadStringFromFile.VB_Description = "Reads a text file to a string from a specified path"
    Dim File As Long
    Dim ByteCount As Long
    Dim result As String
    If dir(path) <> vbNullString Then
        File = FreeFile
        Open path For Input Access Read Lock Read As File
            ByteCount = LOF(File)
            result = Input$(ByteCount, File)
        Close File
    End If
    ReadStringFromFile = result
End Function

'@Description("Prints as string to a text file at the specified path")
Private Sub PrintStringToFile(ByVal path As String, ByVal Content As String)
Attribute PrintStringToFile.VB_Description = "Prints as string to a text file at the specified path"
    Dim File As Long
    File = FreeFile
    Open path For Output Access Write As File
        Print #File, Content
    Close File
End Sub

'@Description("Surrounds the provided string with quote characters")
Private Function WrapQuote(Optional ByVal source As String = vbNullString) As String
Attribute WrapQuote.VB_Description = "Surrounds the provided string with quote characters"
    WrapQuote = CHR_QUOTE & source & CHR_QUOTE
End Function

'@Description("Concatenates all records into a single string to be output as a csv")
Private Function BuildCSVString( _
    ByRef Records() As String, _
    ByVal ColumnDelimiter As String, _
    ByVal RowDelimiter As String _
) As String
Attribute BuildCSVString.VB_Description = "Concatenates all records into a single string to be output as a csv"
    Dim i As Long
    Dim j As Long
    Dim LastRow As Long
    Dim LastCol As Long
    Dim ValidRow As Boolean
    
    LastRow = UBound(Records)
    LastCol = UBound(Records, 2)
    StringBuilder NewString:=True
    For i = LBound(Records) To UBound(Records)
        'skip entirely blank rows
        ValidRow = False
        For j = LBound(Records, 2) To UBound(Records, 2)
            If Records(i, j) <> vbNullString Then
                ValidRow = True
                Exit For
            End If
        Next
        If ValidRow Then
            For j = LBound(Records, 2) To UBound(Records, 2)
                StringBuilder Records(i, j)
                If j = LastCol Then
                    If i <> LastRow Then
                        StringBuilder RowDelimiter
                    End If
                Else
                    StringBuilder ColumnDelimiter
                End If
            Next
        End If
    Next
    BuildCSVString = StringBuilder(Final:=True)
End Function

'@Description("Applies RFC 4180 business rules to all fields")
Private Function EncodeCSVRecords( _
    ByRef Records() As Variant, _
    ByVal ColumnDelimiter As String, _
    ByVal RowDelimiter As String, _
    ByVal EncloseAllInQuotes As Boolean, _
    ByVal DateFormat As String, _
    ByVal NumberFormat As String _
) As String()
Attribute EncodeCSVRecords.VB_Description = "Applies RFC 4180 business rules to all fields"
    Dim FirstDimBounds() As Long
    Dim SecondDimBounds() As Long
    Dim i As Long
    Dim j As Long
    Dim result() As String
    Dim CurrentField As Variant
    
    FirstDimBounds = GetArrayBounds(Records)
    SecondDimBounds = GetMaxBoundsAtDimension(Records, 2)
    ReDim result( _
        FirstDimBounds(0) To FirstDimBounds(1), _
        SecondDimBounds(0) To SecondDimBounds(1) _
    )
    For i = FirstDimBounds(0) To FirstDimBounds(1)
        If IsArray(Records(i)) Then
            For j = LBound(Records(i)) To UBound(Records(i))
                CurrentField = GetScalarRepresentation(Records(i)(j))
                result(i, j) = EncodeCSVField( _
                    CurrentField, _
                    ColumnDelimiter, _
                    RowDelimiter, _
                    EncloseAllInQuotes, _
                    DateFormat, _
                    NumberFormat _
                )
            Next
        End If
    Next
    EncodeCSVRecords = result
End Function

'@Description("Applies RFC 4180 business rules to the encoding of a CSV field")
Private Function EncodeCSVField( _
    ByVal Field As Variant, _
    ByVal ColumnDelimiter As String, _
    ByVal RowDelimiter As String, _
    ByVal EncloseAllInQuotes As Boolean, _
    ByVal DateFormat As String, _
    ByVal NumberFormat As String _
) As String
Attribute EncodeCSVField.VB_Description = "Applies RFC 4180 business rules to the encoding of a CSV field"
    ' https://tools.ietf.org/html/rfc4180#section-2
    Dim LocalField As String
    
    If IsDate(Field) And DateFormat <> vbNullString Then
        On Error Resume Next
        LocalField = Format$(Field, DateFormat)
        On Error GoTo 0
    ElseIf IsNumeric(Field) And NumberFormat <> vbNullString Then
        On Error Resume Next
        LocalField = Format$(Field, NumberFormat)
        On Error GoTo 0
    End If
    If LocalField = vbNullString Then
        LocalField = CStr(Field)
    End If
    LocalField = EscapeCharInString(LocalField, CHR_QUOTE, CHR_QUOTE)
    If EncloseAllInQuotes Or _
        VBA.Strings.instr(LocalField, RowDelimiter) Or _
        VBA.Strings.instr(LocalField, ColumnDelimiter) Then
        LocalField = WrapQuote(LocalField)
    End If
    
    EncodeCSVField = LocalField
    Exit Function
End Function

'@Description("Escapes a substring in a string using a provided Escape substring")
Private Function EscapeCharInString( _
    ByVal Destination As String, _
    ByVal Target As String, _
    ByVal Escape As String, _
    Optional ByVal BothSides As Boolean _
) As String
Attribute EscapeCharInString.VB_Description = "Escapes a substring in a string using a provided Escape substring"
    Dim index As Long
    Dim TargetLength As Long
    Dim EscapeLength As String
    Dim result As String
    
    TargetLength = Len(Target)
    EscapeLength = Len(Escape)
    result = Destination
    index = 1
    Do
        index = VBA.Strings.instr(index, Destination, Target)
        If index Then
            result = InsertIntoStringAtIndex(result, Escape, index)
            Inc index, EscapeLength + TargetLength
            If BothSides Then
                result = InsertIntoStringAtIndex(result, Escape, index)
            End If
        End If
    Loop While index > 0
    
    EscapeCharInString = result
End Function

'@Description("Inserts a substring into a destination string starting at the provided index")
Private Function InsertIntoStringAtIndex( _
    ByVal Destination As String, _
    ByVal source As String, _
    ByVal index As Long _
) As String
Attribute InsertIntoStringAtIndex.VB_Description = "Inserts a substring into a destination string starting at the provided index"
    Dim Front As String
    Dim Back As String
    If index > 1 Then
        Front = left$(Destination, index)
    End If
    
    If index < Len(Destination) Then
        Back = right$(Destination, Len(Destination) - index)
    End If
    InsertIntoStringAtIndex = Front & source & Back
End Function

'@Description("Utility function which delegates to ConcatDelegate")
Private Function InternalConcat(ParamArray Args() As Variant) As Variant()
Attribute InternalConcat.VB_Description = "Utility function which delegates to ConcatDelegate"
    Dim First() As Variant
    First = Array()
    InternalConcat = ConcatDelegate(First, Args)
End Function

'@Description("Concatenates Passed Arrays. Do not use as utility function")
Private Function ConcatDelegate(ByRef First() As Variant, ParamArray Args() As Variant) As Variant()
Attribute ConcatDelegate.VB_Description = "Concatenates Passed Arrays. Do not use as utility function"
    ' NOTE don't call this internally as a utility. use InternalConcat
    Dim i As Long
    Dim Cursor As Long
    Dim NewLength As Long
    Dim rest() As Variant
    Dim result() As Variant
    Dim Current() As Variant
    
    rest = Args(0)
    Cursor = This.LowerBound
    If IsArrayAllocated(First) Then
        Cursor = LBound(First)
    ElseIf IsArray(rest(LBound(rest))) Then
        If IsArrayAllocated(rest(LBound(rest))) Then
            Cursor = LBound(rest(LBound(rest)))
        End If
    End If
    
    NewLength = GetArrayLength(First) + GetTotalLengthOfNestedArrays(rest)
    ReDim result(Cursor To max(Cursor + NewLength - 1, Cursor))
    
    InsertArrayAtIndex result, First, Cursor
    For i = LBound(rest) To UBound(rest)
        If IsArray(rest(i)) Then
            Current = rest(i)
            If IsMultidimensionalArray(Current) Then
                Current = MultiToJagged(Current)
            End If
            InsertArrayAtIndex result, Current, Cursor
        Else
            LetOrSetElement result(Cursor), rest(i)
            Inc Cursor
        End If
    Next
    ConcatDelegate = result
End Function

'@Description("Places the Values in Source within Destination starting at Index")
Private Sub InsertArrayAtIndex(ByRef Destination() As Variant, ByRef source() As Variant, ByRef index As Long)
Attribute InsertArrayAtIndex.VB_Description = "Places the Values in Source within Destination starting at Index"
    Dim Offset As Long
    Dim SourceLength As Long
    Dim StartingIndex As Long
    If IsArrayAllocated(source) Then
        StartingIndex = index
        Offset = StartingIndex - LBound(source)
        SourceLength = GetArrayLength(source)
        Do While index < StartingIndex + SourceLength
            LetOrSetElement Destination(index), source(index - Offset)
            Inc index
        Loop
    End If
End Sub

'@Description("Returns the combined length of all nested arrays")
Private Function GetTotalLengthOfNestedArrays(ByRef source() As Variant) As Long
Attribute GetTotalLengthOfNestedArrays.VB_Description = "Returns the combined length of all nested arrays"
    Dim i As Long
    Dim result As Long
    Dim Current() As Variant
    For i = LBound(source) To UBound(source)
        If IsArray(source(i)) Then
            Current = source(i)
            Inc result, GetArrayLength(Current)
        End If
    Next
    GetTotalLengthOfNestedArrays = result
End Function

'@Description("Truncates the number of rows in an array to the given amount")
Private Function TrimColumnsMultidimensionArray(ByRef Original() As Variant, ByVal AvailableColumns As Long) As Variant()
Attribute TrimColumnsMultidimensionArray.VB_Description = "Truncates the number of rows in an array to the given amount"
    Dim i As Long
    Dim j As Long
    Dim result() As Variant
    Dim OuterBounds(0 To 1) As Long
    Dim InnerBounds(0 To 1) As Long
    Dim CountColumns As Long
    
    CountColumns = UBound(Original, 2) - LBound(Original, 2) + 1
    If CountColumns > AvailableColumns Then
        OuterBounds(0) = LBound(Original, 1)
        OuterBounds(1) = UBound(Original, 1)
        InnerBounds(0) = LBound(Original, 2)
        InnerBounds(1) = InnerBounds(0) + AvailableColumns - 1
        ReDim result(OuterBounds(0) To OuterBounds(1), InnerBounds(0) To InnerBounds(1))
        For i = OuterBounds(0) To OuterBounds(1)
            For j = InnerBounds(0) To InnerBounds(1)
                LetOrSetElement result(i, j), Original(i, j)
            Next
        Next
    Else
        result = Original
    End If
    TrimColumnsMultidimensionArray = result
End Function

'@Description("Truncates the number of rows in an array to the given amount")
Private Function TrimRowsMultidimensionArray(ByRef Original() As Variant, ByVal AvailableRows As Long) As Variant()
Attribute TrimRowsMultidimensionArray.VB_Description = "Truncates the number of rows in an array to the given amount"
    Dim i As Long
    Dim j As Long
    Dim result() As Variant
    Dim OuterBounds(0 To 1) As Long
    Dim InnerBounds(0 To 1) As Long
    Dim CountRows As Long
    
    CountRows = UBound(Original, 1) - LBound(Original, 1) + 1
    If CountRows > AvailableRows Then
        OuterBounds(0) = LBound(Original, 1)
        OuterBounds(1) = OuterBounds(0) + AvailableRows - 1
        InnerBounds(0) = LBound(Original, 2)
        InnerBounds(1) = UBound(Original, 2)
        ReDim result(OuterBounds(0) To OuterBounds(1), InnerBounds(0) To InnerBounds(1))
        For i = OuterBounds(0) To OuterBounds(1)
            For j = InnerBounds(0) To InnerBounds(1)
                LetOrSetElement result(i, j), Original(i, j)
            Next
        Next
    Else
        result = Original
    End If
    TrimRowsMultidimensionArray = result
End Function

'@Description("Increments an index")
Private Function Inc(ByRef index As Long, Optional ByVal value As Long = 1) As Long
Attribute Inc.VB_Description = "Increments an index"
    index = index + value
    Inc = index
End Function

'@Description("Decrements an index")
Private Function dec(ByRef index As Long, Optional ByVal value As Long = 1) As Long
Attribute dec.VB_Description = "Decrements an index"
    index = index - value
    dec = index
End Function

'@Description("Populates TString Types")
Private Function StringFactory(ByRef Expression As String) As TString
Attribute StringFactory.VB_Description = "Populates TString Types"
    Dim result As TString
    result.text = Expression
    result.Length = Len(Expression)
    result.ByteLength = LenB(Expression)
    StringFactory = result
End Function

'@Description("Returns the next byte position in the string of the specified delimiter")
Private Function NextDelimBytePos( _
    ByRef Expression As TString, _
    ByRef delimiter As TString, _
    Optional ByRef StartIndex As Long = 1 _
) As Long
Attribute NextDelimBytePos.VB_Description = "Returns the next byte position in the string of the specified delimiter"
    Dim result As Long
    result = InStrB(StartIndex, Expression.text, delimiter.text, vbBinaryCompare)
    Do Until (result And 1) Or (result = 0)
        result = InStrB(result + 1, Expression.text, delimiter.text, vbBinaryCompare)
    Loop
    NextDelimBytePos = result
End Function

'@Description("Splits the provided string into rows based on the provided row delimiter")
Private Function GetCSVRows( _
    ByRef Expr As TString, _
    ByRef RowDelim As TString, _
    ByRef LiteralDelim As TString _
) As String()
Attribute GetCSVRows.VB_Description = "Splits the provided string into rows based on the provided row delimiter"
    Dim RowDelimIndex As Long
    Dim LastRowDelim As Long
    Dim RowIndex As Long
    Dim BlankTrailingRows As Long
    Dim MaxRows As Long
    Dim LineEndIndices() As Long
    Dim LiteralDelimIndex As Long
    Dim CountRows As Long
    Dim i As Long
    Dim Cursor As Long
    Dim CSVRows() As String

    ' find first row delimiter
    RowDelimIndex = NextDelimBytePos(Expr, RowDelim)

    ' find last row delimiter
    LastRowDelim = InStrRev(Expr.text, RowDelim.text)
    RowIndex = Expr.Length + 1
    Do While RowIndex - LastRowDelim = RowDelim.Length
        RowIndex = LastRowDelim
        LastRowDelim = InStrRev(Expr.text, RowDelim.text, LastRowDelim)
        Inc BlankTrailingRows
    Loop
    RowIndex = Empty

    ' estimate max number of rows - does not account for line breaks within strings
    MaxRows = (Expr.Length - Len(Replace(Expr.text, RowDelim.text, vbNullString))) / RowDelim.Length + 1
    ReDim LineEndIndices(0 To MaxRows)
        
    ' find first quote delimiter
    LiteralDelimIndex = NextDelimBytePos(Expr, LiteralDelim)
    
    Do While RowDelimIndex > 0
        ' see if row delimiter before quote delimiter
        If RowDelimIndex + RowDelim.ByteLength <= LiteralDelimIndex Or LiteralDelimIndex = 0 Then
            ' no preceding literalDelim - iterate row count
            LineEndIndices(CountRows) = RowDelimIndex
            RowDelimIndex = NextDelimBytePos(Expr, RowDelim, RowDelimIndex + RowDelim.ByteLength)
            Inc CountRows
        Else
            ' quote delimiter before row delimiter
            ' find next quote delim
            LiteralDelimIndex = NextDelimBytePos(Expr, LiteralDelim, LiteralDelimIndex + 2)
           ' see if closing quote delim found
            If LiteralDelimIndex Then
                ' find next row delim
                RowDelimIndex = NextDelimBytePos(Expr, RowDelim, LiteralDelimIndex + 2)
                ' if next row delim found
                If RowDelimIndex Then
                    ' find next quote delim
                    LiteralDelimIndex = NextDelimBytePos(Expr, LiteralDelim, LiteralDelimIndex + 2)
                End If
            End If
        End If
    Loop
    
    LineEndIndices(CountRows) = Expr.ByteLength + 1
    dec CountRows, BlankTrailingRows - 1
    ReDim CSVRows(0 To CountRows - 1)
    Cursor = 1
    For i = 0 To CountRows - 1
        CSVRows(i) = MidB$(Expr.text, Cursor, LineEndIndices(i) - Cursor)
        Cursor = LineEndIndices(i) + RowDelim.ByteLength
    Next
    GetCSVRows = CSVRows
End Function

'@Description("Counts the number of delimited columns in a provided string")
Private Function CountCSVColumns(ByRef FirstRow As String, ByRef LiteralDelim As TString, ByVal ColumnDelimiter As String) As Long
Attribute CountCSVColumns.VB_Description = "Counts the number of delimited columns in a provided string"
    ' Each line should contain the same number of fields
    ' https://www.loc.gov/preservation/digital/formats/fdd/fdd000323.shtml
    ' so we can just count the columnd in the first row
    Dim i As Long
    Dim InQuote As Boolean
    Dim CountColumns As Long
    Dim Char As String
    CountColumns = 1
    For i = 0 To Len(FirstRow)
        Char = Mid$(FirstRow, i + 1, 1)
        Select Case Char
            Case LiteralDelim.text
                InQuote = Not InQuote
            Case ColumnDelimiter
                If Not InQuote Then
                    Inc CountColumns
                End If
        End Select
    Next
    CountCSVColumns = CountColumns
End Function

'@Description("Parses CSV string into a 2d or jagged array")
Private Function ParseCSV( _
    ByRef Expression As String, _
    ByVal ColumnDelimiter As String, _
    ByVal RowDelimiter As String, _
    ByRef Quote As String, _
    ByVal IgnoreFirstRow As Boolean, _
    ByVal ReturnJagged As Boolean, _
    ByVal Base As Long, _
    ByVal DuckType As Boolean _
) As Variant()
Attribute ParseCSV.VB_Description = "Parses CSV string into a 2d or jagged array"
    ' CSV is a simple format for representing a rectangular array (matrix) of numeric and textual values.
    ' It an example of a "flat file" format.
    ' It is a delimited data format that has fields/columns separated by the comma character %x2C (Hex 2C)
    ' and records/rows/lines separated by characters indicating a line break.
    ' RFC 4180 stipulates the use of CRLF pairs to denote line breaks, where CR is %x0D (Hex 0D) and LF is %x0A (Hex 0A).
    ' Each line should contain the same number of fields.
    ' Fields that contain a special character (comma, CR, LF, or double quote), must be "escaped" by enclosing them in double quotes (Hex 22).
    ' An optional header line may appear as the first line of the file with the same format as normal record lines.
    ' This header will contain names corresponding to the fields in the file and should contain the same number of fields as the records in the rest of the file.
    ' CSV commonly employs US-ASCII as character set, but other character sets are permitted.
    ' https://www.loc.gov/preservation/digital/formats/fdd/fdd000323.shtml

    Dim i As Long
    Dim j As Long
    Dim Cursor As Long
    Dim ColumnIndex As Long
    Dim CountColumns As Long
    Dim CountRows As Long
    Dim LastRow As Long
    Dim LastColumn As Long
    Dim StartRow As Long
    Dim InQuote As Boolean
    Dim Buffer As String
    Dim Char As String
    Dim Frag As String
    Dim CSVRows() As String
    Dim JaggedRow() As Variant
    Dim Results() As Variant
    Dim element As Variant
    Dim Expr As TString
    Dim RowDelim As TString
    Dim LiteralDelim As TString
    
    Expr = StringFactory(Expression)
    RowDelim = StringFactory(RowDelimiter)
    LiteralDelim = StringFactory(Quote)
    
    If Expr.ByteLength = 0 Or RowDelim.ByteLength = 0 Then
        ' TODO: Raise Err?
        ParseCSV = Array()
        Exit Function
    End If

    CSVRows = GetCSVRows(Expr, RowDelim, LiteralDelim)
    CountColumns = CountCSVColumns(CSVRows(0), LiteralDelim, ColumnDelimiter)
    CountRows = UBound(CSVRows) - LBound(CSVRows) + 1
    
    If IgnoreFirstRow Then
        StartRow = 1
    Else
        StartRow = 0
    End If
    
    LastRow = Base + CountRows - 1 - StartRow
    LastColumn = Base + CountColumns - 1
    If ReturnJagged Then
        ReDim JaggedRow(Base To LastColumn)
        ReDim Results(Base To LastRow)
    Else
        ReDim Results(Base To LastRow, Base To LastColumn)
    End If
    
    For i = StartRow To LastRow
        ColumnIndex = Base
        Buffer = CSVRows(i)
        Cursor = 1
        For j = 0 To Len(Buffer)
            Char = Mid$(Buffer, j + 1, 1)
            If Char = LiteralDelim.text Then
                InQuote = Not InQuote
            ElseIf Char = ColumnDelimiter Or j = Len(Buffer) Then
                If Not InQuote Then
                    Frag = Mid$(Buffer, Cursor, j - Cursor + 1)
                    If DuckType Then
                        element = DuckTypeElement(Frag)
                    Else
                        element = UnquoteString(Frag)
                    End If
                    If ReturnJagged Then
                        JaggedRow(ColumnIndex) = element
                    Else
                        Results(i - StartRow, ColumnIndex) = element
                    End If
                    Cursor = j + 2
                    Inc ColumnIndex
                    Frag = vbNullString
                End If
            End If
        Next
        If ReturnJagged Then
            Results(i - StartRow) = JaggedRow
            ' ReDim jaggedRow(Base To lastColumn)
        End If
    Next
    ParseCSV = Results
End Function

'@Description("Recursvely fills the array (and nested arrays) with the passed value.")
Private Function RecursiveFill( _
        ByRef SourceArray() As Variant, _
        ByVal value As Variant, _
        Optional ByVal StartIndex As Long = MISSING_LONG, _
        Optional ByVal EndIndex As Long = MISSING_LONG _
    ) As Variant()
Attribute RecursiveFill.VB_Description = "Recursvely fills the array (and nested arrays) with the passed value."
    Dim RelativeStart As Long
    Dim RelativeEnd As Long
    Dim i As Long
    
    If StartIndex = MISSING_LONG Then
        RelativeStart = LBound(SourceArray)
    Else
        RelativeStart = StartIndex
    End If
    If EndIndex = MISSING_LONG Then
        RelativeEnd = UBound(SourceArray)
    Else
        RelativeEnd = EndIndex
    End If
    For i = RelativeStart To RelativeEnd
        If IsArray(SourceArray(i)) Then
            Dim PassThru() As Variant
            PassThru = RecursiveFill(PassThru, value)
        Else
            LetOrSetElement SourceArray(i), value
        End If
    Next
    RecursiveFill = SourceArray
End Function

'@Description("Recursively checks if the passed array only includes the search element.")
Private Function RecursiveEvery( _
        ByVal SearchElement As Variant, _
        ByRef SearchArray() As Variant, _
        Optional ByVal FromIndex As Long, _
        Optional ByVal CompareTypeNames As Boolean _
    ) As Boolean
Attribute RecursiveEvery.VB_Description = "Recursively checks if the passed array only includes the search element."
    Dim LocalLowerBound As Long
    Dim LocalUpperBound As Long
    Dim i As Long
    
    LocalLowerBound = LBound(SearchArray)
    If FromIndex > LocalLowerBound Then LocalLowerBound = FromIndex
    LocalUpperBound = UBound(SearchArray)

    For i = LocalLowerBound To LocalUpperBound
        If IsArray(SearchArray(i)) Then
            Dim PassThru() As Variant
            PassThru = SearchArray(i)
            If Not RecursiveEvery(SearchElement, PassThru, CompareTypeNames:=CompareTypeNames) Then
                Exit Function
            End If
        ElseIf CompareTypeNames Then
            If Not InStr( _
                    UCase$(TypeName(SearchArray(i))), _
                    UCase$(CStr(SearchElement)) _
                ) > 0 Then
                Exit Function
            End If
        Else
            If Not ElementsAreEqual(SearchElement, SearchArray(i)) Then
                Exit Function
            End If
        End If
    Next
    
    RecursiveEvery = True
End Function

'@Description("shuffles the order of the passed array.")
Private Function RecursiveShuffle( _
        ByRef SourceArray() As Variant, _
        Optional ByVal Recurse As Boolean _
    ) As Variant()
Attribute RecursiveShuffle.VB_Description = "shuffles the order of the passed array."
    ' https://en.wikipedia.org/wiki/Fisher%E2%80%93Yates_shuffle#The_modern_algorithm
    Dim i As Long
    Dim j As Long
    Dim Lower As Long
    Dim Upper As Long
    Dim Nested() As Variant
    Lower = LBound(SourceArray)
    Upper = UBound(SourceArray)
    Randomize
    For i = Upper To Lower + 1 Step -1
        If IsArray(SourceArray(i)) And Recurse Then
            Nested = SourceArray(i)
            SourceArray(i) = RecursiveShuffle(Nested, Recurse)
        End If
        j = Int(Rnd * (i - Lower) + 1)
        If IsArray(SourceArray(j)) And Recurse Then
            Nested = SourceArray(j)
            SourceArray(j) = RecursiveShuffle(Nested, Recurse)
        End If
        Swap SourceArray, i, j
    Next
    RecursiveShuffle = SourceArray
End Function

'@Description("reverses the order of the passed array.")
Private Function RecursiveReverse( _
        ByRef SourceArray() As Variant, _
        Optional ByVal Recurse As Boolean _
    ) As Variant()
Attribute RecursiveReverse.VB_Description = "reverses the order of the passed array."
    
    Dim LocalLength As Long
    Dim Middle As Long
    Dim Lower As Long
    Dim Upper As Long
    Dim PassThruArray() As Variant
    
    LocalLength = GetArrayLength(SourceArray)
    Lower = LBound(SourceArray)
    Middle = Int(LocalLength / 2) + Lower
    
    Do While Lower <> Middle
        ' TODO: check this works with any lb
        Upper = UBound(SourceArray) + LBound(SourceArray) - Lower
        If IsArray(SourceArray(Lower)) And Recurse Then
            PassThruArray = SourceArray(Lower)
            SourceArray(Lower) = RecursiveReverse(PassThruArray, Recurse)
        End If
        If IsArray(SourceArray(Upper)) And Recurse Then
            PassThruArray = SourceArray(Upper)
            SourceArray(Upper) = RecursiveReverse(PassThruArray, Recurse)
        End If
        Swap SourceArray, Lower, Upper
        Inc Lower
    Loop
    RecursiveReverse = SourceArray
End Function

'@Description("returns the length of the passed array.")
Private Function GetArrayLength(ByRef SourceArray() As Variant) As Long
Attribute GetArrayLength.VB_Description = "returns the length of the passed array."
    Dim result As Long
    result = 0
    If IsArrayAllocated(SourceArray) Then
        If Not IsArrayEmpty(SourceArray) Then
            result = UBound(SourceArray) - LBound(SourceArray) + 1
        End If
    End If
    GetArrayLength = result
End Function

'@Description("converts all the values in a jagged array to a 1d array.")
Private Sub RecursiveFlatten( _
        ByRef SourceArray() As Variant, _
        ByRef Results As BetterArray _
    )
Attribute RecursiveFlatten.VB_Description = "converts all the values in a jagged array to a 1d array."
    Dim element As Variant
    For Each element In SourceArray
        If IsArray(element) Then
            Dim ArrayElement() As Variant
            ArrayElement = element
            RecursiveFlatten ArrayElement, Results
        Else
            Results.Push element
        End If
    Next
End Sub

'@Description("Recursively finds the largest value in an array.")
Private Function RecursiveMax(ByRef SourceArray() As Variant) As Variant
Attribute RecursiveMax.VB_Description = "Recursively finds the largest value in an array."
    Dim i As Long
    Dim result As Variant
    
    If IsMultidimensionalArray(SourceArray) Then
        RaiseError EC_INVALID_MULTIDIMENSIONAL_ARRAY_OPERATION, "Max", "Args"
    Else
        For i = LBound(SourceArray) To UBound(SourceArray)
            If IsArray(SourceArray(i)) Then
                Dim NestedArray() As Variant
                Dim NestedResult As Variant
                NestedArray = SourceArray(i)
                NestedResult = RecursiveMax(NestedArray)
                If IsEmpty(result) Then
                    result = NestedResult
                Else
                    If NestedResult > result Then result = NestedResult
                End If
            Else
                Dim CurrentValue As Variant
                CurrentValue = GetScalarRepresentation(SourceArray(i))
                If CurrentValue <> OBJECT_REPR Then
                    If IsEmpty(result) Then
                        result = CurrentValue
                    Else
                        If CurrentValue > result Then result = CurrentValue
                    End If
                End If
            End If
        Next
    End If
    RecursiveMax = result
End Function

'@Description("Recursively finds the smallest value in an array.")
Private Function RecursiveMin(ByRef SourceArray() As Variant) As Variant
Attribute RecursiveMin.VB_Description = "Recursively finds the smallest value in an array."
    Dim i As Long
    Dim result As Variant
    
    If IsMultidimensionalArray(SourceArray) Then
        RaiseError EC_INVALID_MULTIDIMENSIONAL_ARRAY_OPERATION, "Max", "Args"
    Else
        For i = LBound(SourceArray) To UBound(SourceArray)
            If IsArray(SourceArray(i)) Then
                Dim NestedArray() As Variant
                Dim NestedResult As Variant
                NestedArray = SourceArray(i)
                NestedResult = RecursiveMin(NestedArray)
                If IsEmpty(result) Then
                    result = NestedResult
                Else
                    If NestedResult < result Then result = NestedResult
                End If
            Else
                Dim CurrentValue As Variant
                CurrentValue = GetScalarRepresentation(SourceArray(i))
                If CurrentValue <> OBJECT_REPR Then
                    If IsEmpty(result) Then
                        result = CurrentValue
                    Else
                        If CurrentValue < result Then result = CurrentValue
                    End If
                End If
            End If
        Next
    End If
    RecursiveMin = result
End Function

'@Description("Recursively checks if the passed array includes the search element.")
Private Function RecursiveIncludes( _
        ByVal SearchElement As Variant, _
        ByRef SearchArray() As Variant, _
        Optional ByVal FromIndex As Long, _
        Optional ByVal CompareTypeNames As Boolean, _
        Optional ByVal Recurse As Boolean _
    ) As Boolean
Attribute RecursiveIncludes.VB_Description = "Recursively checks if the passed array includes the search element."
    Dim LocalLowerBound As Long
    Dim LocalUpperBound As Long
    Dim i As Long
    LocalLowerBound = LBound(SearchArray)
    If FromIndex > LocalLowerBound Then LocalLowerBound = FromIndex
    LocalUpperBound = UBound(SearchArray)
    For i = LocalLowerBound To LocalUpperBound
        If CompareTypeNames Then
            If InStr( _
                    UCase$(TypeName(SearchArray(i))), _
                    UCase$(CStr(SearchElement)) _
                ) > 0 _
                Or _
                UCase$(CStr(SearchElement)) = "OBJECT" And _
                IsObject(SearchArray(i)) _
                Then
                RecursiveIncludes = True
                Exit Function
            End If
        End If
        If IsArray(SearchArray(i)) And Recurse Then
            Dim PassThru() As Variant
            PassThru = SearchArray(i)
            If RecursiveIncludes( _
                    SearchElement, _
                    PassThru, _
                    CompareTypeNames:=CompareTypeNames, _
                    Recurse:=Recurse _
                ) Then
                RecursiveIncludes = True
                Exit Function
            End If
        ElseIf Not CompareTypeNames Then
            If ElementsAreEqual(SearchElement, SearchArray(i)) Then
                RecursiveIncludes = True
                Exit Function
            End If
        End If
    Next
    RecursiveIncludes = False
End Function

'@Description("Filters a one dimension array.")
Private Function FilterOneDimension( _
        ByRef SourceArray() As Variant, _
        ByVal Match As Variant, _
        ByVal Include As Boolean, _
        Optional ByVal CompareTypeNames As Boolean _
    ) As Variant()
    Dim result As BetterArray
    Dim LocalLowerBound As Long
    Dim LocalUpperBound As Long
    Dim i As Long
    Dim IsMatch As Boolean
    
    LocalLowerBound = LBound(SourceArray)
    LocalUpperBound = UBound(SourceArray)
    Set result = New BetterArray
    result.LowerBound = This.LowerBound
    For i = LocalLowerBound To LocalUpperBound
        If CompareTypeNames Then
            IsMatch = (InStr( _
                UCase$(TypeName(SourceArray(i))), _
                UCase$(CStr(Match)) _
            ) > 0)
        Else
            IsMatch = ElementsAreEqual(Match, SourceArray(i))
        End If
        If (Include And IsMatch) Or (Not Include And Not IsMatch) Then
            result.Push SourceArray(i)
        End If
    Next
    FilterOneDimension = result.Items
End Function

'@Description("Filters a jaggged array by column.")
Private Function FilterByColumn( _
        ByRef SourceArray() As Variant, _
        ByVal Match As Variant, _
        ByVal Include As Boolean, _
        ByVal ColumnIndex As Long, _
        Optional ByVal CompareTypeNames As Boolean _
    ) As Variant()
    Dim result As BetterArray
    Dim LocalLowerBound As Long
    Dim LocalUpperBound As Long
    Dim i As Long
    Dim IsMatch As Boolean
    Dim ComparisonElement As Variant
    
    LocalLowerBound = LBound(SourceArray)
    LocalUpperBound = UBound(SourceArray)
    Set result = New BetterArray
    result.LowerBound = This.LowerBound

    For i = LocalLowerBound To LocalUpperBound
        LetOrSetElement ComparisonElement, SourceArray(i)(ColumnIndex)
        If CompareTypeNames Then
            IsMatch = (InStr( _
                UCase$(TypeName(ComparisonElement)), _
                UCase$(CStr(Match)) _
            ) > 0)
        Else
            IsMatch = ElementsAreEqual(Match, ComparisonElement)
        End If
        If (Include And IsMatch) Or (Not Include And Not IsMatch) Then
            result.Push SourceArray(i)
        End If
    Next
    FilterByColumn = result.Items
End Function

'@Description("Recursively filters a passed array.")
Private Function RecursiveFilter( _
        ByRef SourceArray() As Variant, _
        ByVal Match As Variant, _
        ByVal Include As Boolean, _
        ByVal Recurse As Boolean, _
        Optional ByVal CompareTypeNames As Boolean _
    ) As Variant()
Attribute RecursiveFilter.VB_Description = "Recursively filters a passed array."
    Dim result As BetterArray
    Dim LocalLowerBound As Long
    Dim LocalUpperBound As Long
    Dim i As Long
    Dim IsMatch As Boolean
    
    LocalLowerBound = LBound(SourceArray)
    LocalUpperBound = UBound(SourceArray)
    Set result = New BetterArray
    result.LowerBound = This.LowerBound
    For i = LocalLowerBound To LocalUpperBound
        If IsArray(SourceArray(i)) And Recurse Then
            If IsArrayAllocated(SourceArray(i)) Then
                Dim LocalItems() As Variant
                LocalItems = SourceArray(i)
                LocalItems = RecursiveFilter( _
                    LocalItems, _
                    Match, _
                    Include, _
                    Recurse, _
                    CompareTypeNames _
                )
                ' don't push a returned empty array
                If Not RecursiveEvery(Empty, LocalItems) Then
                    result.Push LocalItems
                End If
            Else
                ' push an empty array if current is an unalocated rray
                If CompareTypeNames Then
                    IsMatch = (InStr( _
                        UCase$(TypeName(SourceArray(i))), _
                        UCase$(CStr(Match)) _
                    ) > 0)
                    ' push an empty array if only asked to exclude specific types or type
                    ' matches the requested type (even though it's empty...)
                    If (Include And IsMatch) Or (Not Include And Not IsMatch) Then
                        result.Push GetEmptyArray
                    End If
                Else
                    If Not Include Then
                        ' push an empty array if only asked to exclude specific values
                        result.Push GetEmptyArray
                    End If
                End If
            End If
        Else
            If CompareTypeNames Then
                IsMatch = (InStr( _
                    UCase$(TypeName(SourceArray(i))), _
                    UCase$(CStr(Match)) _
                ) > 0)
            Else
                IsMatch = ElementsAreEqual(Match, SourceArray(i))
            End If
            If (Include And IsMatch) Or (Not Include And Not IsMatch) Then
                result.Push SourceArray(i)
            End If
        End If
    Next
    RecursiveFilter = result.Items
End Function

'@Description("Compares two values for equality. Doesn't support multidimensional arrays.")
'@Ignore ShadowedDeclaration
Private Function ElementsAreEqual( _
        ByVal Expected As Variant, _
        ByVal Actual As Variant _
    ) As Boolean
Attribute ElementsAreEqual.VB_Description = "Compares two values for equality. Doesn't support multidimensional arrays."
    ' Using 13dp of precision for EPSILON rather than IEEE 754 standard of 2^-52
    ' some roundings in type conversions cause greater diffs than machine epsilon
    Const Epsilon As Double = 0.0000000000001
    Dim result As Boolean
    Dim i As Long
    
    On Error GoTo ErrHandler
    If IsArray(Expected) Or IsArray(Actual) Then
        If IsArray(Expected) And IsArray(Actual) Then
            If LBound(Expected) = LBound(Actual) And _
                    UBound(Expected) = UBound(Actual) Then
                Dim CurrentlyEqual As Boolean
                CurrentlyEqual = True
                For i = LBound(Expected) To UBound(Actual)
                    If Not ElementsAreEqual(Expected(i), Actual(i)) Then
                        CurrentlyEqual = False
                        Exit For
                    End If
                Next
                result = CurrentlyEqual
            End If
        End If
    ElseIf IsEmpty(Expected) Or IsEmpty(Actual) Then
        If IsEmpty(Expected) And IsEmpty(Actual) Then result = True
    ElseIf IsObject(Expected) Or IsObject(Actual) Then
        If IsObject(Expected) And IsObject(Actual) Then
            If Expected Is Actual Then result = True
        End If
    ElseIf IsNumeric(Expected) Or IsNumeric(Actual) Then
        If IsNumeric(Expected) And IsNumeric(Actual) Then
            Dim Diff As Double
            Diff = Abs(Expected - Actual)
            If Diff <= (IIf( _
                    Abs(Expected) < Abs(Actual), _
                    Abs(Actual), _
                    Abs(Expected) _
                ) * Epsilon) Then
                result = True
            End If
        End If
    ElseIf Expected = Actual Then
        result = True
    End If
    ElementsAreEqual = result
    Exit Function
ErrHandler:
    ElementsAreEqual = False
End Function

' TODO: Refactor to remove recursion
'@Description("Recursively parses nested arrays from a string.")
Private Function ParseDelimitedArrayString( _
        ByVal SourceString As String, _
        ByVal ValueSeparator As String, _
        ByVal Opener As String, _
        ByVal Closer As String, _
        Optional ByRef Cursor As Long = 2 _
    ) As Variant()
Attribute ParseDelimitedArrayString.VB_Description = "Recursively parses nested arrays from a string."
    Dim CurrentChar As String
    Dim LocalResult() As Variant
    Dim i As Long
    Dim BreakLoop As Boolean
    Dim NextOpener As Long
    Dim NextCloser As Long
    
    CurrentChar = Mid$(SourceString, Cursor, 1)
    NextOpener = InStr(Cursor, SourceString, Opener)
    NextCloser = InStr(Cursor, SourceString, Closer)
    
    If CurrentChar <> Opener And (NextCloser < NextOpener Or NextOpener = 0) Then
        ' we're inside an array to be parsed
        ParseDelimitedArrayString = ParseArraySegmentFromString(SourceString, Cursor, NextCloser, ValueSeparator)
        Exit Function
    End If
        
    ' traverse nested arrays
    i = This.LowerBound
    Do
        If CurrentChar = Opener Then
            If i > This.LowerBound Then
                ReDim Preserve LocalResult(i)
            Else
                LocalResult = GetEmptyArray
            End If
            Inc Cursor
            LocalResult(i) = ParseDelimitedArrayString( _
                SourceString, _
                ValueSeparator, _
                Opener, _
                Closer, _
                Cursor _
            )
            Inc i
        End If
        CurrentChar = Mid$(SourceString, Cursor, 1)
        Do Until CurrentChar = Opener
            Inc Cursor
            CurrentChar = Mid$(SourceString, Cursor, 1)
            If CurrentChar = Closer Or Cursor >= Len(SourceString) Then
                BreakLoop = True
                Exit Do
            End If
        Loop
    Loop Until BreakLoop
    
    ParseDelimitedArrayString = LocalResult
End Function

'@Description("Returns an array from a delimited string")
Private Function ParseArraySegmentFromString( _
        ByVal SourceString As String, _
        ByRef Cursor As Long, _
        ByVal NextCloser As Long, _
        ByVal ValueSeparator As String _
    ) As Variant()
Attribute ParseArraySegmentFromString.VB_Description = "Returns an array from a delimited string"
    Dim SegmentLength As Long
    Dim Segment() As String
    SegmentLength = IIf(NextCloser = 0, Len(SourceString), NextCloser - Cursor)
    Segment = Split(Mid$(SourceString, Cursor, SegmentLength), ValueSeparator)
    Cursor = NextCloser
    ParseArraySegmentFromString = DuckTypeStringArray(Segment)
End Function

'@Description("Trims enclosing quote chars from string if present")
Private Function UnquoteString(ByRef element As String) As String
Attribute UnquoteString.VB_Description = "Trims enclosing quote chars from string if present"
    Dim LocalElement As String
    LocalElement = Trim$(element)
    If LocalElement = vbNullString Then
        UnquoteString = vbNullString
    Else
        If Asc(left$(LocalElement, 1)) = 34 And Asc(right$(LocalElement, 1)) = 34 Then
            'trim string delimiters
            LocalElement = Mid$(LocalElement, 2, Len(LocalElement) - 2)
        End If
        UnquoteString = Trim$(LocalElement)
    End If
End Function

'@Description("Takes a string. Returns a Variant with the element converted to an appropriate type")
Private Function DuckTypeElement(ByRef element As String) As Variant
Attribute DuckTypeElement.VB_Description = "Takes a string. Returns a Variant with the element converted to an appropriate type"
    Dim result As Variant
    Dim LocalElement As String
    LocalElement = element
    If UCase$(LocalElement) = "TRUE" Or UCase$(element) = "FALSE" Then
        result = CBool(LocalElement)
    ElseIf IsNumeric(LocalElement) Then
        Const Epsilon As Double = 2 ^ -52
        Dim Diff As Double
        ' check if integer
        Diff = Abs(Fix(LocalElement) - LocalElement)
        If Diff > Epsilon Then
            result = CDbl(LocalElement)
        Else
            result = CLng(LocalElement)
        End If
    Else
        result = UnquoteString(LocalElement)
    End If
    DuckTypeElement = result
End Function

'@Description("Takes a string array. Returns a Variant array with the elements converted to an appropriate type")
Private Function DuckTypeStringArray(ByRef SourceArray() As String) As Variant()
Attribute DuckTypeStringArray.VB_Description = "Takes a string array. Returns a Variant array with the elements converted to an appropriate type"
    Dim i As Long
    Dim LocalLowerBound As Long
    Dim LocalUpperBound As Long
    Dim result() As Variant
    
    LocalLowerBound = LBound(SourceArray)
    LocalUpperBound = UBound(SourceArray)
    ReDim result(LocalLowerBound To LocalUpperBound)
    For i = LocalLowerBound To LocalUpperBound
        result(i) = DuckTypeElement(SourceArray(i))
    Next
    DuckTypeStringArray = result
End Function

'@Description("Populates the ErrorDefinitions array.")
Private Sub PopulateErrorDefinitions()
Attribute PopulateErrorDefinitions.VB_Description = "Populates the ErrorDefinitions array."
    Dim source As String
    source = TypeName(Me)
    This.ErrorDefinitions(ErrorCodes.EC_EXPECTED_RANGE_OBJECT) = ErrorDefinitionFactory( _
        Number:=ErrorCodes.EC_EXPECTED_RANGE_OBJECT, _
        source:=source, _
        Description:="Range Object Expected" _
    )
    This.ErrorDefinitions(ErrorCodes.EC_MAX_DIMENSIONS_LIMIT) = ErrorDefinitionFactory( _
        Number:=ErrorCodes.EC_MAX_DIMENSIONS_LIMIT, _
        source:=source, _
        Description:="Cannot convert structure of arrays with more than 20 dimensions." _
    )
    This.ErrorDefinitions(ErrorCodes.EC_EXPECTED_COLLECTION_OBJECT) = ErrorDefinitionFactory( _
        Number:=ErrorCodes.EC_EXPECTED_COLLECTION_OBJECT, _
        source:=source, _
        Description:="Valid Collection Object Expected" _
    )
    This.ErrorDefinitions(ErrorCodes.EC_EXCEEDS_MAX_SORT_DEPTH) = ErrorDefinitionFactory( _
        Number:=ErrorCodes.EC_EXCEEDS_MAX_SORT_DEPTH, _
        source:=source, _
        Description:="Cannot sort on arrays with more than 2 dimensions" _
    )
    This.ErrorDefinitions(ErrorCodes.EC_EXPECTED_JAGGED_ARRAY) = ErrorDefinitionFactory( _
        Number:=ErrorCodes.EC_EXPECTED_JAGGED_ARRAY, _
        source:=source, _
        Description:="Expected jagged array." _
    )
    This.ErrorDefinitions(ErrorCodes.EC_EXPECTED_MULTIDIMENSION_ARRAY) = ErrorDefinitionFactory( _
        Number:=ErrorCodes.EC_EXPECTED_MULTIDIMENSION_ARRAY, _
        source:=source, _
        Description:="Expected multidimension array." _
    )
    This.ErrorDefinitions(ErrorCodes.EC_EXPECTED_ARRAY) = ErrorDefinitionFactory( _
        Number:=ErrorCodes.EC_EXPECTED_ARRAY, _
        source:=source, _
        Description:="Expected array." _
    )
    This.ErrorDefinitions(ErrorCodes.EC_NULL_STRING) = ErrorDefinitionFactory( _
        Number:=ErrorCodes.EC_NULL_STRING, _
        source:=source, _
        Description:="Cannot parse from a null string. Expected string with length greater than 0." _
    )
    This.ErrorDefinitions(ErrorCodes.EC_UNALLOCATED_ARRAY) = ErrorDefinitionFactory( _
        Number:=ErrorCodes.EC_UNALLOCATED_ARRAY, _
        source:=source, _
        Description:="Cannot operate on unallocated array." _
    )
    This.ErrorDefinitions(ErrorCodes.EC_UNDEFINED_ARRAY) = ErrorDefinitionFactory( _
        Number:=ErrorCodes.EC_UNDEFINED_ARRAY, _
        source:=source, _
        Description:="Array is undefined." _
    )
    This.ErrorDefinitions(ErrorCodes.EC_INVALID_MULTIDIMENSIONAL_ARRAY_OPERATION) = ErrorDefinitionFactory( _
        Number:=ErrorCodes.EC_INVALID_MULTIDIMENSIONAL_ARRAY_OPERATION, _
        source:=source, _
        Description:="Unable to perform the requested operation on a multidimensional array." _
    )
    This.ErrorDefinitions(ErrorCodes.EC_EXPECTED_VARIANT_ARRAY) = ErrorDefinitionFactory( _
        Number:=ErrorCodes.EC_EXPECTED_VARIANT_ARRAY, _
        source:=source, _
        Description:="Unable to perform the requested operation on a typed array." _
    )
    This.ErrorDefinitions(ErrorCodes.EC_EXCEEDS_MAX_ARRAY_LENGTH) = ErrorDefinitionFactory( _
        Number:=ErrorCodes.EC_EXCEEDS_MAX_ARRAY_LENGTH, _
        source:=source, _
        Description:="The requested operation would result in an array which exceeds the maximum possible length." _
    )
    This.ErrorDefinitions(ErrorCodes.EC_STRING_TYPE_EXPECTED) = ErrorDefinitionFactory( _
        Number:=ErrorCodes.EC_STRING_TYPE_EXPECTED, _
        source:=source, _
        Description:="Expected a String or String-coercible type." _
    )
    This.ErrorDefinitions(ErrorCodes.EC_CANNOT_CONVERT_TO_REQUESTED_STRUCTURE) = ErrorDefinitionFactory( _
        Number:=ErrorCodes.EC_CANNOT_CONVERT_TO_REQUESTED_STRUCTURE, _
        source:=source, _
        Description:="The stored array cannot be converted to the requested structure." _
    )
    This.ErrorDefinitions(ErrorCodes.EC_CANNOT_SORT_OBJECTS) = ErrorDefinitionFactory( _
        Number:=ErrorCodes.EC_CANNOT_SORT_OBJECTS, _
        source:=source, _
        Description:="The array contains Objects which cannot be sorted." _
    )
    
End Sub

'@Description("Returns an ErrorDefinition Type populated with the provided arguments.")
Private Function ErrorDefinitionFactory( _
        ByVal Number As Long, _
        ByVal source As String, _
        ByVal Description As String _
    ) As ErrorDefinition
Attribute ErrorDefinitionFactory.VB_Description = "Returns an ErrorDefinition Type populated with the provided arguments."
    Dim result As ErrorDefinition
    result.Number = Number
    result.source = source
    result.Description = Description
    ErrorDefinitionFactory = result
End Function

'@Description("Raises an application error based on the passed ErrorCode and the definitions defined in ErrorDefinitions.")
Private Sub RaiseError( _
        ByVal ErrorCode As ErrorCodes, _
        ByVal Caller As String, _
        Optional ByVal ArgName As String _
    )
Attribute RaiseError.VB_Description = "Raises an application error based on the passed ErrorCode and the definitions defined in ErrorDefinitions."
    Dim CurrentError As ErrorDefinition
    Dim LocalArgName As String
    If ArgName <> vbNullString Then LocalArgName = "Argument " & ArgName & ": "
    CurrentError = This.ErrorDefinitions(ErrorCode)
    err.Raise CurrentError.Number, _
              CurrentError.source & "." & Caller, _
              LocalArgName & CurrentError.Description
End Sub

'Used by ToExcelRange
'@Description("Ensures each element of passed array can be represented as a scalar value.")
Private Function EnsureScalar1DArray(ByRef SourceArray() As Variant) As Variant()
Attribute EnsureScalar1DArray.VB_Description = "Ensures each element of passed array can be represented as a scalar value."
    Dim i As Long
    Dim LocalLowerBound As Long
    Dim LocalUpperBound As Long
    Dim result() As Variant
    
    LocalLowerBound = LBound(SourceArray)
    LocalUpperBound = UBound(SourceArray)
    ReDim result(LocalLowerBound To LocalUpperBound)
    For i = LocalLowerBound To LocalUpperBound
        result(i) = GetScalarRepresentation(SourceArray(i))
    Next
    EnsureScalar1DArray = result
End Function

'@Description("Converts a 1d array to a 1 column wide jagged array.")
Private Function ConvertOneDimensionArrayToJagged(ByRef SourceArray() As Variant) As Variant()
Attribute ConvertOneDimensionArrayToJagged.VB_Description = "Converts a 1d array to a 1 column wide jagged array."
    Dim i As Long
    Dim LocalUpperBound As Long
    Dim LocalLowerBound As Long
    Dim result() As Variant
    LocalUpperBound = UBound(SourceArray)
    LocalLowerBound = LBound(SourceArray)
    ReDim result(LocalLowerBound To LocalUpperBound)
    For i = LocalLowerBound To LocalUpperBound
        result(i) = Array(SourceArray(i))
    Next
    ConvertOneDimensionArrayToJagged = result
End Function

'@Description("Converts a 1d array to a 1 column wide 2d array.")
Private Function Transpose1DArray(ByRef SourceArray() As Variant) As Variant()
Attribute Transpose1DArray.VB_Description = "Converts a 1d array to a 1 column wide 2d array."
    Dim i As Long
    Dim j As Long
    Dim LocalUpperBound As Long
    Dim LocalLowerBound As Long
    Dim result() As Variant
    LocalUpperBound = UBound(SourceArray)
    LocalLowerBound = LBound(SourceArray)
    ReDim result(LocalLowerBound To LocalUpperBound, _
                 LocalLowerBound To LocalLowerBound)
    j = LocalLowerBound
    For i = LocalLowerBound To LocalUpperBound
        result(j, LocalLowerBound) = SourceArray(i)
        Inc j
    Next
    Transpose1DArray = result
End Function

'@Description("Transposes the values in a 2d array. Rows become columns, columns become rows.")
Private Function Transpose2DArray(ByRef SourceArray() As Variant) As Variant()
Attribute Transpose2DArray.VB_Description = "Transposes the values in a 2d array. Rows become columns, columns become rows."
    Dim CurrentRow As Long
    Dim LowerBoundRow As Long
    Dim UpperBoundRow As Long
    Dim CurrentColumn As Long
    Dim LowerBoundCol As Long
    Dim UpperBoundCol As Long
    Dim result() As Variant
    
    LowerBoundCol = LBound(SourceArray, 1)
    UpperBoundCol = UBound(SourceArray, 1)
    LowerBoundRow = LBound(SourceArray, 2)
    UpperBoundRow = UBound(SourceArray, 2)
    ReDim result(LowerBoundRow To UpperBoundRow, LowerBoundCol To UpperBoundCol)
    For CurrentRow = LowerBoundRow To UpperBoundRow
        For CurrentColumn = LowerBoundCol To UpperBoundCol
            result(CurrentRow, CurrentColumn) = SourceArray(CurrentColumn, CurrentRow)
        Next
    Next
    Transpose2DArray = result
End Function

'@Description("Transposes the values in a jagged array with a depth of 2. Rows become columns, columns become rows.")
Private Function TransposeArrayOfArrays(ByRef SourceArray() As Variant) As Variant()
Attribute TransposeArrayOfArrays.VB_Description = "Transposes the values in a jagged array with a depth of 2. Rows become columns, columns become rows."
    Dim CurrentRow As Long
    Dim LowerBoundRow As Long
    Dim UpperBoundRow As Long
    Dim CurrentColumn As Long
    Dim LowerBoundCol As Long
    Dim UpperBoundCol As Long
    Dim result() As Variant
    Dim NestedBounds() As Long
    Dim Nested() As Variant
    
    NestedBounds = GetMaxBoundsAtDimension(SourceArray, 2)
    LowerBoundCol = LBound(SourceArray)
    UpperBoundCol = UBound(SourceArray)
    LowerBoundRow = NestedBounds(0)
    UpperBoundRow = NestedBounds(1)
    'check if array can fit into 1 dimension
    If LowerBoundRow = UpperBoundRow Then
        ReDim result(LowerBoundCol To UpperBoundCol)
        CurrentRow = LowerBoundRow
        For CurrentColumn = LowerBoundCol To UpperBoundCol
            result(CurrentColumn) = SourceArray(CurrentColumn)(CurrentRow)
        Next
    ElseIf LowerBoundCol = UpperBoundCol Then
        ReDim result(LowerBoundRow To UpperBoundRow)
        CurrentColumn = LowerBoundCol
        For CurrentRow = UpperBoundRow To UpperBoundRow
            result(CurrentRow) = SourceArray(CurrentColumn)(CurrentRow)
        Next
    Else
        ReDim result(LowerBoundRow To UpperBoundRow)
        For CurrentRow = LowerBoundRow To UpperBoundRow
            ReDim Nested(LowerBoundCol To UpperBoundCol)
            For CurrentColumn = LowerBoundCol To UpperBoundCol
                Nested(CurrentColumn) = SourceArray(CurrentColumn)(CurrentRow)
            Next
            result(CurrentRow) = Nested
        Next
    End If
    TransposeArrayOfArrays = result
End Function

'@Description("Returns an empty 1d array with 1 slot.")
Private Function GetEmptyArray() As Variant()
Attribute GetEmptyArray.VB_Description = "Returns an empty 1d array with 1 slot."
    Dim result() As Variant
    ReDim result(This.LowerBound To This.LowerBound)
    GetEmptyArray = result
End Function

'@Description("Used to apply the correct specified sort algorithm.")
Private Sub ApplySortMethod( _
        ByRef SourceArray() As Variant, _
        ByVal LocalArrayType As ArrayTypes, _
        Optional ByVal Col As Long _
    )
Attribute ApplySortMethod.VB_Description = "Used to apply the correct specified sort algorithm."
    Select Case This.SortMethod
        Case SortMethods.SM_TIMSORT
            TimSort SourceArray, LocalArrayType, Col
        Case SortMethods.SM_QUICKSORT_RECURSIVE
            QuickSortRecursive _
                SourceArray, _
                LBound(SourceArray), _
                UBound(SourceArray), _
                LocalArrayType, _
                Col
        Case SortMethods.SM_QUICKSORT_ITERATIVE
            QuickSortIterative _
                SourceArray, _
                LBound(SourceArray), _
                UBound(SourceArray), _
                LocalArrayType, _
                Col
    End Select
End Sub

'@Description("Returns an field of a one dimension or two dimension jagged array")
Private Function GetComparisonItem( _
    ByRef source() As Variant, _
    ByVal index As Long, _
    ByVal Col As Long, _
    ByVal LocalArrayType As ArrayTypes _
) As Variant
Attribute GetComparisonItem.VB_Description = "Returns an field of a one dimension or two dimension jagged array"
    If IsObject(source(index)) Then
        GetComparisonItem = ObjPtr(source(index))
    Else
        If LocalArrayType = BA_JAGGED Then
            GetComparisonItem = source(index)(Col)
        Else
            GetComparisonItem = source(index)
        End If
    End If
End Function

'@Description("Sorts the passed array in place using InsertionSort.")
Private Sub InsertionSort( _
    ByRef source() As Variant, _
    ByVal LeftIndex As Variant, _
    ByVal RightIndex As Variant, _
    ByVal LocalArrayType As ArrayTypes, _
    Optional ByVal Col As Long _
)
Attribute InsertionSort.VB_Description = "Sorts the passed array in place using InsertionSort."
    Dim i As Long
    Dim j As Long
    Dim Pivot As Variant
    Dim PivotCompVal As Variant
    Dim Current As Variant
    Dim CurrentCompval As Variant
        
    ' Loop from the element indicated by
    ' `left` until the element indicated by `right`
            
    For i = LeftIndex + 1 To RightIndex
        ' This is the element we want to position in its
        ' correct place
        LetOrSetElement Pivot, source(i)
        PivotCompVal = GetComparisonItem(source, i, Col, LocalArrayType)
        ' Initialize the variable that will be used to
        ' find the correct position of the element referenced
        ' by `key_item`
        j = i - 1
        ' Run through the list of items (the left
        ' portion of the array) and find the correct position
        ' of the element referenced by `key_item`. Do this only
        ' if the `key_item` is smaller than its adjacent values.
        Do While j >= LeftIndex
            LetOrSetElement Current, source(j)
            CurrentCompval = GetComparisonItem(source, j, Col, LocalArrayType)
            If CurrentCompval > PivotCompVal Then
                ' Shift the value one position to the left
                ' and reposition `j` to point to the next element
                ' (from right to left)
                LetOrSetElement source(j + 1), Current
                dec j
            Else
                Exit Do
            End If
        Loop
    
        ' When you finish shifting the elements, position
        ' the `key_item` in its correct location
        '@Ignore UnassignedVariableUsage
        LetOrSetElement source(j + 1), Pivot
    Next
End Sub

'@Description("Sorts the passed array in place using MergeSort.")
Private Sub MergeSort( _
    ByRef source() As Variant, _
    ByVal StartIndex As Long, _
    ByVal MidIndex As Long, _
    ByVal EndIndex As Long, _
    ByVal LocalArrayType As ArrayTypes, _
    Optional ByVal Col As Long _
)
Attribute MergeSort.VB_Description = "Sorts the passed array in place using MergeSort."
    ' Original array is broken in two parts
    ' left and right array
    Dim LowLength As Long
    Dim HighLength As Long
    Dim i As Long
    Dim LowIndex As Long
    Dim HighIndex As Long
    Dim LowPartition() As Variant
    Dim HighPartition() As Variant
    '@Ignore VariableNotAssigned
    Dim LowItem As Variant
    '@Ignore VariableNotAssigned
    Dim HighItem As Variant
    
    LowLength = MidIndex - StartIndex + 1
    HighLength = EndIndex - MidIndex
        
    ReDim LowPartition(0 To max(LowLength - 1, 0))
    ReDim HighPartition(0 To max(HighLength - 1, 0))
    
    i = 0
    Do While i < LowLength
        LetOrSetElement LowPartition(i), source(StartIndex + i)
        Inc i
    Loop
    
    i = 0
    Do While i < HighLength
        LetOrSetElement HighPartition(i), source(MidIndex + 1 + i)
        Inc i
    Loop
    
    ' After comparing, we
    ' merge those two array
    ' in larger sub array
    i = StartIndex
    Do While LowIndex < LowLength And HighIndex < HighLength
        LowItem = GetComparisonItem(LowPartition, LowIndex, Col, LocalArrayType)
        HighItem = GetComparisonItem(HighPartition, HighIndex, Col, LocalArrayType)
        If LowItem <= HighItem Then
            LetOrSetElement source(i), LowPartition(LowIndex)
            Inc LowIndex
        Else
            LetOrSetElement source(i), HighPartition(HighIndex)
            Inc HighIndex
        End If
        Inc i
    Loop
    
    ' Copy remaining elements of left, if any
    Do While LowIndex < LowLength
        LetOrSetElement source(i), LowPartition(LowIndex)
        Inc LowIndex
        Inc i
    Loop
    Do While HighIndex < HighLength
        LetOrSetElement source(i), HighPartition(HighIndex)
        Inc HighIndex
        Inc i
    Loop
    
End Sub

'@Description("Iterative Timsort")
Private Sub TimSort( _
    ByRef source() As Variant, _
    ByVal LocalArrayType As ArrayTypes, _
    Optional ByVal Col As Long _
)
Attribute TimSort.VB_Description = "Iterative Timsort"
    Const MIN_RUN As Long = 32
    Dim i As Long
    Dim SourceLength As Long
    SourceLength = GetArrayLength(source)
    ' Sort individual subarrays of size RUN
    For i = LBound(source) To UBound(source) Step MIN_RUN
        InsertionSort source, i, min((i + MIN_RUN - 1), UBound(source)), LocalArrayType, Col
    Next
    
    ' Now you can start merging the sorted slices.
    ' Start from `min_run`, doubling the size on
    ' each iteration until you surpass the length of
    ' the array.
    Dim size As Long
    Dim Start As Long
    Dim Midpoint As Long
    Dim Endpoint As Long
    Dim LastIndex As Long
    
    LastIndex = UBound(source)
    size = MIN_RUN
    Do While size < SourceLength
        ' Determine the arrays that will
        ' be merged together
        Start = LBound(source)
        Do While Start < UBound(source)
            ' Compute the `midpoint` (where the first array ends
            ' and the second starts) and the `endpoint` (where
            ' the second array ends)
            Midpoint = min(Start + size - 1, LastIndex)
            Endpoint = min(Start + size * 2 - 1, LastIndex)
            ' Merge the two subarrays.
            ' The `left` array should go from `start` to
            ' `midpoint + 1`, while the `right` array should
            ' go from `midpoint + 1` to `end + 1`.
            MergeSort source, Start, Midpoint, Endpoint, LocalArrayType, Col
            Inc Start, size * 2
        Loop
        ' Each iteration should double the size of your arrays
        Inc size, size
    Loop

End Sub

'@Description("Sorts in place a passed array using a Recursive implementation of the QuickSort algorithm.")
Private Sub QuickSortRecursive( _
        ByRef SourceArray() As Variant, _
        ByVal Low As Long, _
        ByVal High As Long, _
        ByVal LocalArrayType As ArrayTypes, _
        Optional ByVal Col As Long _
    )
Attribute QuickSortRecursive.VB_Description = "Sorts in place a passed array using a Recursive implementation of the QuickSort algorithm."
    Dim PartitionIndex As Long
    If Low < High Then
        PartitionIndex = QsPartition(SourceArray, Low, High, LocalArrayType, Col)
        QuickSortRecursive SourceArray, Low, PartitionIndex - 1, LocalArrayType, Col
        QuickSortRecursive SourceArray, PartitionIndex + 1, High, LocalArrayType, Col
    End If
End Sub

'@Description("Sorts in place a passed array using an Iterative implementation of the QuickSort algorithm")
Private Sub QuickSortIterative( _
        ByRef SourceArray() As Variant, _
        ByVal Low As Long, _
        ByVal High As Long, _
        ByVal LocalArrayType As ArrayTypes, _
        Optional ByVal Col As Long _
    )
Attribute QuickSortIterative.VB_Description = "Sorts in place a passed array using an Iterative implementation of the QuickSort algorithm"
    Dim PartitionIndex As Long
    Dim Stack() As Long
    Dim top As Long
    Dim LocalLow As Long
    Dim LocalHigh As Long
    
    LocalLow = Low
    LocalHigh = High
    
    ' Create an auxiliary stack
    ReDim Stack(0 To LocalHigh - LocalLow + 1)
    
    ' initialize top of stack
    top = -1
    ' push initial values of l and h to stack
    Stack(Inc(top)) = LocalLow
    Stack(Inc(top)) = LocalHigh
    
    ' Keep popping from stack while is not empty
    Do While top >= 0
        ' Pop high and low
        LocalHigh = Stack(top)
        LocalLow = Stack(dec(top))
        dec top
        ' Set pivot element at its correct position
        ' in sorted array
        PartitionIndex = QsPartition(SourceArray, LocalLow, LocalHigh, LocalArrayType, Col)
        
        ' If there are elements on left side of pivot,
        ' then push left side to stack
        If PartitionIndex - LocalLow > 1 Then
            Stack(Inc(top)) = LocalLow
            Stack(Inc(top)) = PartitionIndex - 1
        End If
       
        ' If there are elements on right side of pivot,
        ' then push right side to stack
        If PartitionIndex + 1 < LocalHigh Then
            Stack(Inc(top)) = PartitionIndex + 1
            Stack(Inc(top)) = LocalHigh
        End If
        
    Loop
    
End Sub


'@Description("Child function of quickSort. Returns the next partition index.")
Private Function QsPartition( _
        ByRef SourceArray() As Variant, _
        ByVal Low As Long, _
        ByVal High As Long, _
        ByVal LocalArrayType As ArrayTypes, _
        Optional ByVal Col As Long _
    ) As Long
Attribute QsPartition.VB_Description = "Child function of quickSort. Returns the next partition index."
    Dim i As Long
    Dim j As Long
    Dim Pivot As Variant
    Dim Current As Variant
    
    Pivot = GetComparisonItem(SourceArray, High, Col, LocalArrayType)
    
    i = Low - 1
    For j = Low To High - 1
        Current = GetComparisonItem(SourceArray, j, Col, LocalArrayType)
        If Current <= Pivot Then
            Inc i
            Swap SourceArray, i, j
        End If
    Next
    Swap SourceArray, i + 1, High
    QsPartition = i + 1
End Function

'@Description("Swaps the location of two elements in an array.")
Private Sub Swap(ByRef SourceArray() As Variant, ByVal i As Long, ByVal j As Long)
Attribute Swap.VB_Description = "Swaps the location of two elements in an array."
    Dim element As Variant
    LetOrSetElement element, SourceArray(i)
    LetOrSetElement SourceArray(i), SourceArray(j)
    '@Ignore UnassignedVariableUsage
    LetOrSetElement SourceArray(j), element
End Sub

'@Description("Sets or lets the value of a variable by reference depending on the type of the element to be assigned")
Private Sub LetOrSetElement(ByRef Destination As Variant, ByRef source As Variant)
Attribute LetOrSetElement.VB_Description = "Sets or lets the value of a variable by reference depending on the type of the element to be assigned"
    If IsObject(source) Then
        Set Destination = source
    Else
        Destination = source
    End If
End Sub

'@Description("Efficiently concatenates string fragments to a byte array buffer")
Private Function StringBuilder( _
    Optional ByVal Fragment As String = vbNullString, _
    Optional ByVal Final As Boolean, _
    Optional ByVal NewString As Boolean _
) As String
Attribute StringBuilder.VB_Description = "Efficiently concatenates string fragments to a byte array buffer"
    Static Buffer() As Byte
    Static BufferLength As Long
    Static BufferCapacity As Long
    Static Cursor As Long
    Static FirstIndex As Long
    
    Dim FragLength As Long
    Dim LastIndex As Long
    Dim i As Long

    FragLength = LenB(Fragment)
    If Cursor < 1 Or NewString Then
        Buffer = Fragment
        BufferLength = FragLength
        BufferCapacity = FragLength
        FirstIndex = LBound(Buffer)
        Cursor = UBound(Buffer)
    ElseIf FragLength > 0 Then
        Inc BufferLength, FragLength
        LastIndex = FirstIndex + BufferLength - 1
        If BufferLength > BufferCapacity Then
            Do
                BufferCapacity = BufferCapacity * 2
            Loop While BufferLength > BufferCapacity
            ReDim Preserve Buffer(FirstIndex To FirstIndex + BufferCapacity)
        End If
        For i = Cursor + 1 To LastIndex
            Buffer(i) = AscB(MidB$(Fragment, i - Cursor, 1))
        Next
        Cursor = LastIndex
    End If
    
    If Final Then
        ReDim Preserve Buffer(FirstIndex To Cursor)
        StringBuilder = CStr(Buffer)
        Erase Buffer
        Cursor = Empty
    End If
    
End Function

'@Description("Recursively parses an array to a string representation.")
Private Sub RecursiveToString( _
        ByRef SourceArray() As Variant, _
        ByVal PrettyPrint As Boolean, _
        ByVal separator As String, _
        ByVal OpeningDelimiter As String, _
        ByVal ClosingDelimiter As String, _
        ByVal QuoteStrings As Boolean, _
        Optional ByVal Tabs As Long = 1 _
    )
Attribute RecursiveToString.VB_Description = "Recursively parses an array to a string representation."
    Const TabWidth As Long = 2
    Dim i As Long
    Dim Sep As String
    
    StringBuilder OpeningDelimiter
    For i = LBound(SourceArray) To UBound(SourceArray)
        Sep = IIf(i = UBound(SourceArray), ClosingDelimiter, separator)
        If IsArray(SourceArray(i)) Then
            Dim Nested() As Variant
            Nested = SourceArray(i)
            If PrettyPrint Then
                StringBuilder vbCrLf & space(TabWidth * Tabs)
            End If
            RecursiveToString Nested, PrettyPrint, separator, OpeningDelimiter, ClosingDelimiter, QuoteStrings, Tabs + 1
            If i = UBound(SourceArray) And PrettyPrint Then
                StringBuilder vbCrLf
                StringBuilder space(TabWidth * (Tabs - 1))
            End If
            StringBuilder Sep
        Else
            ' ensure no arrays passed to GetScalar as it clears string builder
            StringBuilder Replace( _
                    CStr(GetScalarRepresentation(SourceArray(i), QuoteStrings)), _
                    separator, _
                    vbNullString _
                ) & Sep
        End If
    Next
End Sub

'@Description("Returns scalar values as is or appropriate representation if not scalar.")
Private Function GetScalarRepresentation( _
        ByRef element As Variant, _
        Optional ByVal QuoteStrings As Boolean _
    ) As Variant
Attribute GetScalarRepresentation.VB_Description = "Returns scalar values as is or appropriate representation if not scalar."
    Dim result As Variant
    If IsObject(element) Then
        On Error Resume Next
        'Try to retrieve default member
        result = element
        On Error GoTo 0
        ' if there is no default member or it returns an object result = Empty
        If IsEmpty(result) Then
            result = OBJECT_REPR
        End If
    Else
        result = element
    End If
    ' if the element is array or default member returns an array then convert tostring
    If IsArray(result) And Not IsEmpty(result) Then
        Dim PassThruArray() As Variant
        PassThruArray = result
        StringBuilder NewString:=True
        RecursiveToString PassThruArray, False, CHR_COMMA, "{", "}", QuoteStrings
        result = StringBuilder(Final:=True)
    End If
    If Not IsNumeric(result) And QuoteStrings Then
        GetScalarRepresentation = Chr$(34) & result & Chr$(34)
    Else
        GetScalarRepresentation = result
    End If
    
End Function

'@Description("Returns the type of a passed array.")
Private Function GetArrayType(ByVal SourceArray As Variant) As ArrayTypes
Attribute GetArrayType.VB_Description = "Returns the type of a passed array."
    Dim result As ArrayTypes
    If IsArray(SourceArray) Then
        If Not IsArrayAllocated(SourceArray) Then
            result = BA_UNALLOCATED
        Else
            If IsMultidimensionalArray(SourceArray) Then
                result = BA_MULTIDIMENSION
            ElseIf IsJaggedArray(SourceArray) Then
                result = BA_JAGGED
            Else
                result = BA_ONEDIMENSION
            End If
        End If
    Else
        If IsEmpty(SourceArray) Then
            result = BA_UNDEFINED
        Else
            RaiseError EC_EXPECTED_ARRAY, "getArrayType", "sourceArray"
        End If
    End If
    GetArrayType = result
End Function

'@Description("Tests if an array has a single empty slot.")
Private Function IsArrayEmpty(ByVal SourceArray As Variant) As Boolean
Attribute IsArrayEmpty.VB_Description = "Tests if an array has a single empty slot."
    Dim result As Boolean
    If LBound(SourceArray) = UBound(SourceArray) Then
        On Error Resume Next ' Error handler necessary in case of multidimension array
        result = (SourceArray(LBound(SourceArray)) = Empty)
        On Error GoTo 0
    End If
    IsArrayEmpty = result
End Function

'@Description("Tests if an array has been allocated.")
Private Function IsArrayAllocated(ByVal SourceArray As Variant) As Boolean
Attribute IsArrayAllocated.VB_Description = "Tests if an array has been allocated."
    On Error Resume Next
    IsArrayAllocated = ( _
        IsArray(SourceArray) And _
        Not IsError(LBound(SourceArray, 1)) And _
        LBound(SourceArray, 1) <= UBound(SourceArray, 1) _
    )
    On Error GoTo 0
End Function

'@Description("Tests if an array is jagged.")
Private Function IsJaggedArray(ByVal SourceArray As Variant) As Boolean
Attribute IsJaggedArray.VB_Description = "Tests if an array is jagged."
    If IsArray(SourceArray) Then
        On Error GoTo ErrHandler
        Dim element As Variant
        For Each element In SourceArray
            If IsArray(element) Then
                IsJaggedArray = True
                Exit Function
            End If
        Next
        On Error GoTo 0
    End If
    Exit Function
ErrHandler:
    err.Clear
End Function

'@Description("Tests if an array is multidimensioned.")
Private Function IsMultidimensionalArray(ByVal SourceArray As Variant) As Boolean
Attribute IsMultidimensionalArray.VB_Description = "Tests if an array is multidimensioned."
    If IsArray(SourceArray) Then
        On Error GoTo ErrHandler
        '@Ignore VariableNotUsed
        Dim LocalUpperBound As Long
        '@Ignore AssignmentNotUsed
        LocalUpperBound = UBound(SourceArray, 2)
        IsMultidimensionalArray = True
        On Error GoTo 0
    End If
    Exit Function
ErrHandler:
    err.Clear
End Function

'@Description("re-indexes array to conform to new bounds. Does not change length.")
Private Function Rebase(Optional ByRef SourceArray As Variant, Optional ByVal CurrentArrayType As ArrayTypes) As Variant()
Attribute Rebase.VB_Description = "re-indexes array to conform to new bounds. Does not change length."
    Dim LocalItems() As Variant
    Dim LocalType As ArrayTypes

    If IsMissing(SourceArray) Or Not IsArray(SourceArray) Then
        LocalItems = InternalItems
        LocalType = This.ArrayType
    Else
        LocalItems = SourceArray
        If CurrentArrayType = 0 Then
            LocalType = GetArrayType(LocalItems)
        Else
            LocalType = CurrentArrayType
        End If
    End If
    If LocalType = BA_MULTIDIMENSION Then
        ' ensure all nested arrays have the correct base
        ' if they don't and additional arrays are added via concat the resulting
        ' md array from jaggedToMulti will have unexpected bounds
        Rebase = RecursiveRebase(LocalItems, True)
    Else
        Rebase = RecursiveRebase(LocalItems, False)
    End If
End Function

'@Description("re-indexes nested arrays to conform to new bounds. Child function of Rebase)
Private Function RecursiveRebase( _
        ByRef SourceArray() As Variant, _
        ByVal Recurse As Boolean _
    ) As Variant()
    Dim i As Long
    Dim LocalLowerBound As Long
    Dim LocalUpperBound As Long
    Dim Offset As Long
    Dim NewItems() As Variant
    
    LocalLowerBound = LBound(SourceArray)
    LocalUpperBound = UBound(SourceArray)
    Offset = This.LowerBound - LocalLowerBound
    ReDim NewItems(This.LowerBound To LocalUpperBound + Offset)
    For i = LocalLowerBound To LocalUpperBound
        If IsArray(SourceArray(i)) And Recurse And Offset <> 0 Then
            Dim Nested() As Variant
            Nested = SourceArray(i)
            NewItems(i + Offset) = RecursiveRebase(Nested, Recurse)
        Else
            NewItems(i + Offset) = SourceArray(i)
        End If
    Next
    
    RecursiveRebase = NewItems
End Function

'@Description("Increases capacity of internal array if required.")
Private Sub EnsureCapacity(ByVal MinimumCapacity As Long)
Attribute EnsureCapacity.VB_Description = "Increases capacity of internal array if required."
    If This.Capacity < MinimumCapacity Then
        Dim NewCapacity As Long
        NewCapacity = IIf(This.Capacity = 0, DEFAULT_CAPACITY, This.Capacity * 2)
        If NewCapacity > MAX_ARRAY_LENGTH Then
            NewCapacity = MAX_ARRAY_LENGTH
        End If
        If NewCapacity < MinimumCapacity Then
            NewCapacity = MinimumCapacity
        End If
        Me.Capacity = NewCapacity
    End If
End Sub

'@Description("Converts a typed array to a variant() array")
Private Function ConvertArrayForStorage( _
    ByRef values As Variant, _
    ByVal CurrentArrayType As ArrayTypes, _
    Optional ByVal ConvertMultiToJagged As Boolean, _
    Optional ByVal ConvertJaggedNestedArrays As Boolean _
) As Variant()
Attribute ConvertArrayForStorage.VB_Description = "Converts a typed array to a variant() array"
    Dim result() As Variant
    Select Case CurrentArrayType
    Case ArrayTypes.BA_MULTIDIMENSION
        If ConvertMultiToJagged Then
            result = MultiToJagged(values)
        ElseIf TypeName(values) <> "Variant()" Then
            result = TypedMultiToVariantMulti(values)
        Else
            result = values
        End If
    Case ArrayTypes.BA_ONEDIMENSION, ArrayTypes.BA_JAGGED
        If TypeName(values) <> "Variant()" _
            Or (CurrentArrayType = BA_JAGGED And ConvertJaggedNestedArrays) _
            Or LBound(values) <> This.LowerBound Then
            result = TypedJaggedToVariantJagged( _
                values, _
                ConvertJaggedNestedArrays, _
                ConvertMultiToJagged _
            )
        Else
            result = values
        End If
    End Select
    ConvertArrayForStorage = result
End Function

'@Description("Converts a typed jagged array to a variant() jagged array")
Private Function TypedJaggedToVariantJagged( _
    ByRef SourceArray As Variant, _
    Optional ByVal ConvertJaggedNestedArrays As Boolean, _
    Optional ByVal ConvertMultiToJagged As Boolean _
) As Variant()
Attribute TypedJaggedToVariantJagged.VB_Description = "Converts a typed jagged array to a variant() jagged array"
    Dim result() As Variant
    Dim i As Long
    Dim Bounds(0 To 1) As Long
    Dim Offset As Long
    
    Bounds(0) = LBound(SourceArray)
    Bounds(1) = UBound(SourceArray)
    Offset = This.LowerBound - Bounds(0)
    ReDim result(Bounds(0) + Offset To Bounds(1) + Offset)
    For i = Bounds(0) To Bounds(1)
        If IsArray(SourceArray(i)) Then
            result(i + Offset) = ConvertArrayForStorage( _
                SourceArray(i), _
                GetArrayType(SourceArray(i)), _
                ConvertMultiToJagged, _
                ConvertJaggedNestedArrays _
            )
        Else
            LetOrSetElement result(i + Offset), SourceArray(i)
        End If
    Next
    TypedJaggedToVariantJagged = result
End Function

'@Description("Converts a typed md array to a variant() md array")
Private Function TypedMultiToVariantMulti( _
    ByRef SourceArray As Variant _
) As Variant()
Attribute TypedMultiToVariantMulti.VB_Description = "Converts a typed md array to a variant() md array"
    Dim LocalDepth As Long
    Dim result() As Variant
    
    LocalDepth = GetMultidimensionalArrayDepth(SourceArray)
    
    If LocalDepth = 2 Then
        Dim FirstDimBounds(0 To 1) As Long
        Dim SecondDimBounds(0 To 1) As Long
        Dim FirstDimOffset As Long
        Dim SecondDimOffset As Long
        Dim i As Long
        Dim j As Long
        
        FirstDimBounds(0) = LBound(SourceArray, 1)
        FirstDimBounds(1) = UBound(SourceArray, 1)
        SecondDimBounds(0) = LBound(SourceArray, 2)
        SecondDimBounds(1) = UBound(SourceArray, 2)
        FirstDimOffset = This.LowerBound - FirstDimBounds(0)
        SecondDimOffset = This.LowerBound - SecondDimBounds(0)
        ReDim result( _
            FirstDimBounds(0) + FirstDimOffset To FirstDimBounds(1) + FirstDimOffset, _
            SecondDimBounds(0) + SecondDimOffset To SecondDimBounds(1) + SecondDimOffset _
        )
        For i = FirstDimBounds(0) To FirstDimBounds(1)
            For j = SecondDimBounds(0) To SecondDimBounds(1)
                LetOrSetElement result(i + FirstDimOffset, j + SecondDimOffset), SourceArray(i, j)
            Next
        Next
    ElseIf LocalDepth > 2 And LocalDepth <= 20 Then
        result = RecursiveTypedMultiToVariantMulti(SourceArray, LocalDepth)
    Else
        RaiseError EC_MAX_DIMENSIONS_LIMIT, "MultiToJagged()", "sourceArray()"
    End If
    
    TypedMultiToVariantMulti = result
        
End Function

'@Description("Returns an array representing the structure of a Multidimension array")
Private Function MapMultidimensionArray( _
        ByRef SourceArray As Variant, _
        Optional ByVal KnownDepth As Long _
    ) As Variant()
Attribute MapMultidimensionArray.VB_Description = "Returns an array representing the structure of a Multidimension array"
    Dim i As Long
    Dim LocalMap() As Variant
    Dim LocalDepth As Long
    Dim CurrentBounds(0 To 1) As Long

    If Not IsArray(SourceArray) Then Exit Function

    If KnownDepth > 0 Then
        LocalDepth = KnownDepth
    Else
        LocalDepth = GetMultidimensionalArrayDepth(SourceArray)
    End If

    ' crumbs are base 0
    ReDim LocalMap(0 To LocalDepth - 1)

    For i = LBound(LocalMap) To UBound(LocalMap)
        CurrentBounds(0) = LBound(SourceArray, i + 1)
        CurrentBounds(1) = UBound(SourceArray, i + 1)
        LocalMap(i) = CurrentBounds
    Next

    MapMultidimensionArray = LocalMap
End Function

'@Description("Recursively Converts typred multidimension arrays to variant md arrays arrays. For md arrays with more than 2d.")
Private Function RecursiveTypedMultiToVariantMulti( _
        ByRef SourceArray As Variant, _
        Optional ByVal Depth As Long, _
        Optional ByVal CurrentDepth As Long, _
        Optional ByRef Crumbs As Variant, _
        Optional ByRef result As Variant, _
        Optional ByVal EnsureScalar As Boolean _
    ) As Variant()
Attribute RecursiveTypedMultiToVariantMulti.VB_Description = "Recursively Converts typred multidimension arrays to variant md arrays arrays. For md arrays with more than 2d."
    Dim i As Long
    Dim LocalLowerBound As Long
    Dim LocalUpperBound As Long
    Dim LocalDepth As Long
    Dim LocalCurrentDepth As Long
    Dim LocalCrumbs() As Variant
    Dim LocalResult() As Variant
    Dim CurrentElement As Variant
    
    LocalDepth = Depth
    LocalCurrentDepth = CurrentDepth

    If IsMissing(Crumbs) Then
        ReDim LocalCrumbs(LocalDepth - 1)
    Else
        LocalCrumbs = Crumbs
    End If

    If IsMissing(result) Then
        LocalResult = CreateMultidimensionalArray(MapMultidimensionArray(SourceArray, LocalDepth))
    Else
        LocalResult = result
    End If

    Inc LocalCurrentDepth
    LocalLowerBound = LBound(SourceArray, LocalCurrentDepth)
    LocalUpperBound = UBound(SourceArray, LocalCurrentDepth)
    For i = LocalLowerBound To LocalUpperBound
        LocalCrumbs(LocalCurrentDepth - 1) = i
        If LocalCurrentDepth = LocalDepth Then
            LetOrSetElement CurrentElement, GetElementByBreadcrumb(SourceArray, LocalCrumbs)
            If EnsureScalar Then
                LocalResult = LetElementByBreadcrumb(LocalResult, LocalCrumbs, GetScalarRepresentation(CurrentElement))
            Else
                LocalResult = LetElementByBreadcrumb(LocalResult, LocalCrumbs, CurrentElement)
            End If
        Else
            LocalResult = RecursiveTypedMultiToVariantMulti( _
                SourceArray:=SourceArray, _
                Depth:=LocalDepth, _
                CurrentDepth:=LocalCurrentDepth, _
                Crumbs:=LocalCrumbs, _
                result:=LocalResult, _
                EnsureScalar:=EnsureScalar _
            )
        End If
    Next

    RecursiveTypedMultiToVariantMulti = LocalResult
End Function

'@Description("Converts jagged arrays to multidimension arrays")
Private Function JaggedToMulti( _
        ByRef SourceArray() As Variant, _
        Optional ByVal Depth As Long, _
        Optional ByVal EnsureScalar As Boolean _
    ) As Variant()
Attribute JaggedToMulti.VB_Description = "Converts jagged arrays to multidimension arrays"
    Dim LocalDepth As Long
    Dim result() As Variant
    LocalDepth = Depth
    If LocalDepth = 0 Then
        If Not IsJaggedArray(SourceArray) Then
            RaiseError EC_EXPECTED_JAGGED_ARRAY, "JaggedToMulti", "sourceArray()"
            Exit Function
        End If
        LocalDepth = GetJaggedArrayDepth(SourceArray)
    End If
    
    If LocalDepth <= 1 Then
        result = SourceArray
    ElseIf LocalDepth = 2 Then
        Dim FirstDimBounds() As Long
        Dim SecondDimBounds() As Long
        Dim i As Long
        Dim j As Long
        FirstDimBounds = GetArrayBounds(SourceArray)
        SecondDimBounds = GetMaxBoundsAtDimension(SourceArray, 2)
        ReDim result(FirstDimBounds(0) To FirstDimBounds(1), _
            SecondDimBounds(0) To SecondDimBounds(1))
        For i = FirstDimBounds(0) To FirstDimBounds(1)
            If IsArray(SourceArray(i)) Then
                For j = LBound(SourceArray(i)) To UBound(SourceArray(i))
                    If EnsureScalar Then
                        LetOrSetElement result(i, j), _
                            GetScalarRepresentation(SourceArray(i)(j))
                    Else
                        LetOrSetElement result(i, j), _
                            SourceArray(i)(j)
                    End If
                Next
            Else
                If EnsureScalar Then
                    LetOrSetElement result(i, LBound(result, 2)), _
                        GetScalarRepresentation(SourceArray(i))
                Else
                    LetOrSetElement result(i, LBound(result, 2)), _
                        SourceArray(i)
                End If
            End If
        Next
    ElseIf LocalDepth > 2 And LocalDepth <= 20 Then
        result = RecursiveJaggedToMulti(SourceArray, LocalDepth, EnsureScalar:=EnsureScalar)
    Else
        RaiseError EC_MAX_DIMENSIONS_LIMIT, "JaggedToMulti()", "sourceArray()"
        result = SourceArray
    End If
    JaggedToMulti = result
End Function

Private Function MultiToJagged( _
    ByRef SourceArray As Variant, _
    Optional ByVal Depth As Long _
) As Variant()
    Dim LocalDepth As Long
    Dim result() As Variant
    
    LocalDepth = Depth
    
    If LocalDepth = 0 Then
        If Not IsMultidimensionalArray(SourceArray) Then
            RaiseError EC_EXPECTED_MULTIDIMENSION_ARRAY, "MultiToJagged", "sourceArray()"
            result = SourceArray
            Exit Function
        End If
        LocalDepth = GetMultidimensionalArrayDepth(SourceArray)
    End If
    
    If LocalDepth <= 1 Then
        result = SourceArray
    ElseIf LocalDepth = 2 Then
        Dim FirstDimBounds(0 To 1) As Long
        Dim SecondDimBounds(0 To 1) As Long
        Dim FirstDimOffset As Long
        Dim SecondDimOffset As Long
        Dim Nested() As Variant
        Dim i As Long
        Dim j As Long
        
        FirstDimBounds(0) = LBound(SourceArray, 1)
        FirstDimBounds(1) = UBound(SourceArray, 1)
        SecondDimBounds(0) = LBound(SourceArray, 2)
        SecondDimBounds(1) = UBound(SourceArray, 2)
        FirstDimOffset = This.LowerBound - FirstDimBounds(0)
        SecondDimOffset = This.LowerBound - SecondDimBounds(0)
        ReDim result(FirstDimBounds(0) + FirstDimOffset To FirstDimBounds(1) + FirstDimOffset)
        For i = FirstDimBounds(0) To FirstDimBounds(1)
            ReDim Nested(SecondDimBounds(0) + SecondDimOffset To SecondDimBounds(1) + SecondDimOffset)
            For j = SecondDimBounds(0) To SecondDimBounds(1)
                LetOrSetElement Nested(j + SecondDimOffset), SourceArray(i, j)
            Next
            result(i + FirstDimOffset) = Nested
        Next
    ElseIf LocalDepth > 2 And LocalDepth <= 20 Then
        result = RecursiveMultiToJagged(SourceArray, LocalDepth)
    Else
        RaiseError EC_MAX_DIMENSIONS_LIMIT, "MultiToJagged()", "sourceArray()"
        result = SourceArray
    End If
    
    MultiToJagged = result
End Function

'@Description("Recursively Converts multidimension arrays to jagged arrays. For md arrays with more than 2d.")
Private Function RecursiveMultiToJagged( _
        ByRef SourceArray As Variant, _
        Optional ByVal Depth As Long, _
        Optional ByVal CurrentDepth As Long, _
        Optional ByRef Crumbs As Variant _
    ) As Variant()
Attribute RecursiveMultiToJagged.VB_Description = "Recursively Converts multidimension arrays to jagged arrays. For md arrays with more than 2d."
    Dim i As Long
    Dim LocalLowerBound As Long
    Dim LocalUpperBound As Long
    Dim LocalDepth As Long
    Dim LocalCurrentDepth As Long
    Dim LocalCrumbs() As Variant
    Dim result() As Variant
    Dim BoundOffset As Long
    
    LocalDepth = Depth
    LocalCurrentDepth = CurrentDepth
    
    If LocalDepth > 1 Then
        If IsMissing(Crumbs) Then
            ReDim LocalCrumbs(LocalDepth - 1)
        Else
            LocalCrumbs = Crumbs
        End If
        Inc LocalCurrentDepth
        LocalLowerBound = LBound(SourceArray, LocalCurrentDepth)
        LocalUpperBound = UBound(SourceArray, LocalCurrentDepth)
        BoundOffset = This.LowerBound - LocalLowerBound
        ReDim result(LocalLowerBound + BoundOffset To LocalUpperBound + BoundOffset)
        For i = LocalLowerBound To LocalUpperBound
            LocalCrumbs(LocalCurrentDepth - 1) = i
            If LocalCurrentDepth = LocalDepth Then
                LetOrSetElement result(i + BoundOffset), GetElementByBreadcrumb(SourceArray, LocalCrumbs)
            Else
                result(i + BoundOffset) = RecursiveMultiToJagged(SourceArray, LocalDepth, LocalCurrentDepth, LocalCrumbs)
            End If
        Next
    Else
        result = SourceArray
    End If
    RecursiveMultiToJagged = result
End Function


'@Description("Recursively Converts jagged arrays to multidimension arrays. For jagged arrays with more than 2d.")
Private Function RecursiveJaggedToMulti( _
        ByRef SourceArray() As Variant, _
        Optional ByVal Depth As Long, _
        Optional ByVal CurrentDepth As Long, _
        Optional ByRef Crumbs As Variant, _
        Optional ByRef result As Variant, _
        Optional ByVal EnsureScalar As Boolean _
    ) As Variant()
Attribute RecursiveJaggedToMulti.VB_Description = "Recursively Converts jagged arrays to multidimension arrays. For jagged arrays with more than 2d."
    Dim i As Long
    Dim LocalLowerBound As Long
    Dim LocalUpperBound As Long
    Dim LocalDepth As Long
    Dim LocalCurrentDepth As Long
    Dim LocalCrumbs() As Variant
    Dim LocalResult() As Variant


    LocalDepth = Depth
    LocalCurrentDepth = CurrentDepth

    If IsMissing(Crumbs) Then
        ReDim LocalCrumbs(LocalDepth - 1)
    Else
        LocalCrumbs = Crumbs
    End If

    If IsMissing(result) Then
        LocalResult = CreateMultidimensionalArray(MapJaggedArray(SourceArray, KnownDepth:=LocalDepth))
    Else
        LocalResult = result
    End If

    Inc LocalCurrentDepth
    LocalLowerBound = LBound(SourceArray)
    LocalUpperBound = UBound(SourceArray)
    For i = LocalLowerBound To LocalUpperBound
        LocalCrumbs(LocalCurrentDepth - 1) = i
        If LocalCurrentDepth = LocalDepth Then
            If EnsureScalar Then
                LocalResult = LetElementByBreadcrumb(LocalResult, LocalCrumbs, GetScalarRepresentation(SourceArray(i)))
            Else
                LocalResult = LetElementByBreadcrumb(LocalResult, LocalCrumbs, SourceArray(i))
            End If
        Else
            Dim Nested() As Variant
            If Not IsArray(SourceArray(i)) Then
                Nested = Array(SourceArray(i))
            Else
                Nested = SourceArray(i)
            End If
            LocalResult = RecursiveJaggedToMulti( _
                SourceArray:=Nested, _
                Depth:=LocalDepth, _
                CurrentDepth:=LocalCurrentDepth, _
                Crumbs:=LocalCrumbs, _
                result:=LocalResult, _
                EnsureScalar:=EnsureScalar _
            )
        End If
    Next
    RecursiveJaggedToMulti = LocalResult
End Function

'@Description("Returns a number representing how many levels of nested arrays are contained in array.")
Private Function GetJaggedArrayDepth(ByRef SourceArray() As Variant) As Long
Attribute GetJaggedArrayDepth.VB_Description = "Returns a number representing how many levels of nested arrays are contained in array."
    Dim i As Long
    Dim LocalLowerBound As Long
    Dim LocalUpperBound As Long
    Dim CurrentDepth As Long
    Dim MaxDepth As Long
    Dim Depth As Long
    
    If IsArray(SourceArray) Then
        Inc Depth
        LocalLowerBound = LBound(SourceArray)
        LocalUpperBound = UBound(SourceArray)
        For i = LocalLowerBound To LocalUpperBound
            If IsArray(SourceArray(i)) Then
                Dim Nested() As Variant
                Nested = SourceArray(i)
                CurrentDepth = GetJaggedArrayDepth(Nested)
                If CurrentDepth > MaxDepth Then MaxDepth = CurrentDepth
            End If
        Next
        Inc Depth, MaxDepth
    End If
    GetJaggedArrayDepth = Depth
End Function

'@Description("Gets the maximium bound values for a specified dimension of a jagged array.")
Private Function GetMaxBoundsAtDimension( _
        ByRef SourceArray() As Variant, _
        Optional ByVal Dimension As Long = 1, _
        Optional ByVal CurrentDimension As Long = 1 _
    ) As Long()
Attribute GetMaxBoundsAtDimension.VB_Description = "Gets the maximium bound values for a specified dimension of a jagged array."
    Dim MaxBounds() As Long
    
    If CurrentDimension < Dimension Then
        Dim i As Long
        Dim CurrentBounds() As Long
        Dim LocalLowerBound As Long
        Dim LocalUpperBound As Long
        
        LocalLowerBound = LBound(SourceArray)
        LocalUpperBound = UBound(SourceArray)
        For i = LocalLowerBound To LocalUpperBound
            If IsArray(SourceArray(i)) Then
                Dim Nested() As Variant
                Nested = SourceArray(i)
                CurrentBounds = GetMaxBoundsAtDimension(Nested, Dimension, CurrentDimension + 1)
                If Not IsArrayAllocated(MaxBounds) Then
                    MaxBounds = CurrentBounds
                Else
                    If CurrentBounds(0) < MaxBounds(0) Then MaxBounds(0) = CurrentBounds(0)
                    If CurrentBounds(1) > MaxBounds(1) Then MaxBounds(1) = CurrentBounds(1)
                End If
            End If
        Next
    Else
        MaxBounds = GetArrayBounds(SourceArray)
    End If
    
    GetMaxBoundsAtDimension = MaxBounds
End Function

'@Description("Returns an array representing the structure of a jagged array")
Private Function MapJaggedArray( _
        ByRef SourceArray() As Variant, _
        Optional ByVal KnownDepth As Long _
    ) As Variant()
Attribute MapJaggedArray.VB_Description = "Returns an array representing the structure of a jagged array"
    Dim i As Long
    Dim LocalMap() As Variant
    Dim LocalDepth As Long

    If Not IsArray(SourceArray) Then Exit Function

    If KnownDepth > 0 Then
        LocalDepth = KnownDepth
    Else
        LocalDepth = GetJaggedArrayDepth(SourceArray)
    End If

    ' crumbs are base 0
    ReDim LocalMap(0 To LocalDepth - 1)

    For i = LBound(LocalMap) To UBound(LocalMap)
        LocalMap(i) = GetMaxBoundsAtDimension(SourceArray, i + 1)
    Next

    MapJaggedArray = LocalMap
End Function


'@Description("Returns a 0-based array with two slots. First slot is the lowerbound of the passed array. second slot (index 0) is the upper bound.")
Private Function GetArrayBounds(ByVal SourceArray As Variant) As Long()
Attribute GetArrayBounds.VB_Description = "Returns a 0-based array with two slots. First slot is the lowerbound of the passed array. second slot (index 0) is the upper bound."
    Dim result(0 To 1) As Long
    If IsArray(SourceArray) Then
        result(0) = LBound(SourceArray)
        result(1) = UBound(SourceArray)
    End If
    GetArrayBounds = result
End Function

'@Description("Returns a number representing the total number of dimensions of a multidimension array.")
Private Function GetMultidimensionalArrayDepth(ByVal SourceArray As Variant) As Long
Attribute GetMultidimensionalArrayDepth.VB_Description = "Returns a number representing the total number of dimensions of a multidimension array."
    Dim i As Long
    '@Ignore VariableNotUsed
    Dim Void As Long
    
    On Error Resume Next
    Do
        Inc i
        Void = UBound(SourceArray, i)
    Loop Until err.Number <> 0
    err.Clear
    On Error GoTo 0
    GetMultidimensionalArrayDepth = i - 1
End Function

'@Description("Returns the element stored in an array based on a crumb argument. A crumb is an array representing the location of the multidimension array slot.")
Private Function GetElementByBreadcrumb( _
        ByVal SourceArray As Variant, _
        ByRef Crumb() As Variant _
    ) As Variant
Attribute GetElementByBreadcrumb.VB_Description = "Returns the element stored in an array based on a crumb argument. A crumb is an array representing the location of the multidimension array slot."
    Dim result As Variant
    Select Case UBound(Crumb)
    Case 0
        LetOrSetElement result, SourceArray(Crumb(0))
    Case 1
        LetOrSetElement result, SourceArray(Crumb(0), Crumb(1))
    Case 2
        LetOrSetElement result, SourceArray(Crumb(0), Crumb(1), Crumb(2))
    Case 3
        LetOrSetElement result, SourceArray(Crumb(0), Crumb(1), Crumb(2), Crumb(3))
    Case 4
        LetOrSetElement result, SourceArray(Crumb(0), Crumb(1), Crumb(2), Crumb(3), Crumb(4))
    Case 5
        LetOrSetElement result, SourceArray(Crumb(0), Crumb(1), Crumb(2), Crumb(3), Crumb(4), Crumb(5))
    Case 6
        LetOrSetElement result, SourceArray(Crumb(0), Crumb(1), Crumb(2), Crumb(3), Crumb(4), Crumb(5), Crumb(6))
    Case 7
        LetOrSetElement result, SourceArray(Crumb(0), Crumb(1), Crumb(2), Crumb(3), Crumb(4), Crumb(5), Crumb(6), Crumb(7))
    Case 8
        LetOrSetElement result, SourceArray(Crumb(0), Crumb(1), Crumb(2), Crumb(3), Crumb(4), Crumb(5), Crumb(6), Crumb(7), Crumb(8))
    Case 9
        LetOrSetElement result, SourceArray(Crumb(0), Crumb(1), Crumb(2), Crumb(3), Crumb(4), Crumb(5), Crumb(6), Crumb(7), Crumb(8), _
            Crumb(9))
    Case 10
        LetOrSetElement result, SourceArray(Crumb(0), Crumb(1), Crumb(2), Crumb(3), Crumb(4), Crumb(5), Crumb(6), Crumb(7), Crumb(8), _
            Crumb(9), Crumb(10))
    Case 11
        LetOrSetElement result, SourceArray(Crumb(0), Crumb(1), Crumb(2), Crumb(3), Crumb(4), Crumb(5), Crumb(6), Crumb(7), Crumb(8), _
            Crumb(9), Crumb(10), Crumb(11))
    Case 12
        LetOrSetElement result, SourceArray(Crumb(0), Crumb(1), Crumb(2), Crumb(3), Crumb(4), Crumb(5), Crumb(6), Crumb(7), Crumb(8), _
            Crumb(9), Crumb(10), Crumb(11), Crumb(12))
    Case 13
        LetOrSetElement result, SourceArray(Crumb(0), Crumb(1), Crumb(2), Crumb(3), Crumb(4), Crumb(5), Crumb(6), Crumb(7), Crumb(8), _
            Crumb(9), Crumb(10), Crumb(11), Crumb(12), Crumb(13))
    Case 14
        LetOrSetElement result, SourceArray(Crumb(0), Crumb(1), Crumb(2), Crumb(3), Crumb(4), Crumb(5), Crumb(6), Crumb(7), Crumb(8), _
            Crumb(9), Crumb(10), Crumb(11), Crumb(12), Crumb(13), Crumb(14))
    Case 15
        LetOrSetElement result, SourceArray(Crumb(0), Crumb(1), Crumb(2), Crumb(3), Crumb(4), Crumb(5), Crumb(6), Crumb(7), Crumb(8), _
            Crumb(9), Crumb(10), Crumb(11), Crumb(12), Crumb(13), Crumb(14), Crumb(15))
    Case 16
        LetOrSetElement result, SourceArray(Crumb(0), Crumb(1), Crumb(2), Crumb(3), Crumb(4), Crumb(5), Crumb(6), Crumb(7), Crumb(8), _
            Crumb(9), Crumb(10), Crumb(11), Crumb(12), Crumb(13), Crumb(14), Crumb(15), Crumb(16))
    Case 17
        LetOrSetElement result, SourceArray(Crumb(0), Crumb(1), Crumb(2), Crumb(3), Crumb(4), Crumb(5), Crumb(6), Crumb(7), Crumb(8), _
            Crumb(9), Crumb(10), Crumb(11), Crumb(12), Crumb(13), Crumb(14), Crumb(15), Crumb(16), Crumb(17))
    Case 18
        LetOrSetElement result, SourceArray(Crumb(0), Crumb(1), Crumb(2), Crumb(3), Crumb(4), Crumb(5), Crumb(6), Crumb(7), Crumb(8), _
            Crumb(9), Crumb(10), Crumb(11), Crumb(12), Crumb(13), Crumb(14), Crumb(15), Crumb(16), Crumb(17), Crumb(18))
    Case 19
        LetOrSetElement result, SourceArray(Crumb(0), Crumb(1), Crumb(2), Crumb(3), Crumb(4), Crumb(5), Crumb(6), Crumb(7), Crumb(8), _
            Crumb(9), Crumb(10), Crumb(11), Crumb(12), Crumb(13), Crumb(14), Crumb(15), Crumb(16), Crumb(17), Crumb(18), Crumb(19))
    Case 20
        LetOrSetElement result, SourceArray(Crumb(0), Crumb(1), Crumb(2), Crumb(3), Crumb(4), Crumb(5), Crumb(6), Crumb(7), Crumb(8), _
            Crumb(9), Crumb(10), Crumb(11), Crumb(12), Crumb(13), Crumb(14), Crumb(15), Crumb(16), Crumb(17), Crumb(18), Crumb(19), Crumb(20))
    End Select
    '@Ignore UnassignedVariableUsage
    GetElementByBreadcrumb = result
End Function

'@Description("Assigns an element to a location in a multidimensonal array based on a crumb argument. A crumb is an array representing the location of the multidimension array slot.")
Private Function LetElementByBreadcrumb( _
        ByRef SourceArray() As Variant, _
        ByRef Crumb() As Variant, _
        ByVal element As Variant _
    ) As Variant
Attribute LetElementByBreadcrumb.VB_Description = "Assigns an element to a location in a multidimensonal array based on a crumb argument. A crumb is an array representing the location of the multidimension array slot."
    Select Case UBound(Crumb)
    Case 0
        LetOrSetElement SourceArray(Crumb(0)), element
    Case 1
        LetOrSetElement SourceArray(Crumb(0), Crumb(1)), element
    Case 2
        LetOrSetElement SourceArray(Crumb(0), Crumb(1), Crumb(2)), element
    Case 3
        LetOrSetElement SourceArray(Crumb(0), Crumb(1), Crumb(2), Crumb(3)), element
    Case 4
        LetOrSetElement SourceArray(Crumb(0), Crumb(1), Crumb(2), Crumb(3), Crumb(4)), element
    Case 5
        LetOrSetElement SourceArray(Crumb(0), Crumb(1), Crumb(2), Crumb(3), Crumb(4), Crumb(5)), element
    Case 6
        LetOrSetElement SourceArray(Crumb(0), Crumb(1), Crumb(2), Crumb(3), Crumb(4), Crumb(5), Crumb(6)), element
    Case 7
        LetOrSetElement SourceArray(Crumb(0), Crumb(1), Crumb(2), Crumb(3), Crumb(4), Crumb(5), Crumb(6), Crumb(7)), element
    Case 8
        LetOrSetElement SourceArray(Crumb(0), Crumb(1), Crumb(2), Crumb(3), Crumb(4), Crumb(5), Crumb(6), Crumb(7), Crumb(8)), element
    Case 9
        LetOrSetElement SourceArray(Crumb(0), Crumb(1), Crumb(2), Crumb(3), Crumb(4), Crumb(5), Crumb(6), Crumb(7), Crumb(8), Crumb(9)), _
            element
    Case 10
        LetOrSetElement SourceArray(Crumb(0), Crumb(1), Crumb(2), Crumb(3), Crumb(4), Crumb(5), Crumb(6), Crumb(7), Crumb(8), Crumb(9), _
            Crumb(10)), element
    Case 11
        LetOrSetElement SourceArray(Crumb(0), Crumb(1), Crumb(2), Crumb(3), Crumb(4), Crumb(5), Crumb(6), Crumb(7), Crumb(8), Crumb(9), _
            Crumb(10), Crumb(11)), element
    Case 12
        LetOrSetElement SourceArray(Crumb(0), Crumb(1), Crumb(2), Crumb(3), Crumb(4), Crumb(5), Crumb(6), Crumb(7), Crumb(8), Crumb(9), _
            Crumb(10), Crumb(11), Crumb(12)), element
    Case 13
        LetOrSetElement SourceArray(Crumb(0), Crumb(1), Crumb(2), Crumb(3), Crumb(4), Crumb(5), Crumb(6), Crumb(7), Crumb(8), Crumb(9), _
            Crumb(10), Crumb(11), Crumb(12), Crumb(13)), element
    Case 14
        LetOrSetElement SourceArray(Crumb(0), Crumb(1), Crumb(2), Crumb(3), Crumb(4), Crumb(5), Crumb(6), Crumb(7), Crumb(8), Crumb(9), _
            Crumb(10), Crumb(11), Crumb(12), Crumb(13), Crumb(14)), element
    Case 15
        LetOrSetElement SourceArray(Crumb(0), Crumb(1), Crumb(2), Crumb(3), Crumb(4), Crumb(5), Crumb(6), Crumb(7), Crumb(8), Crumb(9), _
            Crumb(10), Crumb(11), Crumb(12), Crumb(13), Crumb(14), Crumb(15)), element
    Case 16
        LetOrSetElement SourceArray(Crumb(0), Crumb(1), Crumb(2), Crumb(3), Crumb(4), Crumb(5), Crumb(6), Crumb(7), Crumb(8), Crumb(9), _
        Crumb(10), Crumb(11), Crumb(12), Crumb(13), Crumb(14), Crumb(15), Crumb(16)), element
    Case 17
        LetOrSetElement SourceArray(Crumb(0), Crumb(1), Crumb(2), Crumb(3), Crumb(4), Crumb(5), Crumb(6), Crumb(7), Crumb(8), Crumb(9), _
            Crumb(10), Crumb(11), Crumb(12), Crumb(13), Crumb(14), Crumb(15), Crumb(16), Crumb(17)), element
    Case 18
        LetOrSetElement SourceArray(Crumb(0), Crumb(1), Crumb(2), Crumb(3), Crumb(4), Crumb(5), Crumb(6), Crumb(7), Crumb(8), Crumb(9), _
            Crumb(10), Crumb(11), Crumb(12), Crumb(13), Crumb(14), Crumb(15), Crumb(16), Crumb(17), Crumb(18)), element
    Case 19
        LetOrSetElement SourceArray(Crumb(0), Crumb(1), Crumb(2), Crumb(3), Crumb(4), Crumb(5), Crumb(6), Crumb(7), Crumb(8), Crumb(9), _
        Crumb(10), Crumb(11), Crumb(12), Crumb(13), Crumb(14), Crumb(15), Crumb(16), Crumb(17), Crumb(18), Crumb(19)), element
    Case 20
        LetOrSetElement SourceArray(Crumb(0), Crumb(1), Crumb(2), Crumb(3), Crumb(4), Crumb(5), Crumb(6), Crumb(7), Crumb(8), Crumb(9), _
        Crumb(10), Crumb(11), Crumb(12), Crumb(13), Crumb(14), Crumb(15), Crumb(16), Crumb(17), Crumb(18), Crumb(19), Crumb(20)), _
        element
    End Select

    LetElementByBreadcrumb = SourceArray
End Function

'@Description("Returns an empty multidimensional array with the dimensions specified in the crumb argument. A crumb is an array representing the structure of the multidimension array.")
Private Function CreateMultidimensionalArray(ByRef Crumb() As Variant) As Variant()
Attribute CreateMultidimensionalArray.VB_Description = "Returns an empty multidimensional array with the dimensions specified in the crumb argument. A crumb is an array representing the structure of the multidimension array."
    Dim result() As Variant
    Select Case UBound(Crumb)
    Case 0
        ReDim result(Crumb(0)(0) To Crumb(0)(1))
    Case 1
        ReDim result(Crumb(0)(0) To Crumb(0)(1), Crumb(1)(0) To Crumb(1)(1))
    Case 2
        ReDim result(Crumb(0)(0) To Crumb(0)(1), Crumb(1)(0) To Crumb(1)(1), Crumb(2)(0) To Crumb(2)(1))
    Case 3
        ReDim result(Crumb(0)(0) To Crumb(0)(1), Crumb(1)(0) To Crumb(1)(1), Crumb(2)(0) To Crumb(2)(1), Crumb(3)(0) To Crumb(3)(1))
    Case 4
        ReDim result(Crumb(0)(0) To Crumb(0)(1), Crumb(1)(0) To Crumb(1)(1), Crumb(2)(0) To Crumb(2)(1), Crumb(3)(0) To Crumb(3)(1), _
                     Crumb(4)(0) To Crumb(4)(1))
    Case 5
        ReDim result(Crumb(0)(0) To Crumb(0)(1), Crumb(1)(0) To Crumb(1)(1), Crumb(2)(0) To Crumb(2)(1), Crumb(3)(0) To Crumb(3)(1), _
                     Crumb(4)(0) To Crumb(4)(1), Crumb(5)(0) To Crumb(5)(1))
    Case 6
        ReDim result(Crumb(0)(0) To Crumb(0)(1), Crumb(1)(0) To Crumb(1)(1), Crumb(2)(0) To Crumb(2)(1), Crumb(3)(0) To Crumb(3)(1), _
                     Crumb(4)(0) To Crumb(4)(1), Crumb(5)(0) To Crumb(5)(1), Crumb(6)(0) To Crumb(6)(1))
    Case 7
        ReDim result(Crumb(0)(0) To Crumb(0)(1), Crumb(1)(0) To Crumb(1)(1), Crumb(2)(0) To Crumb(2)(1), Crumb(3)(0) To Crumb(3)(1), _
                     Crumb(4)(0) To Crumb(4)(1), Crumb(5)(0) To Crumb(5)(1), Crumb(6)(0) To Crumb(6)(1), Crumb(7)(0) To Crumb(7)(1))
    Case 8
        ReDim result(Crumb(0)(0) To Crumb(0)(1), Crumb(1)(0) To Crumb(1)(1), Crumb(2)(0) To Crumb(2)(1), Crumb(3)(0) To Crumb(3)(1), _
                     Crumb(4)(0) To Crumb(4)(1), Crumb(5)(0) To Crumb(5)(1), Crumb(6)(0) To Crumb(6)(1), Crumb(7)(0) To Crumb(7)(1), _
                     Crumb(8)(0) To Crumb(8)(1))
    Case 9
        ReDim result(Crumb(0)(0) To Crumb(0)(1), Crumb(1)(0) To Crumb(1)(1), Crumb(2)(0) To Crumb(2)(1), Crumb(3)(0) To Crumb(3)(1), _
                     Crumb(4)(0) To Crumb(4)(1), Crumb(5)(0) To Crumb(5)(1), Crumb(6)(0) To Crumb(6)(1), Crumb(7)(0) To Crumb(7)(1), _
                     Crumb(8)(0) To Crumb(8)(1), Crumb(9)(0) To Crumb(9)(1))
    Case 10
        ReDim result(Crumb(0)(0) To Crumb(0)(1), Crumb(1)(0) To Crumb(1)(1), Crumb(2)(0) To Crumb(2)(1), Crumb(3)(0) To Crumb(3)(1), _
                     Crumb(4)(0) To Crumb(4)(1), Crumb(5)(0) To Crumb(5)(1), Crumb(6)(0) To Crumb(6)(1), Crumb(7)(0) To Crumb(7)(1), _
                     Crumb(8)(0) To Crumb(8)(1), Crumb(9)(0) To Crumb(9)(1), Crumb(10)(0) To Crumb(10)(1))
    Case 11
        ReDim result(Crumb(0)(0) To Crumb(0)(1), Crumb(1)(0) To Crumb(1)(1), Crumb(2)(0) To Crumb(2)(1), Crumb(3)(0) To Crumb(3)(1), _
                     Crumb(4)(0) To Crumb(4)(1), Crumb(5)(0) To Crumb(5)(1), Crumb(6)(0) To Crumb(6)(1), Crumb(7)(0) To Crumb(7)(1), _
                     Crumb(8)(0) To Crumb(8)(1), Crumb(9)(0) To Crumb(9)(1), Crumb(10)(0) To Crumb(10)(1), Crumb(11)(0) To Crumb(11)(1))
    Case 12
        ReDim result(Crumb(0)(0) To Crumb(0)(1), Crumb(1)(0) To Crumb(1)(1), Crumb(2)(0) To Crumb(2)(1), Crumb(3)(0) To Crumb(3)(1), _
                     Crumb(4)(0) To Crumb(4)(1), Crumb(5)(0) To Crumb(5)(1), Crumb(6)(0) To Crumb(6)(1), Crumb(7)(0) To Crumb(7)(1), _
                     Crumb(8)(0) To Crumb(8)(1), Crumb(9)(0) To Crumb(9)(1), Crumb(10)(0) To Crumb(10)(1), Crumb(11)(0) To Crumb(11)(1), _
                     Crumb(12)(0) To Crumb(12)(1))
    Case 13
        ReDim result(Crumb(0)(0) To Crumb(0)(1), Crumb(1)(0) To Crumb(1)(1), Crumb(2)(0) To Crumb(2)(1), Crumb(3)(0) To Crumb(3)(1), _
                     Crumb(4)(0) To Crumb(4)(1), Crumb(5)(0) To Crumb(5)(1), Crumb(6)(0) To Crumb(6)(1), Crumb(7)(0) To Crumb(7)(1), _
                     Crumb(8)(0) To Crumb(8)(1), Crumb(9)(0) To Crumb(9)(1), Crumb(10)(0) To Crumb(10)(1), Crumb(11)(0) To Crumb(11)(1), _
                     Crumb(12)(0) To Crumb(12)(1), Crumb(13)(0) To Crumb(13)(1))
    Case 14
        ReDim result(Crumb(0)(0) To Crumb(0)(1), Crumb(1)(0) To Crumb(1)(1), Crumb(2)(0) To Crumb(2)(1), Crumb(3)(0) To Crumb(3)(1), _
                     Crumb(4)(0) To Crumb(4)(1), Crumb(5)(0) To Crumb(5)(1), Crumb(6)(0) To Crumb(6)(1), Crumb(7)(0) To Crumb(7)(1), _
                     Crumb(8)(0) To Crumb(8)(1), Crumb(9)(0) To Crumb(9)(1), Crumb(10)(0) To Crumb(10)(1), Crumb(11)(0) To Crumb(11)(1), _
                     Crumb(12)(0) To Crumb(12)(1), Crumb(13)(0) To Crumb(13)(1), Crumb(14)(0) To Crumb(14)(1))
    Case 15
        ReDim result(Crumb(0)(0) To Crumb(0)(1), Crumb(1)(0) To Crumb(1)(1), Crumb(2)(0) To Crumb(2)(1), Crumb(3)(0) To Crumb(3)(1), _
                     Crumb(4)(0) To Crumb(4)(1), Crumb(5)(0) To Crumb(5)(1), Crumb(6)(0) To Crumb(6)(1), Crumb(7)(0) To Crumb(7)(1), _
                     Crumb(8)(0) To Crumb(8)(1), Crumb(9)(0) To Crumb(9)(1), Crumb(10)(0) To Crumb(10)(1), Crumb(11)(0) To Crumb(11)(1), _
                     Crumb(12)(0) To Crumb(12)(1), Crumb(13)(0) To Crumb(13)(1), Crumb(14)(0) To Crumb(14)(1), Crumb(15)(0) To Crumb(15)(1))
    Case 16
        ReDim result(Crumb(0)(0) To Crumb(0)(1), Crumb(1)(0) To Crumb(1)(1), Crumb(2)(0) To Crumb(2)(1), Crumb(3)(0) To Crumb(3)(1), _
                     Crumb(4)(0) To Crumb(4)(1), Crumb(5)(0) To Crumb(5)(1), Crumb(6)(0) To Crumb(6)(1), Crumb(7)(0) To Crumb(7)(1), _
                     Crumb(8)(0) To Crumb(8)(1), Crumb(9)(0) To Crumb(9)(1), Crumb(10)(0) To Crumb(10)(1), Crumb(11)(0) To Crumb(11)(1), _
                     Crumb(12)(0) To Crumb(12)(1), Crumb(13)(0) To Crumb(13)(1), Crumb(14)(0) To Crumb(14)(1), Crumb(15)(0) To Crumb(15)(1), _
                     Crumb(16)(0) To Crumb(16)(1))
    Case 17
        ReDim result(Crumb(0)(0) To Crumb(0)(1), Crumb(1)(0) To Crumb(1)(1), Crumb(2)(0) To Crumb(2)(1), Crumb(3)(0) To Crumb(3)(1), _
                     Crumb(4)(0) To Crumb(4)(1), Crumb(5)(0) To Crumb(5)(1), Crumb(6)(0) To Crumb(6)(1), Crumb(7)(0) To Crumb(7)(1), _
                     Crumb(8)(0) To Crumb(8)(1), Crumb(9)(0) To Crumb(9)(1), Crumb(10)(0) To Crumb(10)(1), Crumb(11)(0) To Crumb(11)(1), _
                     Crumb(12)(0) To Crumb(12)(1), Crumb(13)(0) To Crumb(13)(1), Crumb(14)(0) To Crumb(14)(1), Crumb(15)(0) To Crumb(15)(1), _
                     Crumb(16)(0) To Crumb(16)(1), Crumb(17)(0) To Crumb(17)(1))
    Case 18
        ReDim result(Crumb(0)(0) To Crumb(0)(1), Crumb(1)(0) To Crumb(1)(1), Crumb(2)(0) To Crumb(2)(1), Crumb(3)(0) To Crumb(3)(1), _
                     Crumb(4)(0) To Crumb(4)(1), Crumb(5)(0) To Crumb(5)(1), Crumb(6)(0) To Crumb(6)(1), Crumb(7)(0) To Crumb(7)(1), _
                     Crumb(8)(0) To Crumb(8)(1), Crumb(9)(0) To Crumb(9)(1), Crumb(10)(0) To Crumb(10)(1), Crumb(11)(0) To Crumb(11)(1), _
                     Crumb(12)(0) To Crumb(12)(1), Crumb(13)(0) To Crumb(13)(1), Crumb(14)(0) To Crumb(14)(1), Crumb(15)(0) To Crumb(15)(1), _
                     Crumb(16)(0) To Crumb(16)(1), Crumb(17)(0) To Crumb(17)(1), Crumb(18)(0) To Crumb(18)(1))
    Case 19
        ReDim result(Crumb(0)(0) To Crumb(0)(1), Crumb(1)(0) To Crumb(1)(1), Crumb(2)(0) To Crumb(2)(1), Crumb(3)(0) To Crumb(3)(1), _
                     Crumb(4)(0) To Crumb(4)(1), Crumb(5)(0) To Crumb(5)(1), Crumb(6)(0) To Crumb(6)(1), Crumb(7)(0) To Crumb(7)(1), _
                     Crumb(8)(0) To Crumb(8)(1), Crumb(9)(0) To Crumb(9)(1), Crumb(10)(0) To Crumb(10)(1), Crumb(11)(0) To Crumb(11)(1), _
                     Crumb(12)(0) To Crumb(12)(1), Crumb(13)(0) To Crumb(13)(1), Crumb(14)(0) To Crumb(14)(1), Crumb(15)(0) To Crumb(15)(1), _
                     Crumb(16)(0) To Crumb(16)(1), Crumb(17)(0) To Crumb(17)(1), Crumb(18)(0) To Crumb(18)(1), Crumb(19)(0) To Crumb(19)(1))
    Case 20
        ReDim result(Crumb(0)(0) To Crumb(0)(1), Crumb(1)(0) To Crumb(1)(1), Crumb(2)(0) To Crumb(2)(1), Crumb(3)(0) To Crumb(3)(1), _
                     Crumb(4)(0) To Crumb(4)(1), Crumb(5)(0) To Crumb(5)(1), Crumb(6)(0) To Crumb(6)(1), Crumb(7)(0) To Crumb(7)(1), _
                     Crumb(8)(0) To Crumb(8)(1), Crumb(9)(0) To Crumb(9)(1), Crumb(10)(0) To Crumb(10)(1), Crumb(11)(0) To Crumb(11)(1), _
                     Crumb(12)(0) To Crumb(12)(1), Crumb(13)(0) To Crumb(13)(1), Crumb(14)(0) To Crumb(14)(1), Crumb(15)(0) To Crumb(15)(1), _
                     Crumb(16)(0) To Crumb(16)(1), Crumb(17)(0) To Crumb(17)(1), Crumb(18)(0) To Crumb(18)(1), Crumb(19)(0) To Crumb(19)(1), _
                     Crumb(20)(0) To Crumb(20)(1))
    End Select
    CreateMultidimensionalArray = result
End Function

Attribute VB_Name = "iArray"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
'MIT License
'
'Copyright (c) 2019-2021 Petr Katerinak
'
'Permission is hereby granted, free of charge, to any person obtaining a copy
'of this software and associated documentation files (the "Software"), to deal
'in the Software without restriction, including without limitation the rights
'to use, copy, modify, merge, publish, distribute, sublicense, and/or sell
'copies of the Software, and to permit persons to whom the Software is
'furnished to do so, subject to the following conditions:
'
'The above copyright notice and this permission notice shall be included in all
'copies or substantial portions of the Software.
'
'THE SOFTWARE IS PROVIDED "AS IS", WITHOUT WARRANTY OF ANY KIND, EXPRESS OR
'IMPLIED, INCLUDING BUT NOT LIMITED TO THE WARRANTIES OF MERCHANTABILITY,
'FITNESS FOR A PARTICULAR PURPOSE AND NONINFRINGEMENT. IN NO EVENT SHALL THE
'AUTHORS OR COPYRIGHT HOLDERS BE LIABLE FOR ANY CLAIM, DAMAGES OR OTHER
'LIABILITY, WHETHER IN AN ACTION OF CONTRACT, TORT OR OTHERWISE, ARISING FROM,
'OUT OF OR IN CONNECTION WITH THE SOFTWARE OR THE USE OR OTHER DEALINGS IN THE
'SOFTWARE.
'
' Version of iArray: 1.0
''修正 元素從 0 開始


Private Const MISSING_LONG As Long = -9999
Private iArray As Collection
Private i As Long ' Counter

' #####################
' #    CONSTRUCTOR    #
' #####################
Private Sub Class_Initialize()
  Set iArray = New Collection
End Sub

' #####################
' #  Getter / Setter  #
' #####################
'Attribute Element.VB_UserMemId = 0 saved in both procedures

'@DefaultMember
Public Property Get element(ByVal index As Long) As Variant
Attribute element.VB_UserMemId = 0
    If index + 1 < 1 Or index + 1 > iArray.Count Then
        Set element = Nothing
        Exit Property
    End If
    If IsObject(iArray(index + 1)) = True Then
        Set element = iArray(index + 1)
    Else
        element = iArray(index + 1)
    End If
'    If VarType(iArray(index + 1)) = vbObject Then
'       Set element = iArray(index + 1)
'    ElseIf VarType(iArray(index + 1)) = vbVariant Then
'       Set element = iArray(index + 1)
'    ElseIf VarType(iArray(index + 1)) = vbArray Then
'       Set element = iArray(index + 1)
'    Else
'        element = iArray(index + 1)
'    End If
 
End Property

'@DefaultMember
Public Property Let element(ByVal index As Long, ByVal val As Variant)
Attribute element.VB_UserMemId = 0
  If index = 0 And iArray.Count = 0 Then
    Me.Push val
    Exit Property
  End If
  If index + 1 > iArray.Count Then
    Dim eMsg As String
    eMsg = IIf(iArray.Count > 0, _
               "Index (" & index + 1 & ") out of iArray bounds (1-" & iArray.Count & ")", _
               "iArray doesn't have any indexes")
    err.Raise Number:=9, Description:=eMsg
    Exit Property
  End If
  iArray.Add val, after:=index + 1
  iArray.Remove index + 1
End Property

' #############################
' # COMMON COLLECTION METHODS #
' #############################
Public Function Count() As Long
  Count = iArray.Count
End Function
Public Sub Add(ByVal val As Variant, Optional ByVal bef As Variant = Empty, Optional ByVal aft As Variant = Empty)
  If IsEmpty(bef) And IsEmpty(aft) Then
    iArray.Add val
  ElseIf IsEmpty(bef) Then
    iArray.Add val, , , aft
  ElseIf IsEmpty(aft) Then
    iArray.Add val, , bef
  Else
    iArray.Add val, , bef, aft
  End If
End Sub
Public Sub Remove(index As Long)
  iArray.Remove index + 1
End Sub

' ####################
' #  PUBLIC METHODS  #
' ####################

'AddAfter
' Adds element after given index.
' {1,2,3} -> index >= 3 -> Push val
' {1,2,3} -> index < 1 -> Unshift val
' {} -> index = any -> Push val
' @param Long index | Index after which will be added an element
' @param Variant val | One element (String, number, ...) to add into iArray
' @return Long | Count of elements inside iArray
Public Function AddAfter(ByVal index As Long, ByVal val As Variant) As Long
  If Me.Count < 1 Or index + 1 >= Me.Count Then
    Me.Push val
  ElseIf index + 1 < 1 Then
    Me.Unshift val
  Else
    Me.Add val, aft:=index + 1
  End If
  AddAfter = Me.Count
End Function

'AddArrayAfter
' Adds elements after given index.
' {1,2,3} -> index >= 3 -> PushArray val
' {1,2,3} -> index < 1 -> UnshiftArray val
' {} -> index = any -> PushArray val
' @param Long index | Index after which will be added an element
' @param Variant val | Array() or iArray of elements to add into iArray
' @return Long | Count of elements inside iArray
Public Function AddArrayAfter(ByVal index As Long, ByVal val As Variant) As Long
  If Me.Count < 1 Or index + 1 >= Me.Count Then
    Me.PushArray val
  ElseIf index + 1 < 1 Then
    Me.UnshiftArray val
  Else
    If TypeOf val Is iArray Then
      For i = 0 To val.Count - 1
        Me.Add val(i), aft:=index + 1
        Inc index
      Next i
    Else
      For i = LBound(val) To UBound(val)
        Me.Add val(i), aft:=index + 1
        Inc index
      Next i
    End If
  End If
  AddArrayAfter = Me.Count
End Function

'AddArrayBefore
' Adds elements before given index.
' {1,2,3} -> index > 3 -> PushArray val
' {1,2,3} -> index <= 1 -> UnshiftArray val
' {} -> index = any -> PushArray val
' @param Long index | Index after which will be added an element
' @param Variant val | Array() or iArray of elements to add into iArray
' @return Long | Count of elements inside iArray
Public Function AddArrayBefore(ByVal index As Long, ByVal val As Variant) As Long
  If Me.Count < 1 Or index + 1 > Me.Count Then
    Me.PushArray val
  ElseIf index <= 0 Then
    Me.UnshiftArray val
  Else
    If TypeOf val Is iArray Then
      For i = val.Count - 1 To 0 Step -1
        Me.Add val(i), bef:=index + 1
      Next i
    Else
      For i = UBound(val) To LBound(val) Step -1
        Me.Add val(i), bef:=index + 1
      Next i
    End If
  End If
  AddArrayBefore = Me.Count
End Function

'AddBefore
' Adds element before given index.
' {1,2,3} -> index > 3 -> Push val
' {1,2,3} -> index <= 1 -> Unshift val
' {} -> index = any -> Push val
' @param Long index | Index before which will be added an element
' @param Variant val | One element (String, number, ...) to add into iArray
' @return Long | Count of elements inside iArray
Public Function AddBefore(ByVal index As Long, ByVal val As Variant) As Long
  If Me.Count < 1 Or index + 1 > Me.Count Then
    Me.Push val
  ElseIf index + 1 <= 1 Then
    Me.Unshift val
  Else
    Me.Add val, bef:=index + 1
  End If
  AddBefore = Me.Count
End Function

'Avg
' Calculates the average of the numeric iArray.
' @return Variant | Average value / "NaN" if iArray contains non-numeric value(s)
Public Function Avg() As Variant
  If Not Me.ContainsOnlyNumeric Then Avg = "NaN": Exit Function
  Avg = Me.sum / Me.Count
End Function

'Clear
' Empties iArray
Public Function Clear() As Boolean
  For i = iArray.Count - 1 To 0 Step -1
    iArray.Remove i + 1
  Next i
  Clear = IIf(iArray.Count = 0, True, False)
End Function

'Clone
' Makes a hard copy of the iArray
' @return iArray | Return exact copy of itself
Public Function clone() As iArray
  Set clone = New iArray
  For i = 0 To Me.Count - 1
    clone.Push Me(i)
  Next i
End Function

'Contains
' Checks if given value is used inside iArray.
' @param Variant val | One element (String, number, ...) to by checked if it exists in iArray
' $return Boolean | True = exists, False = doesn't exists
Public Function Contains(ByVal val As Variant) As Boolean
  Contains = False
  Dim el As Variant
  For Each el In iArray
    If IsObject(val) = True Or VarType(val) And 8192 Then
        If (VarType(el) And 8192) And (VarType(val) And 8192) Then
            If ArrayDifference(el, val) Then
                Contains = True: Exit Function
            End If
        ElseIf IsObject(el) = True And IsObject(val) = True Then
            If el Is val Then
                Contains = True: Exit Function
            End If
        End If
    Else
        If IsObject(el) = False And (VarType(el) And 8192) <> 8192 Then
            If el = val Then
            Contains = True: Exit Function
            End If
        End If
    End If
  Next el
End Function

'ContainsAll
' Checks if all given values are used inside iArray.
' @param Variant val | values to by checked if it exists in iArray
' $return Boolean | True = all exists, False = one ore more values doesn't exists
Public Function ContainsAll(ByVal val As Variant) As Boolean
  ContainsAll = False
  Dim foundOccurrences As Integer: foundOccurrences = 0
  Dim values As New iArray
  If Not TypeOf val Is iArray Then
    If IsArray(val) Then
      values.PushArray (val)
    Else
      values.Push (val)
    End If
  Else
    Set values = val
  End If
  For i = 0 To values.Count - 1
    If Me.Contains(values(i)) Then Inc foundOccurrences
  Next i
  If foundOccurrences = values.Count Then ContainsAll = True
End Function

'CountOccurrences
' Checks how many times is given value used inside iArray.
' @param Variant val | One element (String, number, ...) to by checked
' @return Long | Count of matched occurrences
Public Function CountOccurrences(val As Variant) As Long
  CountOccurrences = 0
  Dim el As Variant
  For Each el In iArray
  
    If IsObject(val) = True Or VarType(val) And 8192 Then
        If VarType(el) And 8192 And VarType(val) And 8192 Then
            If ArrayDifference(el, val) Then
                Inc CountOccurrences
                Exit Function
            End If
        ElseIf IsObject(el) = True And IsObject(val) = True Then
            If el Is val Then
                Inc CountOccurrences
                Exit Function
            End If
        End If
    Else
        If IsObject(el) = False And Not (VarType(el) And 8192) Then
            If el = val Then
                Inc CountOccurrences
                Exit Function
            End If
        End If
    End If
  
     'If el = val Then Inc CountOccurrences
  Next el
End Function

'Dequeue
' Removes an element from the begining of the iArray.
' @return Variant | Removed element or Empty, if iArray is empty
'刪除開頭一個元素。
Public Function Dequeue() As Variant
  Dequeue = Empty
  If iArray.Count > 0 Then
    If VarType(Me(0)) = vbString Then
        Dequeue = Me(0)
    ElseIf TypeOf Me(0) Is iArray Then
        Set Dequeue = Me(0)
    ElseIf VarType(Me(0)) = vbArray Then
        Set Dequeue = Me(0)
    ElseIf VarType(Me(0)) = vbObject Then
        Set Dequeue = Me(0)
    Else
        Dequeue = Me(0)
    End If
    
    iArray.Remove 1
  End If
End Function

'Difference
' Checks for number of differences between two arrays, what was added/deleted or combination.
' @param iArray oldArray | Old iArray to be compared with current iArray
' @param String retType | �dd= deleted from old iArray, �aa= added in current iArray, �cc= combination of both (default)
' @return iArray | iArray with differences found
Public Function Difference(ByRef oldArray As iArray, Optional ByVal retType As String = "c") As iArray
  Set Difference = New iArray
  Select Case LCase(retType)
    Case "d"
      For i = 0 To oldArray.Count - 1
        If Me.Contains(oldArray(i)) = False Then Difference.Push oldArray(i)
      Next i
    Case "a"
      For i = 0 To Count - 1
        If oldArray.Contains(Me(i)) = False Then Difference.Push Me(i)
      Next i
    Case "c"
      For i = 0 To oldArray.Count - 1
        If Me.Contains(oldArray(i)) = False Then Difference.Push oldArray(i)
      Next i
      For i = 0 To Count - 1
        If oldArray.Contains(Me(i)) = False Then Difference.Push Me(i)
      Next i
    Case Else
      err.Raise Number:=5, Description:="Unknown Difference return type attribute:" & vbCrLf & _
                                        "Allowed are 'A'dded/'D'eleted/'C'ombination of both"
  End Select
End Function

'DropLeft
' Remove n elements from the beginning of the iArray. If n > count of iArray elements, all elements are removed.
' @param Long n | Number of elements to be removed
' @return iArray | Array of the removed elements
Public Function DropLeft(ByRef N As Long) As iArray
  Set DropLeft = New iArray
  If N > Me.Count Then N = Me.Count
  For i = 0 To N - 1
    DropLeft.Push Me(i)
  Next i
  For i = N - 1 To 0 Step -1
    Me.Remove (i)
  Next i
End Function

'DropRight
' Remove n elements from the end of the iArray. If n > count of iArray elements, all elements are removed.
' @param Long n | Number of elements to be removed
' @return iArray | Array of the removed elements
Public Function DropRight(ByRef N As Long) As iArray
  Set DropRight = New iArray
  If N > Me.Count Then N = Me.Count
  For i = Me.Count - N To Me.Count - 1
    DropRight.Push Me(i)
  Next i
  For i = Me.Count - 1 To Me.Count - N Step -1
    Me.Remove (i)
  Next i
End Function

'Enqueue
' Adds an element at the end of the iArray.
' @param Variant val | One element (String, number, ...) to add into iArray
' @return Long | Count of elements inside iArray
Public Function Enqueue(ByVal val As Variant) As Long
  Enqueue = Push(val)
End Function

'EnqueueArray
' Adds elements at the end of the iArray
' @param Variant val | Array() or iArray of elements to add into iArray
' @return Long | Count of elements inside array
Public Function EnqueueArray(ByVal val As Variant) As Long
  EnqueueArray = PushArray(val)
End Function

'First
' Returns value of the first element of the iArray.
' @return Variant | Value of the first element or Empty if iArray is Empty
Public Function First() As Variant
  Set First = IIf(Me.Count > 0, Me(0), Empty)
End Function

'Head
' Returns all elements of iArray, except last one.
' @return iArray | Copy of original array, without last element
Public Function head() As iArray
  Set head = Me.clone
  head.Pop
End Function

'Intersect
' Search for element that exists in both iArrays.
' @param iArray intArray | iArray to be intersected with current iArray
' @return iArray | Intersected values
Public Function Intersect(ByRef intersectedArr As iArray) As iArray
  Set Intersect = New iArray
  Dim el As Variant
  For Each el In iArray
    If intersectedArr.Contains(el) Then
      If Not Intersect.Contains(el) Then Intersect.Push (el)
    End If
  Next el
End Function

'ContainsOnlyNumeric
' Verify that all elements are numbers or convertable to numbers
' $return Boolean | True = contains only numeric values, False = contains inconvertible values
Public Function ContainsOnlyNumeric() As Boolean
  ContainsOnlyNumeric = True
  Dim el As Variant
  For Each el In iArray
    If Not IsNumeric(el) Then ContainsOnlyNumeric = False: Exit Function
  Next el
End Function

'Join
' Joins two iArrays.
' @param iArray jArray | iArray to be joined with current iArray
' @return iArray | Joined iArray
Public Function Join(ByRef joinArr As iArray) As iArray
  Set Join = New iArray
  Join.PushArray Me
  Join.PushArray joinArr
End Function

'Last
' Returns value of the last element of the iArray.
' @return Variant | Value of the last element or Empty if iArray is Empty
Public Function Last() As Variant
  Set Last = IIf(Me.Count > 0, Me(Me.Count - 1), Empty)
End Function

'OccurrenceIndexes
' Returns all indexes of a value in iArray.
' @return iArray | iArray containing indexes of occurrence
Public Function OccurenceIndexes(val As Variant) As iArray
  Set OccurenceIndexes = New iArray
  For i = 0 To Me.Count - 1
    If Me(i) = val Then
        OccurenceIndexes.Push (i)
    End If
  Next i
End Function

'Pop
' Removes an element from the end of the iArray.
' @return Variant | Removed element or Empty, if iArray is empty
Public Function Pop() As Variant
  If iArray.Count > 0 Then
    If VarType(Me(iArray.Count - 1)) = vbObject Then
       Set Pop = Me(iArray.Count - 1)
    Else
        Pop = Me(iArray.Count - 1)
    End If
    iArray.Remove iArray.Count
  End If
End Function
  
  

'Push
' Adds an element at the end of the iArray.
' @param Variant val | One element (String, number, ...) to add into iArray
' @return Long | Count of elements inside iArray
Public Function Push(ByVal val As Variant) As Long
  iArray.Add val
  Push = iArray.Count
End Function

'PushArray
' Adds elements at the end of the iArray.
' @param Variant val | Array() or iArray of elements to add into iArray
' @return Long | Count of elements inside array
Public Function PushArray(ByVal val As Variant) As Long
  If TypeOf val Is iArray Then
    For i = 0 To val.Count - 1
      Me.Push val(i)
    Next i
  Else
    For i = LBound(val) To UBound(val)
      Me.Push val(i)
    Next i
  End If
  PushArray = Me.Count
End Function

'RemoveDuplicates
' Keeps only the first occurrence of the value. Affects original array
' @return Long | Count of the removed elements
Public Function RemoveDuplicates() As Long
  RemoveDuplicates = 0
  For i = Me.Count - 1 To 0 Step -1
    If Me.CountOccurrences(Me(i)) > 1 Then
      Me.Remove i
      Inc RemoveDuplicates
    End If
  Next i
End Function

'Reverse
' Reverses the content of the iArray
' @return iArray | Reversed iArray
Public Function Reverse() As iArray
  Set Reverse = New iArray
  For i = 0 To Me.Count - 1
    Reverse.Unshift Me(i)
  Next i
End Function

'Shift
' Removes an element from the begining of the iArray.
' @return Variant | Removed element or Empty, if iArray is empty
'轉移
' 從 iArray 的開頭刪除一個元素。
' @返回第一個元素 | 如果 iArray 為空，則刪除元素或為空
Public Function shift() As Variant
  shift = Empty
  If iArray.Count > 0 Then
    If VarType(Me(0)) = vbString Then
        shift = Me(0)
    ElseIf TypeOf Me(0) Is iArray Then
        Set shift = Me(0)
    ElseIf VarType(Me(0)) = vbArray Then
        Set shift = Me(0)
    ElseIf VarType(Me(0)) = vbObject Then
        Set shift = Me(0)
    Else
        shift = Me(0)
    End If
    
    iArray.Remove 1
  End If
End Function

'Shuffle
' Randomly mixes content of the iArray
' @return iArray | Shuffled iArray
' 隨機播放
' 隨機混合 iArray 的內容
'@return iArray | 打亂iArray
Public Function Shuffle() As iArray
  Set Shuffle = New iArray
  Dim keys As New iArray
  For i = 0 To Me.Count - 1
    keys.Push (i)
  Next i
  Dim rndNo As Long
  Do While keys.Count > 0
    rndNo = randomFromTo(0, keys.Count - 1)
    Shuffle.Push Me(keys(rndNo))
    keys.Remove (rndNo)
  Loop
End Function

'Sum
' Calculates the sum of the numeric iArray.
' @return Variant | Sum value / "NaN" if iArray contains non-numeric value(s)
Public Function sum() As Variant
  If Not Me.ContainsOnlyNumeric Then sum = "NaN": Exit Function
  sum = 0
  Dim el As Variant
  For Each el In iArray
    sum = sum + el
  Next el
End Function

'Tail
' Returns all elements of iArray, except first one.
' @return iArray | Copy of original array, without first element
'返回陣列中除了第一個元素的剩余元素陣列
Public Function Tail() As iArray
  Set Tail = Me.clone
  Tail.Dequeue
End Function

Public Function ToList()
  If Me.Count = 0 Then ToList = Null: Exit Function
  Dim tarr()
  ReDim tarr(Me.Count - 1)
  For i = 0 To Me.Count - 1
    If VarType(Me(i)) = vbString Then
        tarr(i) = Me(i)
    ElseIf TypeOf Me(i) Is iArray Then
        Set tarr(i) = Me(i)
    ElseIf VarType(Me(i)) = vbObject Then
        Set tarr(i) = Me(i)
    Else
        tarr(i) = Me(i)
    End If
  Next i
  ToList = tarr
End Function

'ToString
' Creates string representation of the iArray.
' @param String delimiter | Optional character to separate the iArray's elements (default = " ")
' @return String | Formated representation of tha iArray
Public Function ToString(Optional ByVal delimiter As String = " ") As String
  If Me.Count = 0 Then ToString = "{}": Exit Function
  ToString = vbNullString
  For i = 0 To Me.Count - 1
    If i = 0 Then ToString = ToString + "{"
    If i > 0 Then ToString = ToString + delimiter
    If VarType(Me(i)) = vbString Then
        ToString = ToString + Chr$(34)
        ToString = ToString + CStr(Me(i))
        ToString = ToString + Chr$(34)
    ElseIf TypeOf Me(i) Is iArray Then
        ToString = ToString + Me(i).ToString(delimiter)
    ElseIf (VarType(Me(i)) And vbArray) = vbArray Then
        ToString = ToString + "[Array]"
    ElseIf VarType(Me(i)) = vbObject Then
        ToString = ToString + "[Object]"
    Else
        ToString = ToString + CStr(Me(i))
    End If
    
    If i = iArray.Count - 1 Then ToString = ToString + "}"
  Next i
End Function

'Union
' Combines both iArrays and removes duplicities
' @param iArray uArray | iArray to be unioned with current iArray
' @return iArray | Combined values without duplicities
Public Function Union(ByRef uArr As iArray) As iArray
  Set Union = Me.clone
  Union.PushArray uArr
  Union.RemoveDuplicates
End Function

'Unique
' Returns copy of iArray without duplicated values. Original array is not affected
' @return iArray | iArray with unique values
Public Function Unique() As iArray
  Set Unique = New iArray
  Dim el As Variant
  For Each el In iArray
    If Not Unique.Contains(el) Then Unique.Push (el)
  Next el
End Function

'Unshift
' Add an element at the begining of the iArray.
' @param Variant val | One element (String, number, ...) to add into iArray
' @return Long | Count of elements inside iArray
Public Function Unshift(ByVal val As Variant) As Long
  If iArray.Count = 0 Then
    Unshift = Push(val)
  Else
    iArray.Add val, before:=1
    Unshift = iArray.Count
  End If
End Function

'UnshiftArray
' Add elements at the begining of the iArray.
' @param Variant val | Array() or iArray of elements to add into iArray
' @return Long | Count of elements inside iArray
Public Function UnshiftArray(ByVal val As Variant) As Long
  If TypeOf val Is iArray Then
    For i = val.Count - 1 To 0 Step -1
      Unshift val(i)
    Next i
  Else
    For i = UBound(val) To LBound(val) Step -1
      Unshift val(i)
    Next i
  End If
  UnshiftArray = iArray.Count
End Function


' #####################
' # PRIVATE FUNCTIONS #
' #####################
Sub Inc(ByRef i)
   i = i + 1
End Sub

'Private Function rangeToArray(ByVal rng As Range) As Variant
'  rangeToArray = rng.Value
'End Function

Private Function randomFromTo(ByVal from As Long, ByVal upTo As Long) As Long
  Randomize
  randomFromTo = Int(from + Rnd() * (upTo - from + 1))
End Function

'比對 兩個陣列是否一樣
Private Function ArrayDifference(arr1 As Variant, arr2 As Variant) As Boolean

    Dim i As Integer
    If UBound(arr1) = UBound(arr2) Then
        For i = 0 To UBound(arr1)
            If arr1(i) = arr2(i) Then
                ArrayDifference = True
            Else
                ArrayDifference = False
                Exit Function
            End If
        Next
    Else
        ArrayDifference = False
    End If

End Function

'@Description("Returns a new array containing the portion of the stored array between the StartIndex and EndIndex")
Public Function Slice( _
        ByVal StartIndex As Long, _
        Optional ByVal EndIndex As Long = MISSING_LONG _
    ) As Variant()
    Dim LocalLength As Long
    Dim RelativeStart As Long
    Dim RelativeEnd As Long
    Dim OldIndex As Long
    Dim Final As Long
    Dim Count As Long
    Dim NewIndex As Long
    Dim LocalItems() As Variant
    Dim result() As Variant
    
    LocalItems = InternalItems
    LocalLength = This.Length
    RelativeStart = StartIndex
    If RelativeStart < LBound(LocalItems) Then
        If RelativeStart < 0 Then
            OldIndex = max((LocalLength + RelativeStart), LBound(LocalItems))
        Else
            OldIndex = max((LocalLength - RelativeStart), LBound(LocalItems))
        End If
    Else
        OldIndex = min(RelativeStart, LocalLength)
    End If
    If EndIndex = MISSING_LONG Then
        RelativeEnd = LocalLength + LBound(LocalItems)
    Else
        RelativeEnd = EndIndex
    End If
    If RelativeEnd < LBound(LocalItems) Then
        Final = max((LocalLength + RelativeEnd), LBound(LocalItems))
    Else
        Final = min(RelativeEnd, LocalLength + LBound(LocalItems))
    End If
    
    NewIndex = LBound(LocalItems)
    Count = max(Final - OldIndex, 0) + LBound(LocalItems)
    If Count > NewIndex Then
        ReDim result(NewIndex To Count - 1)
        Do While OldIndex < Final
            If OldIndex >= LBound(LocalItems) And OldIndex <= UBound(LocalItems) Then
                LetOrSetElement result(NewIndex), LocalItems(OldIndex)
                Inc NewIndex
                Inc OldIndex
            End If
        Loop
        If This.ArrayType = BA_MULTIDIMENSION Then
            Slice = JaggedToMulti(result)
        Else
            Slice = result
        End If
    End If
    
End Function


'@Description("changes the contents of the array by removing or replacing existing elements and/or adding new elements in place.")
Public Function Splice( _
        ByVal StartIndex As Long, _
        ParamArray Args() As Variant _
    ) As Variant()
    'Dim LocalItems() As Variant
    Dim ActualStart As Long
    Dim ActualDeleteCount As Long
    Dim ArgsCount As Long
    Dim LocalLength As Long
    Dim LocalArgs() As Variant
    Dim result() As Variant
    Dim i As Long
    Dim TempArray() As Variant
    Dim ItemCount As Long
    Dim TempItems() As Variant
    
    LocalArgs = Args
    'LocalItems = mainArray
    LocalLength = Me.Count
    If StartIndex < LocalLength Then
        ActualStart = StartIndex
    Else
        ActualStart = min(StartIndex, LocalLength)
    End If
    
    ArgsCount = UBound(LocalArgs) + 1
    If ArgsCount = 0 Then
        ' only a start index has been supplied
        ' we're gonna delete everything
        ' 僅提供了起始索引
         '我們要刪除所有內容
        ItemCount = 0
        ActualDeleteCount = LocalLength - ActualStart
    Else
        ' first arg in args is delete count, second onwards are insertion items
        ' args 中的第一個參數是刪除計數，第二個之後是插入項
        ItemCount = ArgsCount - 1
        'deleteCount is first element in args.
        'deleteCount 是 args 中的第一個元素。
        ActualDeleteCount = min(max(Args(LBound(Args)), 0), LocalLength - ActualStart)
    End If
    

    ' get items to be deleted for return val
    ' 取得和刪除
    If ActualDeleteCount > 0 Then
        ReDim result(0 To ActualDeleteCount - 1)
        i = 0
        Do While i < ActualDeleteCount
            If IsObject(Me(ActualStart)) Then
                Set result(i) = Me(ActualStart)
                Me.Remove ActualStart
            Else
                result(i) = Me(ActualStart)
                Me.Remove ActualStart
            End If
            Inc i
        Loop
    Else
        ' return empty array if nothing to be deleted
        ReDim result(0)
    End If
    
    '取得要插入的陣列資料
    If ItemCount > 0 Then
        ReDim TempItems(0 To ItemCount - 1)
        For i = 0 To ItemCount - 1
            If IsObject(LocalArgs(i + 1)) Then
                Set TempItems(i) = LocalArgs(i + 1)
            Else
                TempItems(i) = LocalArgs(i + 1)
            End If
        Next
    Me.AddArrayBefore ActualStart, TempItems
    End If
    
    
    Splice = result
End Function

Attribute VB_Name = "iArrayEaszTemplateList"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
'MIT License
'
'Copyright (c) 2019-2021 Petr Katerinak
'
'Permission is hereby granted, free of charge, to any person obtaining a copy
'of this software and associated documentation files (the "Software"), to deal
'in the Software without restriction, including without limitation the rights
'to use, copy, modify, merge, publish, distribute, sublicense, and/or sell
'copies of the Software, and to permit persons to whom the Software is
'furnished to do so, subject to the following conditions:
'
'The above copyright notice and this permission notice shall be included in all
'copies or substantial portions of the Software.
'
'THE SOFTWARE IS PROVIDED "AS IS", WITHOUT WARRANTY OF ANY KIND, EXPRESS OR
'IMPLIED, INCLUDING BUT NOT LIMITED TO THE WARRANTIES OF MERCHANTABILITY,
'FITNESS FOR A PARTICULAR PURPOSE AND NONINFRINGEMENT. IN NO EVENT SHALL THE
'AUTHORS OR COPYRIGHT HOLDERS BE LIABLE FOR ANY CLAIM, DAMAGES OR OTHER
'LIABILITY, WHETHER IN AN ACTION OF CONTRACT, TORT OR OTHERWISE, ARISING FROM,
'OUT OF OR IN CONNECTION WITH THE SOFTWARE OR THE USE OR OTHER DEALINGS IN THE
'SOFTWARE.
'
' Version of iArray: 1.0
''修正 元素從 0 開始

Private mainArray As New Collection
Private i As Long ' Counter

' #####################
' #    CONSTRUCTOR    #
' #####################
'Private Sub Class_Initialize()
'  Set mainArray = New Collection
'End Sub

' #####################
' #  Getter / Setter  #
' #####################
'Attribute Element.VB_UserMemId = 0 saved in both procedures

'@DefaultMember
Public Property Get element(ByVal index As Long) As iTemplate
Attribute element.VB_UserMemId = 0
    If index + 1 < 1 Or index + 1 > mainArray.Count Then
        Set element = Nothing
        Exit Property
    End If
    If IsObject(mainArray(index + 1)) = True Then
        Set element = mainArray(index + 1)
    Else
        element = mainArray(index + 1)
    End If

 
End Property

'@DefaultMember
Public Property Let element(ByVal index As Long, ByVal val As iTemplate)
Attribute element.VB_UserMemId = 0
  If index = 0 And mainArray.Count = 0 Then
    Me.Push val
    Exit Property
  End If
  If index + 1 > mainArray.Count Then
    Dim eMsg As String
    eMsg = IIf(mainArray.Count > 0, _
               "Index (" & index + 1 & ") out of iArray bounds (1-" & mainArray.Count & ")", _
               "iArray doesn't have any indexes")
    err.Raise Number:=9, Description:=eMsg
    Exit Property
  End If
  mainArray.Add val, after:=index + 1
  mainArray.Remove index + 1
End Property

' #############################
' # COMMON COLLECTION METHODS #
' #############################
Public Function Count() As Long
  Count = mainArray.Count
End Function
Public Sub Add(ByVal val As iTemplate, Optional ByVal bef As Variant = Empty, Optional ByVal aft As Variant = Empty)
  If IsEmpty(bef) And IsEmpty(aft) Then
    mainArray.Add val
  ElseIf IsEmpty(bef) Then
    mainArray.Add val, , , aft
  ElseIf IsEmpty(aft) Then
    mainArray.Add val, , bef
  Else
    mainArray.Add val, , bef, aft
  End If
End Sub
Public Sub Remove(index As Long)
  mainArray.Remove index + 1
End Sub

' ####################
' #  PUBLIC METHODS  #
' ####################

'AddAfter
' Adds element after given index.
' {1,2,3} -> index >= 3 -> Push val
' {1,2,3} -> index < 1 -> Unshift val
' {} -> index = any -> Push val
' @param Long index | Index after which will be added an element
' @param Variant val | One element (String, number, ...) to add into iArray
' @return Long | Count of elements inside iArray
Public Function AddAfter(ByVal index As Long, ByVal val As iTemplate) As Long
  If Me.Count < 1 Or index + 1 >= Me.Count Then
    Me.Push val
  ElseIf index + 1 < 1 Then
    Me.Unshift val
  Else
    Me.Add val, aft:=index + 1
  End If
  AddAfter = Me.Count
End Function

'AddArrayAfter
' Adds elements after given index.
' {1,2,3} -> index >= 3 -> PushArray val
' {1,2,3} -> index < 1 -> UnshiftArray val
' {} -> index = any -> PushArray val
' @param Long index | Index after which will be added an element
' @param Variant val | Array() or iArray of elements to add into iArray
' @return Long | Count of elements inside iArray
Public Function AddArrayAfter(ByVal index As Long, ByVal val As Variant) As Long
  If Me.Count < 1 Or index + 1 >= Me.Count Then
    Me.PushArray val
  ElseIf index + 1 < 1 Then
    Me.UnshiftArray val
  Else
    If TypeOf val Is iArrayTemplateList Then
      For i = 0 To val.Count - 1
        Me.Add val(i), aft:=index + 1
        Inc index
      Next i
    Else
      For i = LBound(val) To UBound(val)
        Me.Add val(i), aft:=index + 1
        Inc index
      Next i
    End If
  End If
  AddArrayAfter = Me.Count
End Function

'AddArrayBefore
' Adds elements before given index.
' {1,2,3} -> index > 3 -> PushArray val
' {1,2,3} -> index <= 1 -> UnshiftArray val
' {} -> index = any -> PushArray val
' @param Long index | Index after which will be added an element
' @param Variant val | Array() or iArray of elements to add into iArray
' @return Long | Count of elements inside iArray
Public Function AddArrayBefore(ByVal index As Long, ByVal val As Variant) As Long
  If Me.Count < 1 Or index + 1 > Me.Count Then
    Me.PushArray val
  ElseIf index <= 0 Then
    Me.UnshiftArray val
  Else
    If TypeOf val Is iArrayTemplateList Then
      For i = val.Count - 1 To 0 Step -1
        Me.Add val(i), bef:=index + 1
      Next i
    Else
      For i = UBound(val) To LBound(val) Step -1
        Me.Add val(i), bef:=index + 1
      Next i
    End If
  End If
  AddArrayBefore = Me.Count
End Function

'AddBefore
' Adds element before given index.
' {1,2,3} -> index > 3 -> Push val
' {1,2,3} -> index <= 1 -> Unshift val
' {} -> index = any -> Push val
' @param Long index | Index before which will be added an element
' @param Variant val | One element (String, number, ...) to add into iArray
' @return Long | Count of elements inside iArray
Public Function AddBefore(ByVal index As Long, ByVal val As iTemplate) As Long
  If Me.Count < 1 Or index + 1 > Me.Count Then
    Me.Push val
  ElseIf index + 1 <= 1 Then
    Me.Unshift val
  Else
    Me.Add val, bef:=index + 1
  End If
  AddBefore = Me.Count
End Function



'Clear
' Empties iArray
Public Function Clear() As Boolean
  For i = mainArray.Count - 1 To 0 Step -1
    mainArray.Remove i + 1
  Next i
  Clear = IIf(mainArray.Count = 0, True, False)
End Function

'Clone
' Makes a hard copy of the mainArray
' @return mainArray | Return exact copy of itself
Public Function clone() As iArrayTemplateList
  Set clone = New iArrayTemplateList
  For i = 0 To Me.Count - 1
    clone.Push Me(i)
  Next i
End Function

'Contains
' Checks if given value is used inside mainArray.
' @param Variant val | One element (String, number, ...) to by checked if it exists in iArray
' $return Boolean | True = exists, False = doesn't exists
Public Function Contains(ByVal val As iTemplate) As Boolean
  Contains = False
  Dim el As Variant
  For Each el In mainArray
    If IsObject(val) = True Or VarType(val) And 8192 Then
        If (VarType(el) And 8192) And (VarType(val) And 8192) Then
            If ArrayDifference(el, val) Then
                Contains = True: Exit Function
            End If
        ElseIf IsObject(el) = True And IsObject(val) = True Then
            If el Is val Then
                Contains = True: Exit Function
            End If
        End If
    Else
        If IsObject(el) = False And (VarType(el) And 8192) <> 8192 Then
            If el = val Then
            Contains = True: Exit Function
            End If
        End If
    End If
  Next el
End Function

'ContainsAll
' Checks if all given values are used inside mainArray.
' @param Variant val | values to by checked if it exists in iArray
' $return Boolean | True = all exists, False = one ore more values doesn't exists
Public Function ContainsAll(ByVal val As iArrayTemplateList) As Boolean
  ContainsAll = False
  Dim foundOccurrences As Integer: foundOccurrences = 0
  Dim values As New iArrayTemplateList
  If Not TypeOf val Is iArrayTemplateList Then
    If IsArray(val) Then
      values.PushArray (val)
    Else
      values.Push (val)
    End If
  Else
    Set values = val
  End If
  For i = 0 To values.Count - 1
    If Me.Contains(values(i)) Then Inc foundOccurrences
  Next i
  If foundOccurrences = values.Count Then ContainsAll = True
End Function


'Dequeue
' Removes an element from the begining of the mainArray.
' @return Variant | Removed element or Empty, if iArray is empty
'刪除開頭一個元素。
Public Function Dequeue() As iTemplate
  Dequeue = Empty
  If mainArray.Count > 0 Then
    If VarType(Me(0)) = vbString Then
        Dequeue = Me(0)
    ElseIf TypeOf Me(0) Is iArrayTemplateList Then
        Set Dequeue = Me(0)
    ElseIf VarType(Me(0)) = vbArray Then
        Set Dequeue = Me(0)
    ElseIf VarType(Me(0)) = vbObject Then
        Set Dequeue = Me(0)
    Else
        Dequeue = Me(0)
    End If
    
    mainArray.Remove 1
  End If
End Function

'Difference
' Checks for number of differences between two arrays, what was added/deleted or combination.
' @param iArray oldArray | Old iArray to be compared with current iArray
' @param String retType | �dd= deleted from old iArray, �aa= added in current iArray, �cc= combination of both (default)
' @return iArray | iArray with differences found
Public Function Difference(ByRef oldArray As iArrayTemplateList, Optional ByVal retType As String = "c") As iArrayTemplateList
  Set Difference = New iArrayTemplateList
  Select Case LCase(retType)
    Case "d"
      For i = 0 To oldArray.Count - 1
        If Me.Contains(oldArray(i)) = False Then Difference.Push oldArray(i)
      Next i
    Case "a"
      For i = 0 To Count - 1
        If oldArray.Contains(Me(i)) = False Then Difference.Push Me(i)
      Next i
    Case "c"
      For i = 0 To oldArray.Count - 1
        If Me.Contains(oldArray(i)) = False Then Difference.Push oldArray(i)
      Next i
      For i = 0 To Count - 1
        If oldArray.Contains(Me(i)) = False Then Difference.Push Me(i)
      Next i
    Case Else
      err.Raise Number:=5, Description:="Unknown Difference return type attribute:" & vbCrLf & _
                                        "Allowed are 'A'dded/'D'eleted/'C'ombination of both"
  End Select
End Function


'First
' Returns value of the first element of the mainArray.
' @return Variant | Value of the first element or Empty if iArray is Empty
Public Function First() As iTemplate
  Set First = IIf(Me.Count > 0, Me(0), Empty)
End Function

'Head
' Returns all elements of iArray, except last one.
' @return iArray | Copy of original array, without last element
Public Function head() As iArrayTemplateList
  Set head = Me.clone
  head.Pop
End Function

'Intersect
' Search for element that exists in both iArrays.
' @param iArray intArray | iArray to be intersected with current iArray
' @return iArray | Intersected values
Public Function Intersect(ByRef intersectedArr As iArrayTemplateList) As iArrayTemplateList
  Set Intersect = New iArrayTemplateList
  Dim el As Variant
  For Each el In mainArray
    If intersectedArr.Contains(el) Then
      If Not Intersect.Contains(el) Then Intersect.Push (el)
    End If
  Next el
End Function

'ContainsOnlyNumeric
' Verify that all elements are numbers or convertable to numbers
' $return Boolean | True = contains only numeric values, False = contains inconvertible values
Public Function ContainsOnlyNumeric() As Boolean
  ContainsOnlyNumeric = True
  Dim el As Variant
  For Each el In mainArray
    If Not IsNumeric(el) Then ContainsOnlyNumeric = False: Exit Function
  Next el
End Function

'Join
' Joins two iArrays.
' @param iArray jArray | iArray to be joined with current iArray
' @return iArray | Joined iArray
Public Function Join(ByRef joinArr As iArrayTemplateList) As iArrayTemplateList
  Set Join = New iArrayTemplateList
  Join.PushArray Me
  Join.PushArray joinArr
End Function

'Last
' Returns value of the last element of the mainArray.
' @return Variant | Value of the last element or Empty if iArray is Empty
Public Function Last() As iTemplate
  Set Last = IIf(Me.Count > 0, Me(Me.Count - 1), Empty)
End Function


'Pop
' Removes an element from the end of the mainArray.
' @return Variant | Removed element or Empty, if iArray is empty
Public Function Pop() As iTemplate
  If mainArray.Count > 0 Then
    If VarType(Me(mainArray.Count - 1)) = vbObject Then
       Set Pop = Me(mainArray.Count - 1)
    Else
        Pop = Me(mainArray.Count - 1)
    End If
    mainArray.Remove mainArray.Count
  End If
End Function
  
  

'Push
' Adds an element at the end of the mainArray.
' @param Variant val | One element (String, number, ...) to add into iArray
' @return Long | Count of elements inside iArray
Public Function Push(ByVal val As iTemplate) As Long
  mainArray.Add val
  Push = mainArray.Count
End Function

'PushArray
' Adds elements at the end of the mainArray.
' @param Variant val | Array() or iArray of elements to add into iArray
' @return Long | Count of elements inside array
Public Function PushArray(ByVal val As Variant) As Long
  If TypeOf val Is iArrayTemplateList Then
    For i = 0 To val.Count - 1
      Me.Push val(i)
    Next i
  Else
    For i = LBound(val) To UBound(val)
      Me.Push val(i)
    Next i
  End If
  PushArray = Me.Count
End Function


'Reverse
' Reverses the content of the iArray
' @return iArray | Reversed iArray
Public Function Reverse() As iArrayTemplateList
  Set Reverse = New iArrayTemplateList
  For i = 0 To Me.Count - 1
    Reverse.Unshift Me(i)
  Next i
End Function

'Shift
' Removes an element from the begining of the mainArray.
' @return Variant | Removed element or Empty, if iArray is empty
'轉移
' 從 iArray 的開頭刪除一個元素。
' @返回第一個元素 | 如果 iArray 為空，則刪除元素或為空
Public Function shift() As iTemplate
  shift = Empty
  If mainArray.Count > 0 Then
    If VarType(Me(0)) = vbString Then
        shift = Me(0)
    ElseIf TypeOf Me(0) Is iArrayTemplateList Then
        Set shift = Me(0)
    ElseIf VarType(Me(0)) = vbArray Then
        Set shift = Me(0)
    ElseIf VarType(Me(0)) = vbObject Then
        Set shift = Me(0)
    Else
        shift = Me(0)
    End If
    
    mainArray.Remove 1
  End If
End Function

'Shuffle
' Randomly mixes content of the iArray
' @return iArray | Shuffled iArray
' 隨機播放
' 隨機混合 iArray 的內容
'@return iArray | 打亂iArray
Public Function Shuffle() As iArrayTemplateList
  Set Shuffle = New iArrayTemplateList
  Dim keys As New iArrayTemplateList
  For i = 0 To Me.Count - 1
    keys.Push (i)
  Next i
  Dim rndNo As Long
  Do While keys.Count > 0
    rndNo = randomFromTo(0, keys.Count - 1)
    Shuffle.Push Me(keys(rndNo))
    keys.Remove (rndNo)
  Loop
End Function



'Tail
' Returns all elements of iArray, except first one.
' @return iArray | Copy of original array, without first element
'返回陣列中除了第一個元素的剩余元素陣列
Public Function Tail() As iArrayTemplateList
  Set Tail = Me.clone
  Tail.Dequeue
End Function

Public Function ToList()
  If Me.Count = 0 Then ToList = Null: Exit Function
  Dim tarr()
  ReDim tarr(Me.Count - 1)
  For i = 0 To Me.Count - 1
    If VarType(Me(i)) = vbString Then
        tarr(i) = Me(i)
    ElseIf TypeOf Me(i) Is iArrayTemplateList Then
        Set tarr(i) = Me(i)
    ElseIf VarType(Me(i)) = vbObject Then
        Set tarr(i) = Me(i)
    Else
        tarr(i) = Me(i)
    End If
  Next i
  ToList = tarr
End Function

'ToString
' Creates string representation of the mainArray.
' @param String delimiter | Optional character to separate the iArray's elements (default = " ")
' @return String | Formated representation of tha iArray
Public Function ToString(Optional ByVal delimiter As String = " ") As String
  If Me.Count = 0 Then ToString = "{}": Exit Function
  ToString = vbNullString
  For i = 0 To Me.Count - 1
    If i = 0 Then ToString = ToString + "{"
    If i > 0 Then ToString = ToString + delimiter
    If VarType(Me(i)) = vbString Then
        ToString = ToString + Chr$(34)
        ToString = ToString + CStr(Me(i))
        ToString = ToString + Chr$(34)
    ElseIf TypeOf Me(i) Is iArrayTemplateList Then
        ToString = ToString + Me(i).ToString(delimiter)
    ElseIf (VarType(Me(i)) And vbArray) = vbArray Then
        ToString = ToString + "[Array]"
    ElseIf VarType(Me(i)) = vbObject Then
        ToString = ToString + "[Object]"
    Else
        ToString = ToString + CStr(Me(i))
    End If
    
    If i = mainArray.Count - 1 Then ToString = ToString + "}"
  Next i
End Function

'Union
' Combines both iArrays and removes duplicities
' @param iArray uArray | iArray to be unioned with current iArray
' @return iArray | Combined values without duplicities
Public Function Union(ByRef uArr As iArrayTemplateList) As iArrayTemplateList
  Set Union = Me.clone
  Union.PushArray uArr
  Union.RemoveDuplicates
End Function

'Unique
' Returns copy of iArray without duplicated values. Original array is not affected
' @return iArray | iArray with unique values
Public Function Unique() As iArrayTemplateList
  Set Unique = New iArrayTemplateList
  Dim el As Variant
  For Each el In mainArray
    If Not Unique.Contains(el) Then Unique.Push (el)
  Next el
End Function

'Unshift
' Add an element at the begining of the mainArray.
' @param Variant val | One element (String, number, ...) to add into iArray
' @return Long | Count of elements inside iArray
Public Function Unshift(ByVal val As Variant) As Long
  If mainArray.Count = 0 Then
    Unshift = Push(val)
  Else
    mainArray.Add val, before:=1
    Unshift = mainArray.Count
  End If
End Function




' #####################
' # PRIVATE FUNCTIONS #
' #####################
Sub Inc(ByRef i)
   i = i + 1
End Sub



'比對 兩個陣列是否一樣
Private Function ArrayDifference(arr1 As Variant, arr2 As Variant) As Boolean

    Dim i As Integer
    If UBound(arr1) = UBound(arr2) Then
        For i = 0 To UBound(arr1)
            If arr1(i) = arr2(i) Then
                ArrayDifference = True
            Else
                ArrayDifference = False
                Exit Function
            End If
        Next
    Else
        ArrayDifference = False
    End If

End Function

'@Description("changes the contents of the array by removing or replacing existing elements and/or adding new elements in place.")
Public Function Splice( _
        ByVal StartIndex As Long, _
        ParamArray Args() As Variant _
    ) As Variant()
    'Dim LocalItems() As Variant
    Dim ActualStart As Long
    Dim ActualDeleteCount As Long
    Dim ArgsCount As Long
    Dim LocalLength As Long
    Dim LocalArgs() As Variant
    Dim result() As Variant
    Dim i As Long
    Dim TempArray() As Variant
    Dim ItemCount As Long
    Dim TempItems() As Variant
    
    LocalArgs = Args
    'LocalItems = mainArray
    LocalLength = Me.Count
    If StartIndex < LocalLength Then
        ActualStart = StartIndex
    Else
        ActualStart = min(StartIndex, LocalLength)
    End If
    
    ArgsCount = UBound(LocalArgs) + 1
    If ArgsCount = 0 Then
        ' only a start index has been supplied
        ' we're gonna delete everything
        ' 僅提供了起始索引
         '我們要刪除所有內容
        ItemCount = 0
        ActualDeleteCount = LocalLength - ActualStart
    Else
        ' first arg in args is delete count, second onwards are insertion items
        ' args 中的第一個參數是刪除計數，第二個之後是插入項
        ItemCount = ArgsCount - 1
        'deleteCount is first element in args.
        'deleteCount 是 args 中的第一個元素。
        ActualDeleteCount = min(max(Args(LBound(Args)), 0), LocalLength - ActualStart)
    End If
    

    ' get items to be deleted for return val
    ' 取得和刪除
    If ActualDeleteCount > 0 Then
        ReDim result(0 To ActualDeleteCount - 1)
        i = 0
        Do While i < ActualDeleteCount
            If IsObject(Me(ActualStart)) Then
                Set result(i) = Me(ActualStart)
                Me.Remove ActualStart
            Else
                result(i) = Me(ActualStart)
                Me.Remove ActualStart
            End If
            Inc i
        Loop
    Else
        ' return empty array if nothing to be deleted
        ReDim result(0)
    End If
    
    '取得要插入的陣列資料
    If ItemCount > 0 Then
        ReDim TempItems(0 To ItemCount - 1)
        For i = 0 To ItemCount - 1
            If IsObject(LocalArgs(i + 1)) Then
                Set TempItems(i) = LocalArgs(i + 1)
            Else
                TempItems(i) = LocalArgs(i + 1)
            End If
        Next
    Me.AddArrayBefore ActualStart, TempItems
    End If
    
    
    Splice = result
End Function

Attribute VB_Name = "iArrayTemplateList"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
'MIT License
'
'Copyright (c) 2019-2021 Petr Katerinak
'
'Permission is hereby granted, free of charge, to any person obtaining a copy
'of this software and associated documentation files (the "Software"), to deal
'in the Software without restriction, including without limitation the rights
'to use, copy, modify, merge, publish, distribute, sublicense, and/or sell
'copies of the Software, and to permit persons to whom the Software is
'furnished to do so, subject to the following conditions:
'
'The above copyright notice and this permission notice shall be included in all
'copies or substantial portions of the Software.
'
'THE SOFTWARE IS PROVIDED "AS IS", WITHOUT WARRANTY OF ANY KIND, EXPRESS OR
'IMPLIED, INCLUDING BUT NOT LIMITED TO THE WARRANTIES OF MERCHANTABILITY,
'FITNESS FOR A PARTICULAR PURPOSE AND NONINFRINGEMENT. IN NO EVENT SHALL THE
'AUTHORS OR COPYRIGHT HOLDERS BE LIABLE FOR ANY CLAIM, DAMAGES OR OTHER
'LIABILITY, WHETHER IN AN ACTION OF CONTRACT, TORT OR OTHERWISE, ARISING FROM,
'OUT OF OR IN CONNECTION WITH THE SOFTWARE OR THE USE OR OTHER DEALINGS IN THE
'SOFTWARE.
'
' Version of iArray: 1.0
''修正 元素從 0 開始

Private mainArray As New Collection
Private i As Long ' Counter

' #####################
' #    CONSTRUCTOR    #
' #####################
'Private Sub Class_Initialize()
'  Set mainArray = New Collection
'End Sub

' #####################
' #  Getter / Setter  #
' #####################
'Attribute Element.VB_UserMemId = 0 saved in both procedures

'@DefaultMember
Public Property Get element(ByVal index As Long) As iTemplate
Attribute element.VB_UserMemId = 0
    If index + 1 < 1 Or index + 1 > mainArray.Count Then
        Set element = Nothing
        Exit Property
    End If
    If IsObject(mainArray(index + 1)) = True Then
        Set element = mainArray(index + 1)
    Else
        element = mainArray(index + 1)
    End If

 
End Property

'@DefaultMember
Public Property Let element(ByVal index As Long, ByVal val As iTemplate)
Attribute element.VB_UserMemId = 0
   If index = 0 And mainArray.Count = 0 Then
    Me.Push val
    Exit Property
  End If
  If index + 1 > mainArray.Count Then
    Dim eMsg As String
    eMsg = IIf(mainArray.Count > 0, _
               "Index (" & index + 1 & ") out of iArray bounds (1-" & mainArray.Count & ")", _
               "iArray doesn't have any indexes")
    err.Raise Number:=9, Description:=eMsg
    Exit Property
  End If
  mainArray.Add val, after:=index + 1
  mainArray.Remove index + 1
End Property

' #############################
' # COMMON COLLECTION METHODS #
' #############################
Public Function Count() As Long
  Count = mainArray.Count
End Function
Public Sub Add(ByVal val As iTemplate, Optional ByVal bef As Variant = Empty, Optional ByVal aft As Variant = Empty)
  If IsEmpty(bef) And IsEmpty(aft) Then
    mainArray.Add val
  ElseIf IsEmpty(bef) Then
    mainArray.Add val, , , aft
  ElseIf IsEmpty(aft) Then
    mainArray.Add val, , bef
  Else
    mainArray.Add val, , bef, aft
  End If
End Sub
Public Sub Remove(index As Long)
  mainArray.Remove index + 1
End Sub

' ####################
' #  PUBLIC METHODS  #
' ####################

'AddAfter
' Adds element after given index.
' {1,2,3} -> index >= 3 -> Push val
' {1,2,3} -> index < 1 -> Unshift val
' {} -> index = any -> Push val
' @param Long index | Index after which will be added an element
' @param Variant val | One element (String, number, ...) to add into iArray
' @return Long | Count of elements inside iArray
Public Function AddAfter(ByVal index As Long, ByVal val As iTemplate) As Long
  If Me.Count < 1 Or index + 1 >= Me.Count Then
    Me.Push val
  ElseIf index + 1 < 1 Then
    Me.Unshift val
  Else
    Me.Add val, aft:=index + 1
  End If
  AddAfter = Me.Count
End Function

'AddArrayAfter
' Adds elements after given index.
' {1,2,3} -> index >= 3 -> PushArray val
' {1,2,3} -> index < 1 -> UnshiftArray val
' {} -> index = any -> PushArray val
' @param Long index | Index after which will be added an element
' @param Variant val | Array() or iArray of elements to add into iArray
' @return Long | Count of elements inside iArray
Public Function AddArrayAfter(ByVal index As Long, ByVal val As Variant) As Long
  If Me.Count < 1 Or index + 1 >= Me.Count Then
    Me.PushArray val
  ElseIf index + 1 < 1 Then
    Me.UnshiftArray val
  Else
    If TypeOf val Is iArrayTemplateList Then
      For i = 0 To val.Count - 1
        Me.Add val(i), aft:=index + 1
        Inc index
      Next i
    Else
      For i = LBound(val) To UBound(val)
        Me.Add val(i), aft:=index + 1
        Inc index
      Next i
    End If
  End If
  AddArrayAfter = Me.Count
End Function

'AddArrayBefore
' Adds elements before given index.
' {1,2,3} -> index > 3 -> PushArray val
' {1,2,3} -> index <= 1 -> UnshiftArray val
' {} -> index = any -> PushArray val
' @param Long index | Index after which will be added an element
' @param Variant val | Array() or iArray of elements to add into iArray
' @return Long | Count of elements inside iArray
Public Function AddArrayBefore(ByVal index As Long, ByVal val As Variant) As Long
  If Me.Count < 1 Or index + 1 > Me.Count Then
    Me.PushArray val
  ElseIf index <= 0 Then
    Me.UnshiftArray val
  Else
    If TypeOf val Is iArrayTemplateList Then
      For i = val.Count - 1 To 0 Step -1
        Me.Add val(i), bef:=index + 1
      Next i
    Else
      For i = UBound(val) To LBound(val) Step -1
        Me.Add val(i), bef:=index + 1
      Next i
    End If
  End If
  AddArrayBefore = Me.Count
End Function

'AddBefore
' Adds element before given index.
' {1,2,3} -> index > 3 -> Push val
' {1,2,3} -> index <= 1 -> Unshift val
' {} -> index = any -> Push val
' @param Long index | Index before which will be added an element
' @param Variant val | One element (String, number, ...) to add into iArray
' @return Long | Count of elements inside iArray
Public Function AddBefore(ByVal index As Long, ByVal val As iTemplate) As Long
  If Me.Count < 1 Or index + 1 > Me.Count Then
    Me.Push val
  ElseIf index + 1 <= 1 Then
    Me.Unshift val
  Else
    Me.Add val, bef:=index + 1
  End If
  AddBefore = Me.Count
End Function

'Avg
' Calculates the average of the numeric mainArray.
' @return Variant | Average value / "NaN" if iArray contains non-numeric value(s)
Public Function Avg() As Variant
  If Not Me.ContainsOnlyNumeric Then Avg = "NaN": Exit Function
  Avg = Me.sum / Me.Count
End Function

'Clear
' Empties iArray
Public Function Clear() As Boolean
  For i = mainArray.Count - 1 To 0 Step -1
    mainArray.Remove i + 1
  Next i
  Clear = IIf(mainArray.Count = 0, True, False)
End Function

'Clone
' Makes a hard copy of the mainArray
' @return mainArray | Return exact copy of itself
Public Function clone() As iArrayTemplateList
  Set clone = New iArrayTemplateList
  For i = 0 To Me.Count - 1
    clone.Push Me(i)
  Next i
End Function

'Contains
' Checks if given value is used inside mainArray.
' @param Variant val | One element (String, number, ...) to by checked if it exists in iArray
' $return Boolean | True = exists, False = doesn't exists
Public Function Contains(ByVal val As iTemplate) As Boolean
  Contains = False
  Dim el As Variant
  For Each el In mainArray
    If IsObject(val) = True Or VarType(val) And 8192 Then
        If (VarType(el) And 8192) And (VarType(val) And 8192) Then
            If ArrayDifference(el, val) Then
                Contains = True: Exit Function
            End If
        ElseIf IsObject(el) = True And IsObject(val) = True Then
            If el Is val Then
                Contains = True: Exit Function
            End If
        End If
    Else
        If IsObject(el) = False And (VarType(el) And 8192) <> 8192 Then
            If el = val Then
            Contains = True: Exit Function
            End If
        End If
    End If
  Next el
End Function

'ContainsAll
' Checks if all given values are used inside mainArray.
' @param Variant val | values to by checked if it exists in iArray
' $return Boolean | True = all exists, False = one ore more values doesn't exists
Public Function ContainsAll(ByVal val As iArrayTemplateList) As Boolean
  ContainsAll = False
  Dim foundOccurrences As Integer: foundOccurrences = 0
  Dim values As New iArrayTemplateList
  If Not TypeOf val Is iArrayTemplateList Then
    If IsArray(val) Then
      values.PushArray (val)
    Else
      values.Push (val)
    End If
  Else
    Set values = val
  End If
  For i = 0 To values.Count - 1
    If Me.Contains(values(i)) Then Inc foundOccurrences
  Next i
  If foundOccurrences = values.Count Then ContainsAll = True
End Function

'CountOccurrences
' Checks how many times is given value used inside mainArray.
' @param Variant val | One element (String, number, ...) to by checked
' @return Long | Count of matched occurrences
Public Function CountOccurrences(val As Variant) As Long
  CountOccurrences = 0
  Dim el As Variant
  For Each el In mainArray
  
    If IsObject(val) = True Or VarType(val) And 8192 Then
        If VarType(el) And 8192 And VarType(val) And 8192 Then
            If ArrayDifference(el, val) Then
                Inc CountOccurrences
                Exit Function
            End If
        ElseIf IsObject(el) = True And IsObject(val) = True Then
            If el Is val Then
                Inc CountOccurrences
                Exit Function
            End If
        End If
    Else
        If IsObject(el) = False And Not (VarType(el) And 8192) Then
            If el = val Then
                Inc CountOccurrences
                Exit Function
            End If
        End If
    End If
  
     'If el = val Then Inc CountOccurrences
  Next el
End Function

'Dequeue
' Removes an element from the begining of the mainArray.
' @return Variant | Removed element or Empty, if iArray is empty
'刪除開頭一個元素。
Public Function Dequeue() As iTemplate
  Dequeue = Empty
  If mainArray.Count > 0 Then
    If VarType(Me(0)) = vbString Then
        Dequeue = Me(0)
    ElseIf TypeOf Me(0) Is iArrayTemplateList Then
        Set Dequeue = Me(0)
    ElseIf VarType(Me(0)) = vbArray Then
        Set Dequeue = Me(0)
    ElseIf VarType(Me(0)) = vbObject Then
        Set Dequeue = Me(0)
    Else
        Dequeue = Me(0)
    End If
    
    mainArray.Remove 1
  End If
End Function

'Difference
' Checks for number of differences between two arrays, what was added/deleted or combination.
' @param iArray oldArray | Old iArray to be compared with current iArray
' @param String retType | �dd= deleted from old iArray, �aa= added in current iArray, �cc= combination of both (default)
' @return iArray | iArray with differences found
Public Function Difference(ByRef oldArray As iArrayTemplateList, Optional ByVal retType As String = "c") As iArrayTemplateList
  Set Difference = New iArrayTemplateList
  Select Case LCase(retType)
    Case "d"
      For i = 0 To oldArray.Count - 1
        If Me.Contains(oldArray(i)) = False Then Difference.Push oldArray(i)
      Next i
    Case "a"
      For i = 0 To Count - 1
        If oldArray.Contains(Me(i)) = False Then Difference.Push Me(i)
      Next i
    Case "c"
      For i = 0 To oldArray.Count - 1
        If Me.Contains(oldArray(i)) = False Then Difference.Push oldArray(i)
      Next i
      For i = 0 To Count - 1
        If oldArray.Contains(Me(i)) = False Then Difference.Push Me(i)
      Next i
    Case Else
      err.Raise Number:=5, Description:="Unknown Difference return type attribute:" & vbCrLf & _
                                        "Allowed are 'A'dded/'D'eleted/'C'ombination of both"
  End Select
End Function

'DropLeft
' Remove n elements from the beginning of the mainArray. If n > count of iArray elements, all elements are removed.
' @param Long n | Number of elements to be removed
' @return iArray | Array of the removed elements
Public Function DropLeft(ByRef N As Long) As iArrayTemplateList
  Set DropLeft = New iArrayTemplateList
  If N > Me.Count Then N = Me.Count
  For i = 0 To N - 1
    DropLeft.Push Me(i)
  Next i
  For i = N - 1 To 0 Step -1
    Me.Remove (i)
  Next i
End Function

'DropRight
' Remove n elements from the end of the mainArray. If n > count of iArray elements, all elements are removed.
' @param Long n | Number of elements to be removed
' @return iArray | Array of the removed elements
Public Function DropRight(ByRef N As Long) As iArrayTemplateList
  Set DropRight = New iArrayTemplateList
  If N > Me.Count Then N = Me.Count
  For i = Me.Count - N To Me.Count - 1
    DropRight.Push Me(i)
  Next i
  For i = Me.Count - 1 To Me.Count - N Step -1
    Me.Remove (i)
  Next i
End Function

'Enqueue
' Adds an element at the end of the mainArray.
' @param Variant val | One element (String, number, ...) to add into iArray
' @return Long | Count of elements inside iArray
Public Function Enqueue(ByVal val As Variant) As Long
  Enqueue = Push(val)
End Function

'EnqueueArray
' Adds elements at the end of the iArray
' @param Variant val | Array() or iArray of elements to add into iArray
' @return Long | Count of elements inside array
Public Function EnqueueArray(ByVal val As Variant) As Long
  EnqueueArray = PushArray(val)
End Function

'First
' Returns value of the first element of the mainArray.
' @return Variant | Value of the first element or Empty if iArray is Empty
Public Function First() As iTemplate
  Set First = IIf(Me.Count > 0, Me(0), Empty)
End Function

'Head
' Returns all elements of iArray, except last one.
' @return iArray | Copy of original array, without last element
Public Function head() As iArrayTemplateList
  Set head = Me.clone
  head.Pop
End Function

'Intersect
' Search for element that exists in both iArrays.
' @param iArray intArray | iArray to be intersected with current iArray
' @return iArray | Intersected values
Public Function Intersect(ByRef intersectedArr As iArrayTemplateList) As iArrayTemplateList
  Set Intersect = New iArrayTemplateList
  Dim el As Variant
  For Each el In mainArray
    If intersectedArr.Contains(el) Then
      If Not Intersect.Contains(el) Then Intersect.Push (el)
    End If
  Next el
End Function

'ContainsOnlyNumeric
' Verify that all elements are numbers or convertable to numbers
' $return Boolean | True = contains only numeric values, False = contains inconvertible values
Public Function ContainsOnlyNumeric() As Boolean
  ContainsOnlyNumeric = True
  Dim el As Variant
  For Each el In mainArray
    If Not IsNumeric(el) Then ContainsOnlyNumeric = False: Exit Function
  Next el
End Function

'Join
' Joins two iArrays.
' @param iArray jArray | iArray to be joined with current iArray
' @return iArray | Joined iArray
Public Function Join(ByRef joinArr As iArrayTemplateList) As iArrayTemplateList
  Set Join = New iArrayTemplateList
  Join.PushArray Me
  Join.PushArray joinArr
End Function

'Last
' Returns value of the last element of the mainArray.
' @return Variant | Value of the last element or Empty if iArray is Empty
Public Function Last() As iTemplate
  Set Last = IIf(Me.Count > 0, Me(Me.Count - 1), Empty)
End Function

'OccurrenceIndexes
' Returns all indexes of a value in mainArray.
' @return iArray | iArray containing indexes of occurrence
Public Function OccurenceIndexes(val As Variant) As iArrayTemplateList
  Set OccurenceIndexes = New iArrayTemplateList
  For i = 0 To Me.Count - 1
    If Me(i) = val Then
        OccurenceIndexes.Push (i)
    End If
  Next i
End Function

'Pop
' Removes an element from the end of the mainArray.
' @return Variant | Removed element or Empty, if iArray is empty
Public Function Pop() As iTemplate
  If mainArray.Count > 0 Then
    If VarType(Me(mainArray.Count - 1)) = vbObject Then
       Set Pop = Me(mainArray.Count - 1)
    Else
        Pop = Me(mainArray.Count - 1)
    End If
    mainArray.Remove mainArray.Count
  End If
End Function
  
  

'Push
' Adds an element at the end of the mainArray.
' @param Variant val | One element (String, number, ...) to add into iArray
' @return Long | Count of elements inside iArray
Public Function Push(ByVal val As iTemplate) As Long
  mainArray.Add val
  Push = mainArray.Count
End Function

'PushArray
' Adds elements at the end of the mainArray.
' @param Variant val | Array() or iArray of elements to add into iArray
' @return Long | Count of elements inside array
Public Function PushArray(ByVal val As Variant) As Long
  If TypeOf val Is iArrayTemplateList Then
    For i = 0 To val.Count - 1
      Me.Push val(i)
    Next i
  Else
    For i = LBound(val) To UBound(val)
      Me.Push val(i)
    Next i
  End If
  PushArray = Me.Count
End Function

'RemoveDuplicates
' Keeps only the first occurrence of the value. Affects original array
' @return Long | Count of the removed elements
Public Function RemoveDuplicates() As Long
  RemoveDuplicates = 0
  For i = Me.Count - 1 To 0 Step -1
    If Me.CountOccurrences(Me(i)) > 1 Then
      Me.Remove i
      Inc RemoveDuplicates
    End If
  Next i
End Function

'Reverse
' Reverses the content of the iArray
' @return iArray | Reversed iArray
Public Function Reverse() As iArrayTemplateList
  Set Reverse = New iArrayTemplateList
  For i = 0 To Me.Count - 1
    Reverse.Unshift Me(i)
  Next i
End Function

'Shift
' Removes an element from the begining of the mainArray.
' @return Variant | Removed element or Empty, if iArray is empty
'轉移
' 從 iArray 的開頭刪除一個元素。
' @返回第一個元素 | 如果 iArray 為空，則刪除元素或為空
Public Function shift() As iTemplate
  shift = Empty
  If mainArray.Count > 0 Then
    If VarType(Me(0)) = vbString Then
        shift = Me(0)
    ElseIf TypeOf Me(0) Is iArrayTemplateList Then
        Set shift = Me(0)
    ElseIf VarType(Me(0)) = vbArray Then
        Set shift = Me(0)
    ElseIf VarType(Me(0)) = vbObject Then
        Set shift = Me(0)
    Else
        shift = Me(0)
    End If
    
    mainArray.Remove 1
  End If
End Function

'Shuffle
' Randomly mixes content of the iArray
' @return iArray | Shuffled iArray
' 隨機播放
' 隨機混合 iArray 的內容
'@return iArray | 打亂iArray
Public Function Shuffle() As iArrayTemplateList
  Set Shuffle = New iArrayTemplateList
  Dim keys As New iArrayTemplateList
  For i = 0 To Me.Count - 1
    keys.Push (i)
  Next i
  Dim rndNo As Long
  Do While keys.Count > 0
    rndNo = randomFromTo(0, keys.Count - 1)
    Shuffle.Push Me(keys(rndNo))
    keys.Remove (rndNo)
  Loop
End Function

'Sum
' Calculates the sum of the numeric mainArray.
' @return Variant | Sum value / "NaN" if iArray contains non-numeric value(s)
Public Function sum() As Variant
  If Not Me.ContainsOnlyNumeric Then sum = "NaN": Exit Function
  sum = 0
  Dim el As Variant
  For Each el In mainArray
    sum = sum + el
  Next el
End Function

'Tail
' Returns all elements of iArray, except first one.
' @return iArray | Copy of original array, without first element
'返回陣列中除了第一個元素的剩余元素陣列
Public Function Tail() As iArrayTemplateList
  Set Tail = Me.clone
  Tail.Dequeue
End Function

Public Function ToList()
  If Me.Count = 0 Then ToList = Null: Exit Function
  Dim tarr()
  ReDim tarr(Me.Count - 1)
  For i = 0 To Me.Count - 1
    If VarType(Me(i)) = vbString Then
        tarr(i) = Me(i)
    ElseIf TypeOf Me(i) Is iArrayTemplateList Then
        Set tarr(i) = Me(i)
    ElseIf VarType(Me(i)) = vbObject Then
        Set tarr(i) = Me(i)
    Else
        tarr(i) = Me(i)
    End If
  Next i
  ToList = tarr
End Function

'ToString
' Creates string representation of the mainArray.
' @param String delimiter | Optional character to separate the iArray's elements (default = " ")
' @return String | Formated representation of tha iArray
Public Function ToString(Optional ByVal delimiter As String = " ") As String
  If Me.Count = 0 Then ToString = "{}": Exit Function
  ToString = vbNullString
  For i = 0 To Me.Count - 1
    If i = 0 Then ToString = ToString + "{"
    If i > 0 Then ToString = ToString + delimiter
    If VarType(Me(i)) = vbString Then
        ToString = ToString + Chr$(34)
        ToString = ToString + CStr(Me(i))
        ToString = ToString + Chr$(34)
    ElseIf TypeOf Me(i) Is iArrayTemplateList Then
        ToString = ToString + Me(i).ToString(delimiter)
    ElseIf (VarType(Me(i)) And vbArray) = vbArray Then
        ToString = ToString + "[Array]"
    ElseIf VarType(Me(i)) = vbObject Then
        ToString = ToString + "[Object]"
    Else
        ToString = ToString + CStr(Me(i))
    End If
    
    If i = mainArray.Count - 1 Then ToString = ToString + "}"
  Next i
End Function

'Union
' Combines both iArrays and removes duplicities
' @param iArray uArray | iArray to be unioned with current iArray
' @return iArray | Combined values without duplicities
Public Function Union(ByRef uArr As iArrayTemplateList) As iArrayTemplateList
  Set Union = Me.clone
  Union.PushArray uArr
  Union.RemoveDuplicates
End Function

'Unique
' Returns copy of iArray without duplicated values. Original array is not affected
' @return iArray | iArray with unique values
Public Function Unique() As iArrayTemplateList
  Set Unique = New iArrayTemplateList
  Dim el As Variant
  For Each el In mainArray
    If Not Unique.Contains(el) Then Unique.Push (el)
  Next el
End Function

'Unshift
' Add an element at the begining of the mainArray.
' @param Variant val | One element (String, number, ...) to add into iArray
' @return Long | Count of elements inside iArray
Public Function Unshift(ByVal val As Variant) As Long
  If mainArray.Count = 0 Then
    Unshift = Push(val)
  Else
    mainArray.Add val, before:=1
    Unshift = mainArray.Count
  End If
End Function

'UnshiftArray
' Add elements at the begining of the mainArray.
' @param Variant val | Array() or iArray of elements to add into iArray
' @return Long | Count of elements inside iArray
Public Function UnshiftArray(ByVal val As Variant) As Long
  If TypeOf val Is iArrayTemplateList Then
    For i = val.Count - 1 To 0 Step -1
      Unshift val(i)
    Next i
  Else
    For i = UBound(val) To LBound(val) Step -1
      Unshift val(i)
    Next i
  End If
  UnshiftArray = mainArray.Count
End Function


' #####################
' # PRIVATE FUNCTIONS #
' #####################
Sub Inc(ByRef i)
   i = i + 1
End Sub

'Private Function rangeToArray(ByVal rng As Range) As Variant
'  rangeToArray = rng.Value
'End Function

Private Function randomFromTo(ByVal from As Long, ByVal upTo As Long) As Long
  Randomize
  randomFromTo = Int(from + Rnd() * (upTo - from + 1))
End Function

'比對 兩個陣列是否一樣
Private Function ArrayDifference(arr1 As Variant, arr2 As Variant) As Boolean

    Dim i As Integer
    If UBound(arr1) = UBound(arr2) Then
        For i = 0 To UBound(arr1)
            If arr1(i) = arr2(i) Then
                ArrayDifference = True
            Else
                ArrayDifference = False
                Exit Function
            End If
        Next
    Else
        ArrayDifference = False
    End If

End Function

'@Description("changes the contents of the array by removing or replacing existing elements and/or adding new elements in place.")
Public Function Splice( _
        ByVal StartIndex As Long, _
        ParamArray Args() As Variant _
    ) As Variant()
    'Dim LocalItems() As Variant
    Dim ActualStart As Long
    Dim ActualDeleteCount As Long
    Dim ArgsCount As Long
    Dim LocalLength As Long
    Dim LocalArgs() As Variant
    Dim result() As Variant
    Dim i As Long
    Dim TempArray() As Variant
    Dim ItemCount As Long
    Dim TempItems() As Variant
    
    LocalArgs = Args
    'LocalItems = mainArray
    LocalLength = Me.Count
    If StartIndex < LocalLength Then
        ActualStart = StartIndex
    Else
        ActualStart = min(StartIndex, LocalLength)
    End If
    
    ArgsCount = UBound(LocalArgs) + 1
    If ArgsCount = 0 Then
        ' only a start index has been supplied
        ' we're gonna delete everything
        ' 僅提供了起始索引
         '我們要刪除所有內容
        ItemCount = 0
        ActualDeleteCount = LocalLength - ActualStart
    Else
        ' first arg in args is delete count, second onwards are insertion items
        ' args 中的第一個參數是刪除計數，第二個之後是插入項
        ItemCount = ArgsCount - 1
        'deleteCount is first element in args.
        'deleteCount 是 args 中的第一個元素。
        ActualDeleteCount = min(max(Args(LBound(Args)), 0), LocalLength - ActualStart)
    End If
    

    ' get items to be deleted for return val
    ' 取得和刪除
    If ActualDeleteCount > 0 Then
        ReDim result(0 To ActualDeleteCount - 1)
        i = 0
        Do While i < ActualDeleteCount
            If IsObject(Me(ActualStart)) Then
                Set result(i) = Me(ActualStart)
                Me.Remove ActualStart
            Else
                result(i) = Me(ActualStart)
                Me.Remove ActualStart
            End If
            Inc i
        Loop
    Else
        ' return empty array if nothing to be deleted
        ReDim result(0)
    End If
    
    '取得要插入的陣列資料
    If ItemCount > 0 Then
        ReDim TempItems(0 To ItemCount - 1)
        For i = 0 To ItemCount - 1
            If IsObject(LocalArgs(i + 1)) Then
                Set TempItems(i) = LocalArgs(i + 1)
            Else
                TempItems(i) = LocalArgs(i + 1)
            End If
        Next
    Me.AddArrayBefore ActualStart, TempItems
    End If
    
    
    Splice = result
End Function

Attribute VB_Name = "iArrayTest"
Option Explicit
Private iArr As iArray
Private iArr1 As iArray
Private iArr2 As iArray
Private cool As New Collection
Public Type miss2
    Name As String * 20
    idx As Integer
End Type
Public Type qq
     aaas As String
End Type

Public Function getMiss() As miss2()
    Dim gg As miss2
    Dim gm(3) As miss2
    gm(0).Name = "33"
    gm(0).idx = 74
    getMiss = gm
End Function
Sub objAdd()
    Dim mm As New Dictionary
    mm("asdfwe") = 4
 
    
End Sub
Public Function Splice( _
        ByVal StartIndex As Long, _
        ParamArray Args() As Variant _
    ) As Variant()
    Dim max As Integer
    Dim min As Integer
    max = UBound(Args)
    min = LBound(Args)
    End Function

Public Function getSlur(ss As String) As vSlur
    Set getSlur = New vSlur
    getSlur.label = ss
End Function
Public Sub sortPitch1()
    Dim sorted As Boolean
    Dim p As Integer
    Dim tmp
    Dim es As New iArray
    es.Push getSlur("6")
    es.Push getSlur("5")
    es.Push getSlur("4")
        For p = 0 To es.Count - 1
            If p + 1 >= es.Count Then
                sorted = True
            ElseIf (es(p).label > es(p + 1).label) Then
                Set tmp = es(p)
                es(p) = es(p + 1)
                es(p + 1) = tmp
            End If
        Next
    
End Sub



Public Sub iArrayVoiceTest()
    
    
    
    Dim vv As New iArray
    Dim v2
    
    vv.Add 0
    vv.Add 1
    vv.Add 2
    vv.Add 3
    vv.Add 4
    vv.Add 5
    vv.Add 6
    vv.Add 7
    vv.Add 8
    vv.Add 9
    vv.Add 0
    v2 = vv.Splice(3, 3, "a", "b")
    
    
    vv.Add "aa", , 3


End Sub
Sub oobjectIS()
    Dim aa As New iArray
    Dim bb(4) As Double
    Dim cc
    Dim dd As New point
    Dim ee As Date
    Dim ff As New point
    Dim gg As Boolean
    
    Dim ans As Boolean
    

    
    cc = Array(3, 4, 5, 23)
    
    Debug.Print "iArray" & vbTab & IsObject(aa)
    Debug.Print "Double()" & vbTab & IsObject(bb)
    Debug.Print "Variant" & vbTab & IsObject(cc)
    Debug.Print "Point " & vbTab & IsObject(dd)
    Debug.Print "Date" & vbTab & IsObject(ee)
    Debug.Print "miss2" & vbTab & IsObject(ff)
    Debug.Print "boolean" & vbTab & IsObject(gg)
    
    Debug.Print "iArray" & vbTab & VarType(aa)
    Debug.Print "Double()" & vbTab & VarType(bb)
    Debug.Print "Variant" & vbTab & VarType(cc)
    Debug.Print "Point" & vbTab & VarType(dd)
    Debug.Print "Date" & vbTab & VarType(ee)
    Debug.Print "miss2" & vbTab & VarType(ff)
    Debug.Print "boolean" & vbTab & VarType(gg)
    
    
End Sub
Public Sub iArrayPointTest()

    Set iArr = New iArray
    Dim pt As New point
    Call pt.c(3, 2)
    iArr.Push pt.clone
    Call pt.c(13, 12)
    iArr.Push pt.clone
    Call pt.c(23, 22)
    iArr.Push pt.clone
    Dim tmp
    Set tmp = iArr.head


End Sub


Public Sub iArrTest2()
    Dim llpt As New PointList
    Dim pt As New point
    Call pt.c(3, 2)
    llpt.Push pt.clone
    Call pt.c(13, 12)
    llpt.Push pt.clone
    Call pt.c(23, 22)
    llpt.Push pt.clone
    
    Dim tttmp
    tttmp = llpt.AddArrayAfter(1, llpt)
End Sub
Sub mae()
    Dim aa()
    Dim ppt As New point
    Dim p1 As New point
    Dim ss
    aa = Array(3, 4, 5)
    ss = TypeName(aa)
    p1.c 3, 4, 5
    
    ppt = p1
    'if TypeOf aa is Array then
    'End If
    
    
End Sub


Public Sub test_iTemplate_test()
    Dim it As iTemplate
    Dim tarr As New iArrayTemplateList
    Dim a2 As New iArrayTemplateList
    Dim aa(3) As Double
    Dim bb(3) As Double
    Dim cc
    
    cc = Array(33, 44, 11)
    If VarType(aa) = VarType(bb) Then
        cc = 33
    End If
    
    
    Set it = New iTemplate
    it.Name = "abc"
    it.typs = 12
    tarr.Push it
    
    Set it = New iTemplate
    it.Name = "Tita"
    it.typs = 33
    tarr.Push it
    
    Set it = New iTemplate
    it.Name = "May"
    it.typs = 23
    tarr.Push it
    
    Set a2 = tarr.head
    
    Set cc = tarr.Pop
    
End Sub


Public Sub test_type_test()
    Dim it
    Dim tarr As New iArray
    Dim a2
    Dim aa
    Dim bb
    
    it = Array(3, 4, 5, 6)
    tarr.Push it
    
    it = Array("_a_", "_b_", "_c_")
    tarr.Push it

    Set a2 = tarr.head
    
End Sub

Public Sub iArrayTest()
'Dim aa As Variant
Dim bb As Variant
'aa = Array(10, 20, 30)
bb = Array("_A_", "_B_", "_C_")
Dim aa As New point
'Dim bb As New point
aa.c 3, 4, 5
'bb.c 3, 4, 5


'ii(0) = 4

  ' ##### PUSH / POP TEST
  Debug.Print vbCrLf & " #### Push/Pop test"
  Set iArr = New iArray
  iArr.PushArray Array(aa, "a", True, 1, aa, "ba", bb)
  Call validate("Push", 4, iArr.Push("Hello world"))
  Debug.Print iArr(1)
  iArr.Pop
  iArr.Pop
  Call validate("Pop", True, iArr.Pop)
    
  ' ##### SHIFT / UNSHIFT TEST
  Debug.Print vbCrLf & " #### Shift/Unshift test"
  Set iArr = New iArray
  iArr.Unshift "..."
  Call validate("Unshift", "{""...""}", iArr.ToString)
  iArr.Unshift 123456
  iArr.UnshiftArray Array(aa, 3.1415, Empty, vbNullString, bb, "a")
  Call validate("UnshiftArray", Array("{3.1415  """" ""a"" 123456 ""...""}", "{3,1415  """" ""a"" 123456 ""...""}"), iArr.ToString)
  iArr.shift
  iArr.shift
  iArr.shift
  Call validate("Shift", "{""a"" 123456 ""...""}", iArr.ToString)

  ' ##### ENQUEUE / DEQUEUE TEST
  Debug.Print vbCrLf & " #### Enqueue/Dequeue test"
  Set iArr = New iArray
  iArr.Enqueue ("Queued element")
  Call validate("Enqueue", "{""Queued element""}", iArr.ToString)
  iArr.EnqueueArray Array(aa, 1, "2", 3.14, False, "Last", bb)
  Call validate("EnqueueArray", Array("{""Queued element"" 1 ""2"" 3.14 False ""Last""}", "{""Queued element"" 1 ""2"" 3,14 False ""Last""}"), iArr.ToString)
  iArr.Dequeue
  iArr.Dequeue
  Call validate("Dequeue", 1, iArr.Dequeue)

  ' ##### DEFAULT MEMBERS TEST
  Debug.Print vbCrLf & " #### Default members test"
  Set iArr = New iArray
  iArr.PushArray Array(aa, "1", 2, "3", 4, bb)
  Call validate("Default Members set", 2, iArr(2))
  iArr(2) = "Two"
  Call validate("Default Members edit", "Two", iArr(2))

  ' ##### CLEAR ARRAY TEST
  Debug.Print vbCrLf & " #### Clear array test"
  Set iArr = New iArray
  iArr.PushArray Array(1, 2, 3, 4, 5, "a", "b", "c", True, Empty)
  iArr.Clear
  Call validate("Clear", "{}", iArr.ToString)

  ' ##### COUNT OCCURRENCES TEST
  Debug.Print vbCrLf & " #### Count occurrences test"
  Set iArr = New iArray
  iArr.PushArray Array(1, 2, 2, 1, 3, 1, 2)
  Call validate("Count occurrences (yes)", 3, iArr.CountOccurrences(2))
  Call validate("Count occurrences (not)", 0, iArr.CountOccurrences(4))

  ' ##### CONTAINS TEST
  Debug.Print vbCrLf & " #### Contains test"
  Set iArr = New iArray
  iArr.PushArray Array(1, 2, 2, 1, 3, 1, 2, aa, bb)
  Call validate("Contains (yes)", True, iArr.Contains(1))
  Call validate("Contains (not)", False, iArr.Contains(5))

  ' ##### CONTAINS ALL TEST
  Debug.Print vbCrLf & " #### Contains All test"
  Set iArr = New iArray
  iArr.PushArray Array(aa, bb, 1, 2, 2, 1, 3, 1, 2, aa, bb)
  Call validate("ContainsAll (yes)", True, iArr.ContainsAll(Array(1, 3)))
  Call validate("ContainsAll (not)", False, iArr.ContainsAll(Array(1, 4, 5)))

  ' ##### FIND DIFFERENCES TEST
  Debug.Print vbCrLf & " #### Difference test"
  Set iArr1 = New iArray
  iArr1.PushArray Array(1, 2, 3, aa, bb)
  Set iArr2 = New iArray
  iArr2.PushArray Array(2, 3, 4, aa, bb)
  Set iArr = iArr2.Difference(iArr1)
  Call validate("Difference", "{1 4}", iArr.ToString)
  Set iArr = iArr2.Difference(iArr1, "d")
  Call validate("Difference (with ""d"" param)", "{1}", iArr.ToString)
  Set iArr = iArr2.Difference(iArr1, "a")
  Call validate("Difference (with ""a"" param)", "{4}", iArr.ToString)

  ' ##### JOINING ARRAYS TEST
  Debug.Print vbCrLf & " #### Joining arrays test"
  Set iArr1 = New iArray
  iArr1.PushArray Array(1, 2, 3, "a", "b", "c", aa, bb)
  Set iArr2 = New iArray
  iArr2.PushArray Array(4, 5, 6, "d", "e", "f", aa, bb)
  Set iArr = iArr1.Join(iArr2)
  Call validate("Join", "{1 2 3 ""a"" ""b"" ""c"" 4 5 6 ""d"" ""e"" ""f""}", iArr.ToString)

  ' ##### DROP LEFT/RIGHT TEST
  Debug.Print vbCrLf & " #### Drop left/right test"
  Set iArr = New iArray
  iArr.PushArray Array(aa, "1", "Two", "3", 4, 1, 2, 3, 4, 5, "a", "b", "c", True, bb)
  Call validate("DropLeft return", "{""1"" ""Two""}", iArr.DropLeft(2).ToString)
  Call validate("DropLeft", "{""3"" 4 1 2 3 4 5 ""a"" ""b"" ""c"" True}", iArr.ToString)
  Call validate("DropRight return", "{""b"" ""c"" True}", iArr.DropRight(3).ToString)
  Call validate("DropRight", "{""3"" 4 1 2 3 4 5 ""a""}", iArr.ToString)

  ' ##### UNIQUE / REMOVE DUPLICATES TEST
  Debug.Print vbCrLf & " #### Unique / Remove duplicates test"
  Set iArr = New iArray
  iArr.PushArray Array("3", 4, 1, 2, 3, 4, 5, "a", "b", "3", "c", "a", True, aa, bb)
  Dim uniqueArr As New iArray
  Set uniqueArr = iArr.Unique
  Call validate("Unique", "{""3"" 4 1 2 3 5 ""a"" ""b"" ""c"" True}", uniqueArr.ToString)
  Call validate("RemoveDuplicates (removed count)", 3, iArr.RemoveDuplicates)
  Call validate("RemoveDuplicates", "{""3"" 4 1 2 3 5 ""a"" ""b"" ""c"" True}", iArr.ToString)

  ' ##### CLONE ARRAY TEST
  Debug.Print vbCrLf & " #### Clone array test"
  Set iArr = New iArray
  iArr.PushArray Array("3", 4, 1, 2, 3, 4, 5, "a", "b", "c", True, aa, bb)
  Dim arrCloned As New iArray
  Set arrCloned = iArr.clone
  iArr.Clear
  Call validate("Clone", "{""3"" 4 1 2 3 4 5 ""a"" ""b"" ""c"" True [Object] [Array]}", arrCloned.ToString)

  ' ##### SHUFFLE ARRAY TEST
  Debug.Print vbCrLf & " #### Shuffle array test"
  Set iArr = New iArray
  iArr.PushArray Array("3", 4, 1, 2, 3, 4, 5, "a", "b", "c", True, aa, bb)
  Dim arrShufl As New iArray
  Set arrShufl = iArr.Shuffle
  Call validate("Shuffle", True, arrShufl.ToString <> iArr.ToString And arrShufl.ContainsAll(iArr))

  ' ##### REVERSE ARRAY TEST
  Debug.Print vbCrLf & " #### Reverse array test"
  Set iArr = New iArray
  iArr.PushArray Array("3", 4, 1, 2, 3, 4, 5, "a", "b", "c", True)
  Dim arrRev As New iArray
  Set arrRev = iArr.Reverse
  Call validate("Reverse", "{True ""c"" ""b"" ""a"" 5 4 3 2 1 4 ""3""}", arrRev.ToString)

  ' ##### FIRST/LAST TEST
  Debug.Print vbCrLf & " #### First/Last test"
  Set iArr = New iArray
  iArr.PushArray Array(1, 2, 3, 4, 5)
  Call validate("First", 1, iArr.First)
  Call validate("Last", 5, iArr.Last)

  ' ##### ADD AFTER/BEFORE TEST
  Debug.Print vbCrLf & " #### Add after/before test"
  Set iArr = New iArray
  iArr.AddBefore 2, "Something"
  iArr.PushArray Array(1, 2, 3, 4, 5)
  iArr.AddBefore 1, "New First"
  Call validate("AddBefore", "{""New First"" ""Something"" 1 2 3 4 5}", iArr.ToString)
  iArr.AddAfter 4, "Hello"
  Call validate("AddAfter", "{""New First"" ""Something"" 1 2 ""Hello"" 3 4 5}", iArr.ToString)

  ' ##### ADD AFTER/BEFORE ARRAY TEST
  Debug.Print vbCrLf & " #### Add after/before array test"
  Set iArr = New iArray
  iArr.PushArray Array(1, 2, 3, 4, 5)
  iArr.AddArrayAfter 2, Array("a", "b", "c")
  Call validate("AddArrayBefore", "{1 2 ""a"" ""b"" ""c"" 3 4 5}", iArr.ToString)
  iArr.AddArrayBefore 7, Array(True, False)
  Call validate("AddArrayBefore", "{1 2 ""a"" ""b"" ""c"" 3 True False 4 5}", iArr.ToString)
  
  ' ##### TAIL/HEAD TEST
  Debug.Print vbCrLf & " #### Tail / Head test"
  Set iArr = New iArray
  iArr.PushArray Array("3", 4, 1, 2, 3, 4, 5, "a", "b", "c", True)
  Dim tailArr As New iArray
  Set tailArr = iArr.Tail
  Call validate("Tail", "{4 1 2 3 4 5 ""a"" ""b"" ""c"" True}", tailArr.ToString)
  Dim headArr As New iArray
  Set headArr = tailArr.head
  Call validate("Head", "{4 1 2 3 4 5 ""a"" ""b"" ""c""}", headArr.ToString)
  
  ' ##### CONTAINS ONLY NUMERIC TEST
  Debug.Print vbCrLf & " #### Contains Only Numeric test"
  Set iArr = New iArray
  iArr.PushArray Array("3", 4, "3.1415", 2, "1E-2")
  Call validate("ContainsOnlyNumeric", True, iArr.ContainsOnlyNumeric)
  Set iArr = New iArray
  iArr.PushArray Array("3a", 4, 3.1415, 2, "1E-2")
  Call validate("ContainsOnlyNumeric", False, iArr.ContainsOnlyNumeric)
  
  ' ##### AVERAGE / SUM TEST
  Debug.Print vbCrLf & " #### Average / Sum test"
  Set iArr = New iArray
  iArr.PushArray Array("3a", 4, "3.1415", 2, "1E-2")
  Call validate("Sum", "NaN", iArr.sum)
  Set iArr = New iArray
  iArr.PushArray Array("3", 4, 3.1415, 2, "1E-2")
  Call validate("Sum", 12.1515, iArr.sum)
  Call validate("Average", 2.4303, iArr.Avg)
  
  ' ##### OCCURRENCE INDEXES TEST
  Debug.Print vbCrLf & " #### Occurence Indexes test"
  Set iArr = New iArray
  iArr.PushArray Array(1, 2, True, "Abc", 2, "1", 3, 1, 2)
  Call validate("Occurrence indexes", "{1 8}", iArr.OccurenceIndexes(1).ToString)
  
  ' ##### INTERSECT ARRAYS TEST
  Debug.Print vbCrLf & " #### Intersect arrays test"
  Set iArr1 = New iArray
  iArr1.PushArray Array(1, 2, 3, "a", "b", "a")
  Set iArr2 = New iArray
  iArr2.PushArray Array(3, 2, 6, "a", "a", "f")
  Set iArr = iArr1.Intersect(iArr2)
  Call validate("Intersect", "{2 3 ""a""}", iArr.ToString)
  
  ' ##### UNION ARRAYS TEST
  Debug.Print vbCrLf & " #### Union arrays test"
  Set iArr1 = New iArray
  iArr1.PushArray Array(1, 2, 3, "a", "b", "a")
  Set iArr2 = New iArray
  iArr2.PushArray Array(3, 2, 6, "a", "a", "f")
  Set iArr = iArr1.Union(iArr2)
  Call validate("Union", "{1 2 3 ""a"" ""b"" 6 ""f""}", iArr.ToString)
End Sub

Private Sub validate(Name As String, Expected, Actual As String)
  If Not IsArray(Expected) Then Expected = Array(Expected)
  
  Dim found As Boolean: found = False
  Dim possibleResult As String
  
  Dim i As Integer
  For i = LBound(Expected) To UBound(Expected)
    If Expected(i) = Actual Then found = True: Exit For
  Next i
  
  If found Then
    Debug.Print Name + " - OK"
  Else
    Debug.Print Name + " - NOK"
    Debug.Print " - Actual value: " + Actual
    
    Dim expectedString As Variant
    For i = LBound(Expected) To UBound(Expected)
      If i > LBound(Expected) Then expectedString = expectedString + " or "
      expectedString = expectedString + Expected(i)
    Next i
    Debug.Print " - Expected value: " + CStr(expectedString)
  End If
End Sub

Public Function ToString(self, Optional ByVal delimiter As String = " ") As String
    Dim j As Long
     If (VarType(self) And vbArray) = vbArray Then
     ElseIf TypeOf self Is iArray Then
     
     End If
  If Me.Count = 0 Then ToString = "{}": Exit Function
  ToString = vbNullString
  For i = 0 To Me.Count - 1
    If i = 0 Then ToString = ToString + "{"
    If i > 0 Then ToString = ToString + delimiter
    If VarType(Me(i)) = vbString Then
        ToString = ToString + Chr$(34)
        ToString = ToString + CStr(Me(i))
        ToString = ToString + Chr$(34)
    ElseIf TypeOf Me(i) Is iArray Then
        ToString = ToString + Me(i).ToString(delimiter)
    ElseIf (VarType(Me(i)) And vbArray) = vbArray Then
        ToString = ToString + "[Array]"
    ElseIf VarType(Me(i)) = vbObject Then
        ToString = ToString + "[Object]"
    Else
        ToString = ToString + CStr(Me(i))
    End If
    
    If i = iArray.Count - 1 Then ToString = ToString + "}"
  Next i
End Function

Attribute VB_Name = "iTemplate"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public typs As Integer
Public Name As String

Attribute VB_Name = "jsABCgetJson"
Option Explicit

Public ts As New iArray
Public Function getAbcJson() As iArray
    ''把 abc2svg 的 TS 資料 轉換成  VBA 物件 =>ts
    Dim prod As Variant
    Baidu_appition
    Dim cdtxt As String
    Dim tsCount As Integer
    Dim childCount As Integer
    Dim i As Integer
    Dim j As Integer
    Dim childItem As voiceItem
    Dim childList As iArray
    tsCount = WD.ExecuteScript("return ts.length")
    ts.Clear
    For i = 0 To tsCount - 1
        If i >= ts.Count - 1 Then
            ts.Push New iArray
        End If
        Set childList = ts(i)
        
        childCount = WD.ExecuteScript("return ts[" & i & "].length")
        For j = 0 To childCount - 1
            cdtxt = "ts[" & i & "][" & j & "]"
            prod = WD.ExecuteScript("return JSON.stringify(" & cdtxt & ", JsonReplacerABC2SVG, 2)")
            'Debug.Print prod
            Set childItem = childGetTsItem(prod)
            childItem.fname = "ts[" & i & "][" & j & "]"
            childList.Push childItem
        Next
    Next
    
 Set getAbcJson = ts
End Function

Function childGetTsItem(prod) As voiceItem
    On Error GoTo ErrorHandler
    Dim JsonObject
    Dim Json As Dictionary
    Dim key
    Dim abcItem As New iArray
    Dim getArrList As iArray
    Dim vItem As voiceItem
    
    Set vItem = New voiceItem
    Set Json = JsonConverter.ParseJson(prod)
    For Each key In Json.keys
        Select Case key    ' Evaluate Number.
            Case "notes":
                Set getArrList = objArrayItem(Json.item(key), AbcObject.noteItem)
                'Call vItem.ConvertVarName(key, Json.Item(key))
                CallByName vItem, key, VbSet, getArrList
            Case "slurStart":
                Set getArrList = objArrayItem(Json.item(key), AbcObject.Number)
                'Call vItem.ConvertVarName(key, Json.Item(key))
                CallByName vItem, key, VbSet, getArrList
            Case "slurEnd":
                Set getArrList = objArrayItem(Json.item(key), AbcObject.Number)
                'Call vItem.ConvertVarName(key, Json.Item(key))
                CallByName vItem, key, VbSet, getArrList
            Case "k_map", "a_gch":
                Set getArrList = objArrayItem(Json.item(key), AbcObject.KMapItem)
                'Call vItem.ConvertVarName(key, Json.Item(key))
                CallByName vItem, key, VbSet, getArrList
            Case "a_meter":
            Case "x_meter":
            Case "tempo_notes":
            Case "tempo_wh":
            Case "slur":
            Case "pos":
            Case "sy":
            Case "type":
                CallByName vItem, "typs", VbLet, Json.item(key)
            Case "next":
                CallByName vItem, "nexs", VbLet, Json.item(key)
            Case "__TSpos":
                CallByName vItem, "TS_pos", VbLet, Json.item(key)
            Case Else
                CallByName vItem, key, VbLet, Json.item(key)
                'Call vItem.ConvertVarName(key, Json.Item(key))
callBack1:
        End Select
    Next
    Set childGetTsItem = vItem
    Exit Function
ErrorHandler:
    If VarType(Json.item(key)) = vbObject Then
        Debug.Print "key-> " & key & " value-> [object]"
    Else
        Debug.Print "key-> " & key & " value-> " & Json.item(key)
    End If
GoTo callBack1

End Function
Function objArrayItem(ListObject, ByVal objectEnum As AbcObject) As iArray
    On Error GoTo ErrorHandler
        Dim ky1, lsNote, o, o2, ks
        Dim i, j
        Dim ListNote
        Dim aObj
        Dim aObjArr As New iArray
        Dim retArrList
        If objectEnum = Number Or objectEnum = Booling Then
            For Each o In ListObject
                aObjArr.Push o
            Next
        Else
            For Each o In ListObject
                Set aObj = newObjectItem(objectEnum)
                For Each ks In o.keys
                    CallByName aObj, ks, VbLet, o.item(ks)
                    Select Case key    ' Evaluate Number.
                        Case "font":
                            Set retArrList = objArrayItem(o.item(key), AbcObject.FontItem)
                            'Call vItem.ConvertVarName(key, Json.Item(key))
                            CallByName aObj, ks, VbSet, retArrList
                      
                        Case Else
                            CallByName aObj, ks, VbLet, o.item(ks)

                     End Select
                    
                    'Call aNote.ConvertVarName(o2, lsNote.Item(o2))
callback2:
                Next
                Call aObjArr.Push(aObj)
            Next
        End If
        Set objArrayItem = aObjArr
        Exit Function
ErrorHandler:
    Debug.Print "objArrayItemkey=> "& "[" &   &"]" & ks & "  value-> " & o.item(ks)
GoTo callback2
        ' Resume execution at same line
        ' that caused the error.

End Function
Function newObjectItem(objectName As AbcObject)
    '創建任合物件
        Select Case objectName
            ''一般
            Case AbcObject.noteItem:        Set newObjectItem = New aNoteItem
            Case AbcObject.DecorationItme:  Set newObjectItem = New aDecorationItem
            Case AbcObject.FontItem:        Set newObjectItem = New aFontItem
            Case AbcObject.GchordItem:      Set newObjectItem = New aGchordItem
            Case AbcObject.LyrcsItem:       Set newObjectItem = New aLyricsItem
            Case AbcObject.VoiecItem:       Set newObjectItem = New voiceItem
            Case AbcObject.KMapItem:        Set newObjectItem = New aKMap
            Case Else
                Debug.Print "沒有變數 " & key & "名"
        End Select
End Function
Function testJSON()
    Dim JsonString As String
    Dim JsonObject
    Dim Json As Dictionary
    Set Json = JsonConverter.ParseJson("{""a"":123,""b"":[1,2,3,4],""c"":{""d"":456}}")
    
    ' Json("a") -> 123
    ' Json("b")(2) -> 2
    ' Json("c")("d") -> 456
    Json("c")("e") = 789
    
    Debug.Print JsonConverter.ConvertToJson(Json)
    ' -> "{"a":123,"b":[1,2,3,4],"c":{"d":456,"e":789}}"
    
    Debug.Print JsonConverter.ConvertToJson(Json, Whitespace:=2)
    Debug.Print Json.Count

End Function

Function voieMusic()
    Dim vvbase As New voiceBase
    Debug.Print vvbase.typs
    vvbase.typs = 3
    Debug.Print vvbase.typs
    
    Dim vvbar As New voiceBar
    Debug.Print vvbar.typs
End Function

Attribute VB_Name = "layoutStaffGroup"
Option Explicit
'
'import StaffGroupElement from '../creation/elements/staff-group-element'
'import VoiceElement from '../creation/elements/voice-element'
'import Renderer from '../renderer'
'import layoutVoiceElements from './voice-elements'

Function checkLastBarX(voices As VoiceElementList)
''這是把最後的小節線對齊
    Dim maxX As Double
    Dim i As Integer
    For i = 0 To voices.Count - 1
        Dim curVoice
        Dim LastChildNum As Integer
        Dim maxChild As MusicItem 'VoiceElement
        Dim barX As Double
        Set curVoice = voices(i)
        If (curVoice.children.Count > 0) Then
            LastChildNum = curVoice.children.Count - 1
            Set maxChild = curVoice.children(LastChildNum)
'            If (maxChild.abcelem.el_type = "bar") Then
'                barX = maxChild.children(0).x
'                If (barX > maxX) Then
'                    maxX = barX
'                 Else
'                    maxChild.children [0].x = maxX
'                End If
'            End If
            If (maxChild.typs = Cg.bar) Then
                barX = maxChild.x
                If (barX > maxX) Then
                    maxX = barX
                 Else
                    maxChild.x = maxX
                End If
            End If
        End If
    Next
End Function

Public Function layoutStaffGroup2(spaci As Double, renderer As RendererModule, debug_ As Boolean, staffGroup As StaffGroupElement, leftEdge As Double) As Dictionary

    Dim currentduration
    Dim durationIndex   As Double
    Const Epsilon As Double = 0.0000001
    Dim spacingunit As Double
    Dim spacingUnits As Double
    Dim minSpace As Double
    Dim x As Double
    Dim i As Integer, j As Integer, k As Integer
    
    
    
    For i = 0 To staffGroup.voices.Count - 1
        layoutVoiceElements.beginLayout x, staffGroup.voices(i)
    Next
    
    
    Dim errCount As Long
    minSpace = 1000
    '這迴圈是設定 X 軸向
    Do While (finished(staffGroup.voices) = False And errCount < 500)  ' Inner loop.
'       Dim currVoice As VoiceElement
'       Set currVoice = StaffGroup.voices(1)
'       Debug.Print "layoutStaffGroup loop :" & currVoice.i
       errCount = errCount + 1
        
        '' 找到要在跨聲音的候選者之間佈置的第一個持續時間級別
        currentduration = Empty '' candidate smallest duration level
        For i = 0 To staffGroup.voices.Count - 1
            If Not layoutVoiceElements.layoutEnded(staffGroup.voices(i)) Then
                If IsEmpty(currentduration) Then
                    currentduration = getDurationIndex(staffGroup.voices(i))
                ElseIf getDurationIndex(staffGroup.voices(i)) < currentduration Then
                    currentduration = getDurationIndex(staffGroup.voices(i))
                    
                End If
            End If
        Next
        
        
              
        
        ''isolate voices at current duration level
        ''隔離目前持續時間等級的語音
        Dim currentvoices As New iArray ' VoiceElement[] = []
        Dim othervoices As New iArray ' VoiceElement[] = []
        currentvoices.Clear
        othervoices.Clear
        For i = 0 To staffGroup.voices.Count - 1
            durationIndex = getDurationIndex(staffGroup.voices(i))
            '' PER: Because of the inexactness of JS floating point math, we just get close.
            '' PER：由於 JS 浮點數學的不精確性，我們只是接近而已。
            If (durationIndex - currentduration > Epsilon) Then
                othervoices.Push staffGroup.voices(i)
            Else
                currentvoices.Push staffGroup.voices(i)
            End If
            
        Next
        
        '' among the current duration level find the one which needs starting furthest right
        '' 在目前持續時間級別中找到需要從最右邊開始的持續時間級別
        spacingunit = 0 '' number of spacingunits coming from the previously laid out element to this one
        Dim spacingduration As Double
        For i = 0 To currentvoices.Count - 1
            
            If (layoutVoiceElements.getNextX(currentvoices(i)) > x) Then
                x = layoutVoiceElements.getNextX(currentvoices(i))
                spacingunit = layoutVoiceElements.getSpacingUnits(currentvoices(i))
                spacingduration = currentvoices(i).spacingduration
            End If
        Next
        spacingUnits = spacingUnits + spacingunit
        minSpace = Math.min(Array(minSpace, spacingunit))
        

        Dim lastTopVoice
        For i = 0 To currentvoices.Count - 1
            Dim v As VoiceElement
            Dim topVoice As VoiceElement
            Dim voicechildx As Double
            Dim dx As Double
            Set v = currentvoices(i)
            If (v.voicenumber = 0) Then lastTopVoice = i
            If lastTopVoice <> Empty And currentvoices(lastTopVoice).voicenumber <> v.voicenumber Then
                Set topVoice = currentvoices(lastTopVoice)
            Else
                Set topVoice = Nothing
            End If
            ''line 不知到 if (~isSameStaff(v, topVoice)) then   Set topVoice = Empty
            'Debug.Print v.children(v.I).notes(0).mnote
            voicechildx = layoutVoiceElements.layoutOneItem(x, spaci, v, 0, topVoice)
            dx = voicechildx - x
            ''這是看是否有前倚音
            ''如果有，全部的音符就在加前倚音的距離
            If (dx > 0) Then
                x = voicechildx ''update x
                For j = 0 To i '' shift over all previously laid out elements
                    Call layoutVoiceElements.shiftRight(dx, currentvoices(j))
                Next
            End If
        Next

        '' remove the value of already counted spacing units in other voices
        '' (e.g.if a voice had planned to use up 5 spacing units but is not in line to be laid out at this duration level -
        '' where we've used 2 spacing units - then we must use up 3 spacing units, not 5)
        '' 刪除其他語音中已計算的間隔單位的值
        ''（例如，如果一個語音計劃使用 5 個間隔單位，但未在此持續時間級別上排列 -
        '' 我們使用了 2 個間隔單位 - 那麼我們必須用完3個間距單位，而非5 個）
        '' 測試後不需要
        For i = 0 To othervoices.Count - 1
            othervoices(i).spacingduration = othervoices(i).spacingduration - spacingduration
            Call layoutVoiceElements.updateOtherNextX(x, spaci, othervoices(i))   '' adjust other voices expectations
        Next
        
                    
              
        '' 更新目前佈局元素的索引
        For i = 0 To currentvoices.Count - 1
            Dim voice As VoiceElement
            Set voice = currentvoices(i)
            '' 把每一個 voice.i 加 1 為下一個子元素
            '' 還有修改 voice.durationindex 加上現在已經讀取 的音符長度
            '' 4分音附=0.25 2分音附=0.5 全分音附=1
            '' 每一小節總長(分母)為 1
            Call layoutVoiceElements.updateIndices(voice)
        Next
    Loop
    i = i + 1



    '' find the greatest remaining x as a base for the width
    '' 找出最大的剩餘 x 作為寬度的基數
    For i = 0 To i < staffGroup.voices.Count - 1
        If (layoutVoiceElements.getNextX(staffGroup.voices(i)) > x) Then
            x = layoutVoiceElements.getNextX(staffGroup.voices(i))
            spacingunit = layoutVoiceElements.getSpacingUnits(staffGroup.voices(i))
        End If
    Next

    '' adjust lastBar when needed (multi staves)
    Call checkLastBarX(staffGroup.voices)
    ''console.log("greatest remaining",spacingunit,x)
    spacingUnits = spacingUnits + spacingunit
    ''把一組的 V 寬度設定 最寬
    staffGroup.setWidth (x)
    
    
    staffGroup.spacingUnits = spacingUnits
    staffGroup.minSpace = minSpace
    
End Function


Public Function finished(voices As VoiceElementList) As Boolean
    Dim i As Integer
    Dim v As VoiceElement
    For i = 0 To voices.Count - 1
        Set v = voices(i)
        If (layoutVoiceElements.layoutEnded(v) = False) Then
            finished = False
            Exit Function
        End If
    Next
            
    finished = True
End Function

Function getDurationIndex(element As VoiceElement) As Double
    '' if the ith element doesn't have a duration (is not a note), its duration index is fractionally before.
    '' This enables CLEF KEYSIG TIMESIG PART, etc.to be laid out before we get to the first note of other voices
    '' 如果第 i 個元素沒有持續時間（不是音符），則其持續時間索引在前面。
    '' 這使得 CLEF KEYSIG TIMESIG PART 等能夠在我們到達其他聲音的第一個音符之前進行佈局
    Dim getItemDuration As Double
    
    If Not (element.children(element.i) Is Nothing) Then
        If TypeOf element.children(element.i) Is MusicItem Then
            If element.children(element.i).duration > 0 Then
                getItemDuration = 0
            Else
                getItemDuration = 0.0000005
            End If
        Else
            getItemDuration = 0.0000005
        End If
        
    Else
        getItemDuration = 0.0000005
    End If
    
    getDurationIndex = element.durationIndex - getItemDuration
End Function

Public Function isSameStaff(voice1 As VoiceElement, voice2 As VoiceElement) As Boolean
    If (IsEmpty(voice1) Or IsEmpty(voice1.Staff) Or IsEmpty(voice1.Staff.voices) Or voice1.Staff.voices.Count = 0) Then
        isSameStaff = False
        Exit Function
    End If
    If (IsEmpty(voice2) Or IsEmpty(voice2.Staff) Or IsEmpty(voice2.Staff.voices) Or voice2.Staff.voices.Count = 0) Then
        isSameStaff = False
        Exit Function
    End If
    isSameStaff = Not (voice1.Staff.voices(0) <> voice2.Staff.voices(0))
End Function

Attribute VB_Name = "layoutVoiceElements"
Option Explicit

Sub beginLayout(startX As Double, voice As VoiceElement)

    voice.i = 0
    voice.durationIndex = 0
    ''this.ii=this.children.length
    voice.startX = startX
    voice.minX = startX '' furthest left To where negatively positioned elements are allowed To go
    voice.nextX = startX '' x position where the Next element Of this voice should be placed assuming no other voices And no fixed width constraints
    voice.spacingduration = 0 '' duration left To be laid out In current iteration (omitting additional spacing due To other aspects, such As bars, dots, sharps And flats)
End Sub


Function layoutEnded(voice As VoiceElement) As Boolean
    layoutEnded = (voice.i >= voice.children.Count)
End Function


Function getNextX(voice As VoiceElement) As Double
    getNextX = Math.max(Array(voice.minX, voice.nextX))
        'Return Math.max(voice.minx, voice.nextx)
End Function

'' number of spacing units expected for next positioning
Function getSpacingUnits(voice As VoiceElement)
    If (G.IsBarAlign) Then
        getSpacingUnits = voice.spacingduration# / 384
    Else
        getSpacingUnits = Sqrt(voice.spacingduration# / 384)
    End If
   
   'getSpacingUnits = Sqrt(Sqrt(voice.spacingduration# / 384))
   'getSpacingUnits = voice.spacingduration# / 384
End Function

'**
'* 嘗試佈局索引 this.i 處的元素
'* 每次迭代不能多次呼叫此函數
'* @param x position to try to layout the element at
'*          嘗試佈局元素的位置
'* @param spacing base spacing
'*                基礎間距
'*'
Function layoutOneItem(x As Double, spacing As Double, voice As VoiceElement, minPadding As Double, firstVoice As VoiceElement)
    Dim child As MusicItem 'voiceItem
    Dim er As Double
    Dim pad  As Double
    Dim firstChild As MusicItem 'voiceItem
    Dim overlaps As Boolean
    Dim j As Integer
    Set child = voice.children(voice.i)
    If (child Is Nothing) Then
        layoutOneItem = 0
        Exit Function
    End If
    '' er : available extrawidth To the left  左側可用的額外寬度
    er = x - voice.minX
    '' pad : only add padding To the items that aren't fixed to the left edge.
    '' pad : 僅在未固定到左邊緣的項目新增填滿。
    If voice.durationIndex + child.duration > 0 Then
        pad = minPadding
    Else
        pad = 0
    End If
        '' See if this item overlaps the item in the first voice. If firstVoice Is undefined then there's nothing to compare.
        '' 查看該項目是否與第一個語音中的項目重疊。 如果 firstVoice 未定義，則沒有什麼可比較的。
    '    If (child.abcelem.el_type === "note" && !child.abcelem.rest && voice.voicenumber! == 0 && firstVoice) Then
    '    firstChild = firstVoice.children(firstVoice.i)
    '    '' It overlaps if the either the child's top or bottom is inside the firstChild's or at least within 1
    '    '' A special case Is if the element Is on the same line then it can share a note head, if the notehead Is the same
    '    '' 如果孩子的頂部或底部在第一個孩子的內部或至少在 1 之內，則它重疊
    '    '' 一種特殊情況是如果元素在同一行那麼它可以共用一個音符頭，如果音符頭相同
    '    overlaps = firstChild &&
    '            ((child.abcelem.maxpitch <= firstChild.abcelem.maxpitch + 1 && child.abcelem.maxpitch >= firstChild.abcelem.minpitch - 1) ||
    '                (child.abcelem.minpitch <= firstChild.abcelem.maxpitch + 1 && child.abcelem.minpitch >= firstChild.abcelem.minpitch - 1))
    '        '' See if they can share a note head
    '        '' 看看他們是否可以共享一個音符頭
    '        If (overlaps && child.abcelem.minpitch === firstChild.abcelem.minpitch && child.abcelem.maxpitch === firstChild.abcelem.maxpitch &&
    '            firstChild.heads && firstChild.heads.length > 0 && child.heads && child.heads.length > 0 &&
    '            firstChild.heads[0].c === child.heads[0].c) Then overlaps = False
    '    '' If this note overlaps the note in the first voice And we haven't moved the note yet (this can be called multiple times)
    '    '' 如果這個音符與第一個聲音中的音符重疊，並且我們還沒有移動該音符（可以多次呼叫）
    '    If (overlaps) Then
    '        '' I think that firstChild should always have at least one note head, but defensively make sure.
    '        '' There was a problem with this being called more than once so if a value Is adjusted then it Is saved so it Is only adjusted once.
    '        var firstChildNoteWidth = firstChild.heads && firstChild.heads.length > 0 ? firstChild.heads[0].realWidth : firstChild.fixed.w
    '        If (!child.adjustedWidth) Then
    '            child.adjustedWidth = firstChildNoteWidth + child.w
    '            child.w = child.adjustedWidth
    '            For (j = 0 j < child.children.length j++) then
    '                var relativeChild = child.children[j]
    '                If (relativeChild.name.indexOf("accidental") < 0) Then {
    '                    If (!relativeChild.adjustedWidth) Then
    '                    relativeChild.adjustedWidth = relativeChild.dx + firstChildNoteWidth
    '                End If
    '                relativeChild.dx = relativeChild.adjustedWidth
    '            End If

    '        Next
    '    End If
    'End If

    If child.typs = Cg.meter Then
        voice.meteA = child.mete
        voice.meteB = child.mete2
    End If
    Dim extraWidth As Double
    extraWidth = getExtraWidth(child, pad)
    If (er < extraWidth) Then  '' shift right by needed amount 右移所需數量
        '' There's an exception if a bar element is after a Part element, there is no shift.
        '' 如果 bar 元素位於 Part 元素之後，則有例外情況，則不會發生移位。
        If (voice.i = 0 Or child.typs <> Cg.bar) Then
            x = x + extraWidth - er
        ElseIf voice.children(voice.i - 1).typs <> Cg.part And voice.children(voice.i - 1).typs <> Cg.tempo Then
            x = x + extraWidth - er
        End If
    End If
    child.setX x
    If child.duration > 0 Then
        voice.spacingduration = child.duration
    Else
        voice.spacingduration = 1
    End If
    
    ''updateMinx
    Call updateMinX(x, voice)

    '' 計算下一個元件的位置
    Call updateNextX(x, spacing, voice)

    '' contribute to staff y position
    ''this.staff.top = Math.max(child.top,this.staff.top)
    ''this.staff.bottom = Math.min(child.bottom,this.staff.bottom)

    layoutOneItem = x '' where we End up having placed the child
End Function

Sub shiftRight(dx As Double, voice As VoiceElement)
    Dim child As voiceItem
    Set child = voice.children(voice.i)
    If IsEmpty(child) Then Exit Sub
    child.setX (child.x + dx)
    voice.minX = voice.minX + dx
    voice.nextX = voice.nextX + dx
End Sub
'' call when spacingduration has been updated
Sub updateMinX(x As Double, voice As VoiceElement)
    Dim child As MusicItem 'voiceItem
    Dim barDurAll As Double
    Dim currDur As Double
    Dim nextTyps As Cg
    
    barDurAll = voice.barDurationIndex
    currDur = voice.children(voice.i).duration
    Set child = voice.children(voice.i)
    
    voice.minX = x + getMinWidth(child) '' add necessary layout space 新增必要的佈局空間
    If (voice.i <> voice.children.Count - 1) Then
        voice.minX = voice.minX + child.minspacing '' add minimumspacing except On last elem 新增除最後一個元素之外的最小間距
    End If


    If voice.children.Count > voice.i + 1 Then
        nextTyps = voice.children(voice.i + 1).typs
    Else
        nextTyps = Cg.Other
    End If
    
      
    If (barDurAll + currDur) > 0 And _
    (barDurAll + currDur) Mod (Cg.BLEN / voice.meteB) = 0 And _
    nextTyps <> Cg.bar Then
        ''Debug.Print "all_" & voice.durationIndex & "   x_" & x
        voice.minX = x + getMinWidth(child) + child.minspacing + amt.wNote2note
    Else
        voice.minX = x + getMinWidth(child) + child.minspacing
    End If
End Sub '' call when spacingduration has been updated
'' call when spacingduration has been updated
Sub updateNextX(x As Double, spacing As Double, voice As VoiceElement)

    ''voice.nextX = x + (spacing * Math.Sqrt(voice.spacingduration / 384 / 1000 * 8))
    Dim barDurAll As Double
    Dim currDur As Double
    Dim nextTyps As Cg
    barDurAll = voice.barDurationIndex
    currDur = voice.children(voice.i).duration

    If voice.children.Count > voice.i + 1 Then
        nextTyps = voice.children(voice.i + 1).typs
    Else
        nextTyps = Cg.Other
    End If
    
      
    If (barDurAll + currDur) > 0 And _
    (barDurAll + currDur) Mod (Cg.BLEN / voice.meteB) = 0 And _
    nextTyps <> Cg.bar Then
        ''Debug.Print "all_" & voice.durationIndex & "   x_" & x
        voice.nextX = x + spacing * getSpacingUnits(voice) + amt.wNote2note
    Else
        voice.nextX = x + spacing * getSpacingUnits(voice)
    End If
End Sub '' call when spacingduration has been updated
Sub updateOtherNextX(x As Double, spacing As Double, voice As VoiceElement)

    ''voice.nextX = x + (spacing * Math.Sqrt(voice.spacingduration / 384 / 1000 * 8))
    Dim barDurAll As Double
    Dim currDur As Double
    Dim nextTyps As Cg
    barDurAll = voice.barDurationIndex
    currDur = voice.children(voice.i).duration

    If voice.children.Count > voice.i + 1 Then
        nextTyps = voice.children(voice.i + 1).typs
    Else
        nextTyps = Cg.Other
    End If

    
    If (barDurAll) > 0 And _
    (barDurAll) Mod (Cg.BLEN / voice.meteB) = 0 And _
    nextTyps <> Cg.bar Then
        ''Debug.Print "all_" & voice.durationIndex & "   x_" & x
        voice.nextX = x + spacing * getSpacingUnits(voice) + amt.wNote2note
    Else
        'voice.nextX = x + spacing * getSpacingUnits(voice)
    End If
End Sub

Sub updateIndices(voice As VoiceElement)
    If (layoutEnded(voice) = False) Then
        If voice.children(voice.i).typs = Cg.bar Then
            voice.barDurationIndex = 0
        Else
            voice.barDurationIndex = voice.barDurationIndex + voice.children(voice.i).duration
        End If
    
        voice.durationIndex = voice.durationIndex + voice.children(voice.i).duration
        If (voice.children(voice.i).typs = Cg.bar) Then
            '' everytime we meet a barline, do rounding to nearest 64th
            '' 每次遇到小節線時，都會四捨五入到最接近的第 64 位
            'voice.durationIndex = Round(voice.durationIndex / 6400) * 6400 '' 64) / 64 '' everytime we meet a barline, Do rounding To nearest 64th
        End If
        voice.i = voice.i + 1
    End If

End Sub
Function getExtraWidth(child As MusicItem, minPadding As Double) As Double   '' space needed To the left Of the note
    Dim padding As Double
    If (child.typs = Cg.note Or child.typs = Cg.bar) Then
        padding = minPadding
    End If
    getExtraWidth = -child.extraw + padding
End Function

Function getMinWidth(child As MusicItem) As Double  '' absolute space taken To the right Of the note
    getMinWidth = child.w
End Function

Attribute VB_Name = "newABCModule"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public Function VoiceElem(voicenumber As Integer, voicetotal As Integer) As VoiceElement
    Set VoiceElem = New VoiceElement
    VoiceElem.init voicenumber, voicetotal
End Function

Public Function AbstractEng(gTextSize As getTextSize, tuneNumber As Integer, options As Dictionary) As AbstractEngraver
    Set AbstractEng = New AbstractEngraver
    AbstractEng.init gTextSize, tuneNumber, options

End Function

Function RelativeElem(c As String, dx As Double, w As Double, pitch As Double, Optional opt As oRelativeOptions = Nothing) As RelativeElement
    Dim rElem As New RelativeElement
    rElem.init c, dx, w, pitch, opt
    
    Set RelativeElem = rElem
End Function

Function AbsoluteElem(slefelem, duration As Double, minspacing As Double, typs As String, tuneNumber As Integer, Optional options1 As Dictionary = Nothing)
    Dim abselem As New AbsoluteElement
    Dim vABC As VoiceABC
    If (TypeOf slefelem Is vClefProperties) Then
        Set vABC = slefelem.ToVoiceABC
    ElseIf (TypeOf slefelem Is vKeySignature) Then
        Set vABC = slefelem.ToVoiceABC
    ElseIf (TypeOf slefelem Is VoiceABC) Then
        Set vABC = slefelem
    Else
        Set vABC = slefelem.ToVoiceABC
    End If

    abselem.init vABC, duration, minspacing, typs, tuneNumber, options1
    Set AbsoluteElem = abselem
End Function

Public Function BeamElem(stemHeight As Double, typs As String, flat, Optional firstElement As VoiceABC = Nothing) As BeamElem
    Set BeamElem = New BeamElem
    BeamElem.init stemHeight, typs, flat, firstElement
End Function

Public Function BraceElem(voice As VoiceElement, typs As String) As BraceElem
    Dim brelem As New BraceElem
    brelem.init voice, typs
    Set BraceElem = brelem
End Function


Function TempoElem(tempo As vtempoProperties, tuneNumber As Integer) As TempoElement
    Set telem = New TempoElement
    telem.init tempo.ToVoiceABC, tuneNumber
    Set TempoElem = telem
End Function

Function TieElem(options As Dictionary) As TieElem
    Set tieEle = New TieElem
    tieEle.init options
    Set TieElem = tieEle
End Function



Public Function StaffGroupElem(gTextSize As getTextSize) As StaffGroupElement
    Set StaffGroupElem = New StaffGroupElement
    StaffGroupElem.init gTextSize
End Function

Attribute VB_Name = "oNoteHeadOptions"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public dir As String
Public headx As Double
Public extrax As Double
Public flag As String
Public dot As Integer
Public dotshiftx As Double
Public scale_ As Double
Public accidentalSlot As iArray
Public shouldExtendStem As Boolean
Public printAccidentals As Boolean

Attribute VB_Name = "oRelativeOptions"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public typs As String
Public klass As String
Public Name As String
Public anchor As String      '"start" | "middle" | "end"
Public position As String
Public dime As Variant
Public pitch2 As Double
Public realWidth As Double
Public lineWidth As Double
Public thickness As Double
Public stemHeight As Double
Public scalex As Double
Public scaley As Double
Public top As Double
Public bottom As Double
Public height As Double
Public width As Double

Attribute VB_Name = "point"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit


Public x As Double
Public y As Double
Public Z As Double

' #####################
' #    CONSTRUCTOR    #
' #####################
'Private Sub Class_Initialize()
'  Set iArray = New Collection
'End Sub

' #####################
' #  Getter / Setter  #
' #####################
'Attribute Element.VB_UserMemId = 0 saved in both procedures

'@DefaultMember
'Public Property Get element() As point
'    ' add Attribute element.VB_UserMemId = 0
'    Dim mm
'    Set mm = Me
'   Set element = mm
'End Property

'@DefaultMember
Public Property Let element(ByVal tmp As Variant)
Attribute element.VB_UserMemId = 0
    'add Attribute element.VB_UserMemId = 0
    If TypeOf tmp Is point Then
        x = tmp.x
        y = tmp.y
        Z = tmp.Z
    ElseIf (VarType(tmp) And vbArray) = vbArray Then
        If UBound(tmp) = 2 Then
            x = tmp(0)
            y = tmp(1)
            Z = tmp(2)
        ElseIf UBound(tmp) = 1 Then
            x = tmp(0)
            y = tmp(1)
            Z = 0
        End If
    ElseIf VarType(tmp) And vbVariant Then
              
    End If

End Property

' #############################
' # COMMON COLLECTION METHODS #
' #############################


Function c(xPt As Variant, yPt As Variant, Optional zPt As Variant = 0)
        x = IIf(IsNumeric(xPt), xPt, 0)
        y = IIf(IsNumeric(yPt), yPt, 0)
        Z = IIf(IsNumeric(zPt), zPt, 0)
        Set c = Me
End Function
Function a(varPt As Variant)
    If TypeOf varPt Is point Then
        x = varPt.x
        y = varPt.y
        Z = varPt.Z
    ElseIf UBound(varPt) >= 2 Then
        x = varPt(0)
        y = varPt(1)
        Z = varPt(2)
    ElseIf UBound(varPt) = 1 Then
        x = varPt(0)
        y = varPt(1)
        Z = 0
    End If
    Set a = Me
End Function

Function at() As Double()
    Dim dd(0 To 2) As Double
    dd(0) = x
    dd(1) = y
    dd(2) = Z
     at = dd
End Function
Function clone() As point
    Dim pp As point
    Set pp = New point
    pp.c x, y, Z
    Set clone = pp
End Function

Function ToArray()
    Dim tarr(2)
    tarr(0) = x
    tarr(1) = y
    tarr(2) = Z
    ToArray = tarr
End Function
Function ToDouble() As Double()
    Dim arrD(2) As Double
    arrD(0) = x
    arrD(1) = y
    arrD(2) = Z
    ToDouble = arrD
End Function

Attribute VB_Name = "preferences"
Option Explicit


Type AMusicType
    DEFINE_FontFileName  As String          '預設字型的名字
    DEFINE_TEXT_SIZE As Double          '預設字型的大小

    
    A_TEXT_WIDTH   As Double   '預設一個字的寬度  字形的 百分比

    LINE_PASE As Double '''這是從原點 要高 字形的 百分比
    LINE_JUMP   As Double                   '每一個拍線和拍線的間格 字形的 百分比
    LINE_THICKNESS   As Double                   '這是拍線的厚度 字形的 百分比
    LINE_LEN   As Double                   '這是拍線的長度 字形的 百分比

    DROP_UP   As Double                   '高八度的位置  字形的 百分比
    DROP_DOWN   As Double                   '低八度的位置  字形的 百分比
    DROP_CIRCLE_RADIUS_SIZE   As Double                   '圓的 直徑 SIZE 字形的 百分比
    DROP_INTERVAL  As Double                   '每八度的間距 字形的 百分比
    DROP_ADD_LINE_INTERVAL  As Double                   '下點 多一條線點要下去多少  字形的 百分比

    BAR_WITCH As Double    '小節線的粗細

    'IsGiFill As Boolean                 '在閉合的圖形元素上產生填充區域
    IsGiFill As Boolean                 '是否填充區域
    IsDebugDialog As Boolean                 '是否叫出 DebugDialog

    IsDrawCursory As Boolean                 '是否 繪自定的點
    mHowData As Integer        '有多少行資料
    
    iTONE As Integer         ' * 行
    iFinge As Integer    '這是指法行     _+)(*&
    iScale  As Integer     '這是過低音行   .,:
    iNote  As Integer      '這為主行       1234567.|l
    iTempo  As Integer    '這是拍子       -=368acefz
    iTowFinge  As Integer     '這是指法行第二行  _+)(*&
    iSlur  As Integer         ' 連音符行    (3456)
    iAdd As Integer           '這是合音行 [2467]
    
    L_BUF_MD  As Integer   '這是看Buf_md要多少行
    L_WHAT  As Integer    '這是指法看要放在那一行
    
    
    
    f一指 As Integer
    f二指 As Integer
    f三指 As Integer
    f四指 As Integer
    f空弦 As Integer
    f揉弦 As Integer
    
    '2015/1/10 設定圖塊的資料，駐點的位置不一樣
    
    bkMidHight As Double    '物件中間下點的高度
    bkMidUpHight As Double    '物件中間上點的高度
    
    bkInster_Line_H As Double    '物件原點跟拍線的高度
    barInsterNumberSize As Double   '小節號字大小
    
    
    wBar As Double          '小節線的寬度
    wMete As Double         '拍號的寬度
    wNote As Double         '音符的寬度
    wOther As Double
    wNote2note As Double    '每拍到每拍的間距

    extraScale As Double    '前綴元素 比例
End Type

Public amt As AMusicType
Public rTime As runTime

'MusicTextBlock  畫圖塊用資料

Public Type MusicFing
    sTONE As String        ' 升降記號 行
    sFinge As String   '這是指法行     _+)(*&
    sScale As String   '這是高低音行   .,:
    sNote As String   '這為主行       1234567.|l
    sTempo As String   '這是拍子       -=368acefz
    sTowFinge As String   '這是指法行第二行  _+)(*&
    sSlur As String
    
    iScale As Integer     '這是高低音行   .,:
    iNote As Integer     '這為主行       1234567.|l
    iTempo As Integer    '這是拍子       -=368acefz
    mfPosition As point    '這是看這第一指法字上下移多少
    mfTowPosition As point '這是看這第二指法字上下移多少
End Type


'音附的駐點位置
Public Type GripPoints
    gptMid As point       '在正中間
    gptLeftDown As point     '在左下
    gptMidUp As point     '在中上
    gptLeft As point      '在左中
    gptRight As point      '在右中
    atPt As point           '備注點
End Type

    
Public Type Glode
    check1 As Boolean
    fontName As String
    fontsize As Double
    Many As Integer     '幾聲部設定
    bar As Integer
    mete As Integer     '3/4 拍號的分子 --> 3
    mete2 As Integer    '3/4 拍號的分母 --> 4
    
    
    barsperstaff  As Integer '設定每行幾小節
    durationIndex As Double ''累記 現在已經讀取每小節的音符長度總合
    currLine As Integer     '現在是第幾行
    currMeasure As Integer     '現在是 這行的第幾小節
    
    pagewidth As Double
    LeftSpace As Double
    RightSpace As Double
    BarToNoteSpace As Double     '小節線到音符的空白
    TrackToTrack As Double
    LineToLine As Double
    MIN_X As Double
    Beat_MIN_X As Double
    IsBarAlign As Boolean       '小節是否對齊
    
    isVirtualChar As Boolean    '空心字
    
    lastRightPoint As New point '計錄最後一個元素的 右邊點
End Type


    ''''''''''''''''''''''''''''''''''
Sub AMT_LOAD()
    Dim DEFINE_TEXT_SIZE  As Double
    amt.DEFINE_FontFileName = "細明體"              '預設字型的名字
    amt.DEFINE_TEXT_SIZE = 1000              '預設字型的大小
    DEFINE_TEXT_SIZE = 1000
    
    amt.A_TEXT_WIDTH = 726# / DEFINE_TEXT_SIZE               '預設一個字的寬度  字形的 百分比
    
    amt.LINE_PASE = 592.2 / DEFINE_TEXT_SIZE            '這是從原點 要高 字形的 百分比
    amt.LINE_JUMP = 155 / DEFINE_TEXT_SIZE            '每一個拍線和拍線的間格 字形的 百分比
    amt.LINE_THICKNESS = 65 / DEFINE_TEXT_SIZE            '這是拍線的厚度 字形的 百分比
    amt.LINE_LEN = 723.5 / DEFINE_TEXT_SIZE            '這是拍線的長度 字形的 百分比
    
    amt.DROP_UP = 1950# / DEFINE_TEXT_SIZE             '高八度的位置  字形的 百分比
    amt.DROP_DOWN = 500# / DEFINE_TEXT_SIZE             '低八度的位置  字形的 百分比
    amt.DROP_CIRCLE_RADIUS_SIZE = 200# / DEFINE_TEXT_SIZE / 2           '圓的 直徑 SIZE 字形的 百分比
    amt.DROP_INTERVAL = 290# / DEFINE_TEXT_SIZE             '每八度的間距 字形的 百分比
    amt.DROP_ADD_LINE_INTERVAL = 170# / DEFINE_TEXT_SIZE               '下點 多一條線點要下去多少  字形的 百分比
    
    amt.BAR_WITCH = 340 / DEFINE_TEXT_SIZE                '小節線的粗細

    '''bool  IsGiFill    =true ''在閉合的圖形元素上產生填充區域
    amt.IsGiFill = False '是否填充區域
    amt.IsDebugDialog = False      '是否叫出 DebugDialog

    amt.IsDrawCursory = True    '是否 繪自定的點

    amt.mHowData = 9    '有9行的資料

    amt.iTONE = 1        ' * 行
    amt.iFinge = 2    '這是指法行     _+)(*&
    amt.iScale = 3    '這是高低音行   .,:
    amt.iNote = 4     '這為主行       1234567.|l
    amt.iTempo = 5    '這是拍子       -=368acefz
    amt.iTowFinge = 6    '這是指法行第二行  _+)(*&
    amt.iSlur = 7        ' 連音符行    (3456)
    amt.iAdd = 8        ' 合音符行    [3456]
    
    amt.L_BUF_MD = 9  '這是看Buf_md要多少行
    amt.L_WHAT = 8    '這是指法看要放在那一行

    '二胡用
    amt.f一指 = 1
    amt.f二指 = 2
    amt.f三指 = 4
    amt.f四指 = 8
    amt.f空弦 = 16
    amt.f揉弦 = 32
    
    
    
    '2015/1/10 設定圖塊的資料，駐點的位置不一樣
    amt.bkMidHight = 690# / DEFINE_TEXT_SIZE      '物件中間下點的高度
    amt.bkMidUpHight = 1690# / DEFINE_TEXT_SIZE     '物件中間上點的高度
    amt.bkInster_Line_H = 97.8 / DEFINE_TEXT_SIZE    '物件原點跟拍線的高度
    amt.barInsterNumberSize = 0.6
    
    
    amt.wBar = 1    '小節線的寬度
    amt.wMete = 1      '拍號的寬度
    amt.wNote = 0.75        '音符的寬度
    amt.wOther = 1
    amt.wNote2note = 0.5 '每拍到每拍的間距
    
    amt.extraScale = 0.6 '
    
End Sub

Attribute VB_Name = "runTime"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
'MIT License
'
'Copyright (c) 2019-2021 Petr Katerinak
'
'Permission is hereby granted, free of charge, to any person obtaining a copy
'of this software and associated documentation files (the "Software"), to deal
'in the Software without restriction, including without limitation the rights
'to use, copy, modify, merge, publish, distribute, sublicense, and/or sell
'copies of the Software, and to permit persons to whom the Software is
'furnished to do so, subject to the following conditions:
'
'The above copyright notice and this permission notice shall be included in all
'copies or substantial portions of the Software.
'
'THE SOFTWARE IS PROVIDED "AS IS", WITHOUT WARRANTY OF ANY KIND, EXPRESS OR
'IMPLIED, INCLUDING BUT NOT LIMITED TO THE WARRANTIES OF MERCHANTABILITY,
'FITNESS FOR A PARTICULAR PURPOSE AND NONINFRINGEMENT. IN NO EVENT SHALL THE
'AUTHORS OR COPYRIGHT HOLDERS BE LIABLE FOR ANY CLAIM, DAMAGES OR OTHER
'LIABILITY, WHETHER IN AN ACTION OF CONTRACT, TORT OR OTHERWISE, ARISING FROM,
'OUT OF OR IN CONNECTION WITH THE SOFTWARE OR THE USE OR OTHER DEALINGS IN THE
'SOFTWARE.
'
' Version of iArray: 1.0
''修正 元素從 0 開始

Private iArray As Collection
Private dict As Dictionary
Private i As Long ' Counter

' #####################
' #    CONSTRUCTOR    #
' #####################
Private Sub Class_Initialize()
  Set iArray = New Collection
  Set dict = New Dictionary
End Sub

' #####################
' #  Getter / Setter  #
' #####################
'Attribute Element.VB_UserMemId = 0 saved in both procedures

'@DefaultMember
Public Sub element(ByVal timeName As String)
Attribute element.VB_UserMemId = 0
    If timeName = "" Or timeName = " " Then
        
        Exit Sub
    End If
    Dim tt
    Dim iaa As iArray
    If IsObject(dict(timeName)) Then
        dict(timeName).Push Timer
        
    ElseIf IsEmpty(dict(timeName)) Then
    
        Set dict(timeName) = New iArray
        dict(timeName).Push Timer
        
    End If
    tt = dict.keys
    
    
 
End Sub
'
''@DefaultMember
'Public Property Let element(ByVal index As Long, ByVal val As Variant)
'  If index + 1 > iArray.Count Then
'    Dim eMsg As String
'    eMsg = IIf(iArray.Count > 0, _
'               "Index (" & index + 1 & ") out of iArray bounds (1-" & iArray.Count & ")", _
'               "iArray doesn't have any indexes")
'    err.Raise Number:=9, Description:=eMsg
'    Exit Property
'  End If
'  iArray.Remove index + 1
'  iArray.Add val, before:=index + 1
'End Property

' #############################
' # COMMON COLLECTION METHODS #
' #############################
Public Function Count() As Long
  Count = iArray.Count
End Function
Public Sub Add(ByVal val As Variant, Optional ByVal bef As Variant = Empty, Optional ByVal aft As Variant = Empty)
  If IsEmpty(bef) And IsEmpty(aft) Then
    iArray.Add val
  ElseIf IsEmpty(bef) Then
    iArray.Add val, , , aft
  ElseIf IsEmpty(aft) Then
    iArray.Add val, , bef
  Else
    iArray.Add val, , bef, aft
  End If
End Sub
Public Sub Remove(index As Long)
  iArray.Remove index + 1
End Sub

'Clear
' Empties iArray
Public Function Clear() As Boolean
  For i = iArray.Count - 1 To 0 Step -1
    iArray.Remove i + 1
  Next i
  Clear = IIf(iArray.Count = 0, True, False)
End Function

'Clone
' Makes a hard copy of the iArray
' @return iArray | Return exact copy of itself
Public Function clone() As iArray
  Set clone = New iArray
  For i = 0 To Me.Count - 1
    clone.Push Me(i)
  Next i
End Function


'Sum
' Calculates the sum of the numeric iArray.
' @return Variant | Sum value / "NaN" if iArray contains non-numeric value(s)
Public Function sum() As Variant
  If Not Me.ContainsOnlyNumeric Then sum = "NaN": Exit Function
  sum = 0
  Dim el As Variant
  For Each el In iArray
    sum = sum + el
  Next el
End Function



Public Function ToList()
  If dict.Count = 0 Then
    Exit Function
  End If
  
  Dim sn As String
  Dim j As Integer
  Dim k As Integer
  Dim iaa As iArray
  Dim sum As Double
  Dim stime As Double
  Dim etime As Double
  Debug.Print "******** run Time sum   *********"
  For j = 0 To UBound(dict.keys)
    sn = dict.keys(j)
    Set iaa = dict(sn)
    If iaa.Count Mod 2 <> 0 Then
        Debug.Print sn & " 資料沒結束."
    End If
    sum = 0
    For k = 0 To iaa.Count - 1 Step 2
        If k + 1 < iaa.Count Then
           sum = sum + iaa(k + 1) - iaa(k)
        End If
    Next
    Debug.Print Format(sn, "@@@@@@@@@@@@@@@@") & " : " & Format(CStr(sum), "000.000000") & "秒"
  Next
  
  
End Function

'ToString
' Creates string representation of the iArray.
' @param String delimiter | Optional character to separate the iArray's elements (default = ";")
' @return String | Formated representation of tha iArray
Public Function ToString(Optional ByVal delimiter As String = ";") As String
  If Me.Count = 0 Then ToString = "{}": Exit Function
  ToString = vbNullString
  For i = 0 To Me.Count - 1
    If i = 0 Then ToString = ToString + "{"
    If i > 0 Then ToString = ToString + delimiter
    If VarType(Me(i)) = vbString Then
        ToString = ToString + Chr$(34)
        ToString = ToString + CStr(Me(i))
        ToString = ToString + Chr$(34)
    ElseIf TypeOf Me(i) Is iArray Then
        ToString = ToString + Me(i).ToString(delimiter)
    ElseIf (VarType(Me(i)) And vbArray) = vbArray Then
        ToString = ToString + "[Array]"
    ElseIf VarType(Me(i)) = vbObject Then
        ToString = ToString + "[Object]"
    Else
        ToString = ToString + CStr(Me(i))
    End If
    
    If i = iArray.Count - 1 Then ToString = ToString + "}"
  Next i
End Function

Attribute VB_Name = "ttfdump"
Attribute VB_Base = "0{CDB9CEFA-C39A-4108-A135-EC13F6D011B7}{7480EEB2-CA30-44C2-90BB-5A97E9CCB0A5}"
Attribute VB_GlobalNameSpace = False
Attribute VB_Creatable = False
Attribute VB_PredeclaredId = True
Attribute VB_Exposed = False
Attribute VB_TemplateDerived = False
Attribute VB_Customizable = False

Option Explicit

Dim xylist As New PointList

Private Sub comDrawing_Click()
    Dim pt As Variant
    Dim xyString As String
    Dim sX As String
    Dim sY As String
    Dim i As Long
    
    Me.Hide
    ' Return a point using a prompt
    pt = ThisDrawing.Utility.GetPoint(, "\n選擇要插入的點 ：Enter insertion point: ")
    '畫出定位線
    
    For i = 0 To xylist.size - 1
        sX = xylist.at(i).x + pt(0)
        sY = xylist.at(i).y + pt(1)
        xyString = xyString & sX & "," & sY & " "
    Next
    
    ThisDrawing.SendCommand "line " & xyString
    
End Sub

Private Sub CommandButton1_Click()
    Dim arr As Variant
    Dim SearchString, SearchChar, MyPos
    
    SearchChar = "abs"    ' 要尋找字串 "abs"。
    Dim i As Long
    Dim y As Long
    Dim pt As New point
    Dim SStr As String
    arr = Split(Me.TextBox1.text, vbCrLf)

    xylist.clean
    Me.TextBox2.text = ""
    For i = 0 To UBound(arr) - 1
        If InStr(1, arr(i), "ABS", 1) <> 0 Then
            SearchString = arr(i)   ' 被搜尋的字串。
            ' 小寫 p 和大寫 P 在 [文字比對] 下是一樣的。
            MyPos = InStr(1, SearchString, SearchChar, 1)
            arr(i) = Mid(arr(i), MyPos, Len(arr(i)))    '取得 ABS()的資料
            
                
            SStr = Replace(arr(i), " ", "")       '空白移除
            
            Set pt = getABS_XY(SStr)
            Call xylist.addpt(pt)
        End If
        Me.TextBox2 = Me.TextBox2 & pt.x & "," & pt.y & vbCrLf
        'Me.TextBox2 = Me.TextBox2.text & vbCrLf & ARR(i) '看資料
    Next
'
'    For i = 0 To UBound(ARR) - 1
'        Me.TextBox2 = Me.TextBox2.text & vbCrLf & ARR(i)
'    Next
End Sub

Private Function getABS_XY(dataXY As String) As point
'取得括弧內的 xy 資料
    Dim fpos As Integer
    Dim mpos As Integer
    Dim lpos As Integer
    Dim i As Integer
    Dim sX As String
    Dim sY As String
    Dim tPt As New point
    
    fpos = InStr(1, dataXY, "(")
    mpos = InStr(1, dataXY, ",")
    lpos = InStr(fpos, dataXY, ")")
    
    sX = Mid(dataXY, fpos + 1, mpos - fpos - 1)
    sY = Mid(dataXY, mpos + 1, lpos - mpos - 1)
    tPt.x = CDbl(sX)
    tPt.y = CDbl(sY)
    Set getABS_XY = tPt
End Function

Attribute VB_Name = "vAccidental"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public acc As String
Public note As String
Public verticalPos As Double

Attribute VB_Name = "vBox"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public left As Double
Public top As Double
Public right As Double
Public bottom As Double

Attribute VB_Name = "vCharRange"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public startChar As Integer
Public endChar As Integer

Attribute VB_Name = "vClefProperties"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public typs As String
Public el_typs As String
Public verticalPos As Double
Public clefPos As Double

Public stafflines As Double
Public staffscale As Double
Public transpose As Double

Public Function ToVoiceABC() As VoiceABC
        Set ToVoiceABC = New VoiceABC
        ToVoiceABC.typs = Me.typs
        ToVoiceABC.el_typs = Me.el_typs
        ToVoiceABC.verticalPos = Me.verticalPos
        ToVoiceABC.clefPos = Me.clefPos
        ToVoiceABC.stafflines = Me.stafflines
        ToVoiceABC.staffscale = Me.staffscale
        ToVoiceABC.transpose = Me.transpose


End Function

Attribute VB_Name = "vFixedCoords"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public x As Double
Public y As Double
Public w As Double
Public h As Double
Public t As Double
Public B As Double

Attribute VB_Name = "vFont"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public face As String
Public size As Double
Public weight As String
Public style As String
Public decoration As String
Public box As Boolean

Attribute VB_Name = "vFormatting"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public alignbars As Double
Public aligncomposer As String 'Alignment
Public auquality As String
Public bagpipes As Boolean
Public botmargin As Double
Public botspace As Double
Public bstemdown As Boolean
Public composerspace As Double
Public continueall As Boolean
Public continuous As String
Public dynalign As Boolean
Public exprabove As Boolean
Public exprbelow As Boolean
Public flatBeams As Boolean
Public footer As String
Public freegchord As Boolean
Public gchordbox As Boolean
Public graceSlurs As Boolean
Public gracespacebefore As Double
Public gracespaceinside As Double
Public gracespaceafter As Double
Public header As String
Public INDENT As Double
Public infoline As Boolean
Public infospace As Double
Public leftmargin As Double
Public linesep As Double
Public lineskipfac As Double
Public map As String
Public maxshrink As Double
Public maxstaffsep As Double
Public maxsysstaffsep As Double
Public measurebox As Boolean
Public midi As New Dictionary
'{
'Public barlines As MidiParam
'Public bassprog As MidiParam
'Public bassvol As MidiParam
'Public beat As MidiParam
'Public beataccents As MidiParam
'Public beatmod As MidiParam
'Public beatstring As MidiParam
'Public bendvelocity As MidiParam
'Public c As MidiParam
'Public channel As MidiParam
'Public chordattack As MidiParam
'Public chordname As MidiParam
'Public chordprog As MidiParam
'Public chordvol As MidiParam
'Public control As MidiParam
'Public controlcombo As MidiParam
'Public deltaloudness As MidiParam
'Public drone As MidiParam
'Public droneoff As MidiParam
'Public droneon As MidiParam
'Public drum As MidiParam
'Public drumbars As MidiParam
'Public drummap: MidiParam
'Public drumoff As MidiParam
'Public drumon As MidiParam
'Public expand As MidiParam
'Public fermatafixed As MidiParam
'Public fermataproportional As MidiParam
'Public gchord As MidiParam
'Public gchordon As MidiParam
'Public gchordoff As MidiParam
'Public grace As MidiParam
'Public gracedivider As MidiParam
'Public makechordchannels As MidiParam
'Public nobarlines As MidiParam
'Public nobeataccents As MidiParam
'Public noportamento As MidiParam
'Public pitchbend As MidiParam
'Public program As MidiParam
'Public portamento As MidiParam
'Public ptstress As MidiParam
'Public randomchordattack As MidiParam
'Public ratio As MidiParam
'Public rtranspose As MidiParam
'Public snt As MidiParam
'Public stressmodel As MidiParam
'Public temperamentlinear As MidiParam
'Public temperamentnormal As MidiParam
'Public transpose As MidiParam
'Public trim As MidiParam
'Public volinc: MidiParam
'public   }
Public musicspace As Double
Public nobarcheck As String
Public noteSpacingFactor As Double
Public parskipfac As Double
Public partsbox As Boolean
Public partsspace As Double
Public percmap As New iArray   'Array<PercMapElement>
Public playtempo As String
Public rightmargin As Double
Public scale_ As Double
Public score As String
Public slurHeight As Double
Public splittune As Boolean
Public squarebreve As Boolean
Public staffsep As Double
Public staffwidth As Double
Public stemHeight As Double
Public straightflags As Boolean
Public stretchLast As Double
Public stretchstaff As Boolean
Public subtitlespace As Double
Public sysstaffsep As Double
Public systemsep As Double
Public textspace As Double
Public titleformat As String
Public titleleft As Boolean
Public titlespace As Double
Public topmargin As Double
Public topspace As Double
Public vocalabove As Boolean
Public vocalspace As Double
Public wordsspace As Double
Public annotationfont As vFont
Public composerfont As vFont
Public footerfont As vFont
Public gchordfont As vFont
Public headerfont As vFont
Public historyfont As vFont
Public infofont As vFont
Public measurefont As vFont
Public pageheight As Double
Public pagewidth As Double
Public partsfont As vFont
Public repeatfont As vFont
Public subtitlefont As vFont
Public tabgracefont As vFont
Public tablabelfont As vFont
Public tabnumberfont As vFont
Public tempofont As vFont
Public textfont As vFont
Public titlefont As vFont
Public tripletfont As vFont
Public vocalfont As vFont
Public voicefont As vFont
Public wordsfont As vFont


Public jazzchords As Boolean

Attribute VB_Name = "vGlyphTyps"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public d As String
Public w As Double
Public h As Double

Attribute VB_Name = "vKeySignature"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public el_typs As String
Public accidentals As iArray     'Array<Accidental>;
Public root As String
Public acc As String
Public mode As String

Public Function ToVoiceABC() As VoiceABC
        Set ToVoiceABC = New VoiceABC
        ToVoiceABC.el_typs = Me.el_typs
        Set ToVoiceABC.accidentals = Me.accidentals
        ToVoiceABC.root = Me.root
        ToVoiceABC.acc = Me.acc
        ToVoiceABC.mode = Me.mode
End Function

Attribute VB_Name = "vMetaText"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public abc_copyright As String
Public abc_creator As String
Public abc_version As String
Public abc_charset As String
Public abc_edited_by As String
Public author As String
Public book As String
Public composer As String
Public decorationPlacement As String     'Placement
Public discography As String
Public footer As Dictionary
Public group As String
Public header As Dictionary
Public history As String
Public instruction As String
Public measurebox As Boolean
Public notes As String
Public origin As String
Public partOrder As String
Public rhythm As String
Public source As String
Public tempo As vtempoProperties
Public textBlock As String
Public title As String
Public transcription As String
Public unalignedWords As iArray
Public url As String

Attribute VB_Name = "vMetaTextInfo"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public abc_copyright       As vCharRange
Public abc_creator       As vCharRange
Public abc_version       As vCharRange
Public abc_charset       As vCharRange
Public abc_edited_by       As vCharRange
Public author As vCharRange
Public book As vCharRange
Public composer As vCharRange
Public discography As vCharRange
Public footer As vCharRange
Public group As vCharRange
Public header As vCharRange
Public history As vCharRange
Public instruction As vCharRange
Public notes As vCharRange
Public origin As vCharRange
Public partOrder As vCharRange
Public rhythm As vCharRange
Public source As vCharRange
Public tempo As vCharRange
Public textBlock As vCharRange
Public title As vCharRange
Public transcription As vCharRange
Public unalignedWords As vCharRange
Public url As vCharRange

Attribute VB_Name = "vMeter"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public el_typs As String
Public typs As String
Public value As vMeterFractionList       ' Array<MeterFraction>;
Public beat_division   As vMeterFractionList   'Array<MeterFraction>;

Public Function ToVoiceABC() As VoiceABC
        Set ToVoiceABC = New VoiceABC
        ToVoiceABC.el_typs = Me.el_typs
        ToVoiceABC.typs = Me.typs
        Set ToVoiceABC.value = Me.value
        Set ToVoiceABC.beat_division = Me.beat_division
        
End Function

Attribute VB_Name = "vMeterFraction"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public num As Double
Public den As Double

Attribute VB_Name = "vMeterFractionList"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
'MIT License
'
'Copyright (c) 2019-2021 Petr Katerinak
'
'Permission is hereby granted, free of charge, to any person obtaining a copy
'of this software and associated documentation files (the "Software"), to deal
'in the Software without restriction, including without limitation the rights
'to use, copy, modify, merge, publish, distribute, sublicense, and/or sell
'copies of the Software, and to permit persons to whom the Software is
'furnished to do so, subject to the following conditions:
'
'The above copyright notice and this permission notice shall be included in all
'copies or substantial portions of the Software.
'
'THE SOFTWARE IS PROVIDED "AS IS", WITHOUT WARRANTY OF ANY KIND, EXPRESS OR
'IMPLIED, INCLUDING BUT NOT LIMITED TO THE WARRANTIES OF MERCHANTABILITY,
'FITNESS FOR A PARTICULAR PURPOSE AND NONINFRINGEMENT. IN NO EVENT SHALL THE
'AUTHORS OR COPYRIGHT HOLDERS BE LIABLE FOR ANY CLAIM, DAMAGES OR OTHER
'LIABILITY, WHETHER IN AN ACTION OF CONTRACT, TORT OR OTHERWISE, ARISING FROM,
'OUT OF OR IN CONNECTION WITH THE SOFTWARE OR THE USE OR OTHER DEALINGS IN THE
'SOFTWARE.
'
' Version of iArray: 1.0
''修正 元素從 0 開始

Private mainArray As New Collection
Private i As Long ' Counter

' #####################
' #    CONSTRUCTOR    #
' #####################
'Private Sub Class_Initialize()
'  Set mainArray = New Collection
'End Sub

' #####################
' #  Getter / Setter  #
' #####################
'Attribute Element.VB_UserMemId = 0 saved in both procedures

'@DefaultMember
Public Property Get element(ByVal index As Long) As vMeterFraction
Attribute element.VB_UserMemId = 0
    If index + 1 < 1 Or index + 1 > mainArray.Count Then
        Set element = Nothing
        Exit Property
    End If
    If IsObject(mainArray(index + 1)) = True Then
        Set element = mainArray(index + 1)
    Else
        element = mainArray(index + 1)
    End If

 
End Property

'@DefaultMember
Public Property Let element(ByVal index As Long, ByVal val As vMeterFraction)
Attribute element.VB_UserMemId = 0
  If index = 0 And mainArray.Count = 0 Then
    Me.Push val
    Exit Property
  End If
  If index + 1 > mainArray.Count Then
    Dim eMsg As String
    eMsg = IIf(mainArray.Count > 0, _
               "Index (" & index + 1 & ") out of iArray bounds (1-" & mainArray.Count & ")", _
               "iArray doesn't have any indexes")
    err.Raise Number:=9, Description:=eMsg
    Exit Property
  End If
  mainArray.Add val, after:=index + 1
  mainArray.Remove index + 1
End Property

' #############################
' # COMMON COLLECTION METHODS #
' #############################
Public Function Count() As Long
  Count = mainArray.Count
End Function
Public Sub Add(ByVal val As vMeterFraction, Optional ByVal bef As Variant = Empty, Optional ByVal aft As Variant = Empty)
  If IsEmpty(bef) And IsEmpty(aft) Then
    mainArray.Add val
  ElseIf IsEmpty(bef) Then
    mainArray.Add val, , , aft
  ElseIf IsEmpty(aft) Then
    mainArray.Add val, , bef
  Else
    mainArray.Add val, , bef, aft
  End If
End Sub
Public Sub Remove(index As Long)
  mainArray.Remove index + 1
End Sub

' ####################
' #  PUBLIC METHODS  #
' ####################

'AddAfter
' Adds element after given index.
' {1,2,3} -> index >= 3 -> Push val
' {1,2,3} -> index < 1 -> Unshift val
' {} -> index = any -> Push val
' @param Long index | Index after which will be added an element
' @param Variant val | One element (String, number, ...) to add into iArray
' @return Long | Count of elements inside iArray
Public Function AddAfter(ByVal index As Long, ByVal val As vMeterFraction) As Long
  If Me.Count < 1 Or index + 1 >= Me.Count Then
    Me.Push val
  ElseIf index + 1 < 1 Then
    Me.Unshift val
  Else
    Me.Add val, aft:=index + 1
  End If
  AddAfter = Me.Count
End Function

'AddArrayAfter
' Adds elements after given index.
' {1,2,3} -> index >= 3 -> PushArray val
' {1,2,3} -> index < 1 -> UnshiftArray val
' {} -> index = any -> PushArray val
' @param Long index | Index after which will be added an element
' @param Variant val | Array() or iArray of elements to add into iArray
' @return Long | Count of elements inside iArray
Public Function AddArrayAfter(ByVal index As Long, ByVal val As Variant) As Long
  If Me.Count < 1 Or index + 1 >= Me.Count Then
    Me.PushArray val
  ElseIf index + 1 < 1 Then
    Me.UnshiftArray val
  Else
    If TypeOf val Is vMeterFractionList Then
      For i = 0 To val.Count - 1
        Me.Add val(i), aft:=index + 1
        Inc index
      Next i
    Else
      For i = LBound(val) To UBound(val)
        Me.Add val(i), aft:=index + 1
        Inc index
      Next i
    End If
  End If
  AddArrayAfter = Me.Count
End Function

'AddArrayBefore
' Adds elements before given index.
' {1,2,3} -> index > 3 -> PushArray val
' {1,2,3} -> index <= 1 -> UnshiftArray val
' {} -> index = any -> PushArray val
' @param Long index | Index after which will be added an element
' @param Variant val | Array() or iArray of elements to add into iArray
' @return Long | Count of elements inside iArray
Public Function AddArrayBefore(ByVal index As Long, ByVal val As Variant) As Long
  If Me.Count < 1 Or index + 1 > Me.Count Then
    Me.PushArray val
  ElseIf index <= 0 Then
    Me.UnshiftArray val
  Else
    If TypeOf val Is vMeterFractionList Then
      For i = val.Count - 1 To 0 Step -1
        Me.Add val(i), bef:=index + 1
      Next i
    Else
      For i = UBound(val) To LBound(val) Step -1
        Me.Add val(i), bef:=index + 1
      Next i
    End If
  End If
  AddArrayBefore = Me.Count
End Function

'AddBefore
' Adds element before given index.
' {1,2,3} -> index > 3 -> Push val
' {1,2,3} -> index <= 1 -> Unshift val
' {} -> index = any -> Push val
' @param Long index | Index before which will be added an element
' @param Variant val | One element (String, number, ...) to add into iArray
' @return Long | Count of elements inside iArray
Public Function AddBefore(ByVal index As Long, ByVal val As vMeterFraction) As Long
  If Me.Count < 1 Or index + 1 > Me.Count Then
    Me.Push val
  ElseIf index + 1 <= 1 Then
    Me.Unshift val
  Else
    Me.Add val, bef:=index + 1
  End If
  AddBefore = Me.Count
End Function

'Avg
' Calculates the average of the numeric mainArray.
' @return Variant | Average value / "NaN" if iArray contains non-numeric value(s)
Public Function Avg() As Variant
  If Not Me.ContainsOnlyNumeric Then Avg = "NaN": Exit Function
  Avg = Me.sum / Me.Count
End Function

'Clear
' Empties iArray
Public Function Clear() As Boolean
  For i = mainArray.Count - 1 To 0 Step -1
    mainArray.Remove i + 1
  Next i
  Clear = IIf(mainArray.Count = 0, True, False)
End Function

'Clone
' Makes a hard copy of the mainArray
' @return mainArray | Return exact copy of itself
Public Function clone() As vMeterFractionList
  Set clone = New vMeterFractionList
  For i = 0 To Me.Count - 1
    clone.Push Me(i)
  Next i
End Function

'Contains
' Checks if given value is used inside mainArray.
' @param Variant val | One element (String, number, ...) to by checked if it exists in iArray
' $return Boolean | True = exists, False = doesn't exists
Public Function Contains(ByVal val As vMeterFraction) As Boolean
  Contains = False
  Dim el As Variant
  For Each el In mainArray
    If IsObject(val) = True Or VarType(val) And 8192 Then
        If (VarType(el) And 8192) And (VarType(val) And 8192) Then
            If ArrayDifference(el, val) Then
                Contains = True: Exit Function
            End If
        ElseIf IsObject(el) = True And IsObject(val) = True Then
            If el Is val Then
                Contains = True: Exit Function
            End If
        End If
    Else
        If IsObject(el) = False And (VarType(el) And 8192) <> 8192 Then
            If el = val Then
            Contains = True: Exit Function
            End If
        End If
    End If
  Next el
End Function

'ContainsAll
' Checks if all given values are used inside mainArray.
' @param Variant val | values to by checked if it exists in iArray
' $return Boolean | True = all exists, False = one ore more values doesn't exists
Public Function ContainsAll(ByVal val As vMeterFractionList) As Boolean
  ContainsAll = False
  Dim foundOccurrences As Integer: foundOccurrences = 0
  Dim values As New vMeterFractionList
  If Not TypeOf val Is vMeterFractionList Then
    If IsArray(val) Then
      values.PushArray (val)
    Else
      values.Push (val)
    End If
  Else
    Set values = val
  End If
  For i = 0 To values.Count - 1
    If Me.Contains(values(i)) Then Inc foundOccurrences
  Next i
  If foundOccurrences = values.Count Then ContainsAll = True
End Function

'CountOccurrences
' Checks how many times is given value used inside mainArray.
' @param Variant val | One element (String, number, ...) to by checked
' @return Long | Count of matched occurrences
Public Function CountOccurrences(val As Variant) As Long
  CountOccurrences = 0
  Dim el As Variant
  For Each el In mainArray
  
    If IsObject(val) = True Or VarType(val) And 8192 Then
        If VarType(el) And 8192 And VarType(val) And 8192 Then
            If ArrayDifference(el, val) Then
                Inc CountOccurrences
                Exit Function
            End If
        ElseIf IsObject(el) = True And IsObject(val) = True Then
            If el Is val Then
                Inc CountOccurrences
                Exit Function
            End If
        End If
    Else
        If IsObject(el) = False And Not (VarType(el) And 8192) Then
            If el = val Then
                Inc CountOccurrences
                Exit Function
            End If
        End If
    End If
  
     'If el = val Then Inc CountOccurrences
  Next el
End Function

'Dequeue
' Removes an element from the begining of the mainArray.
' @return Variant | Removed element or Empty, if iArray is empty
'刪除開頭一個元素。
Public Function Dequeue() As vMeterFraction
  Dequeue = Empty
  If mainArray.Count > 0 Then
    If VarType(Me(0)) = vbString Then
        Dequeue = Me(0)
    ElseIf TypeOf Me(0) Is vMeterFractionList Then
        Set Dequeue = Me(0)
    ElseIf VarType(Me(0)) = vbArray Then
        Set Dequeue = Me(0)
    ElseIf VarType(Me(0)) = vbObject Then
        Set Dequeue = Me(0)
    Else
        Dequeue = Me(0)
    End If
    
    mainArray.Remove 1
  End If
End Function

'Difference
' Checks for number of differences between two arrays, what was added/deleted or combination.
' @param iArray oldArray | Old iArray to be compared with current iArray
' @param String retType | �dd= deleted from old iArray, �aa= added in current iArray, �cc= combination of both (default)
' @return iArray | iArray with differences found
Public Function Difference(ByRef oldArray As vMeterFractionList, Optional ByVal retType As String = "c") As vMeterFractionList
  Set Difference = New vMeterFractionList
  Select Case LCase(retType)
    Case "d"
      For i = 0 To oldArray.Count - 1
        If Me.Contains(oldArray(i)) = False Then Difference.Push oldArray(i)
      Next i
    Case "a"
      For i = 0 To Count - 1
        If oldArray.Contains(Me(i)) = False Then Difference.Push Me(i)
      Next i
    Case "c"
      For i = 0 To oldArray.Count - 1
        If Me.Contains(oldArray(i)) = False Then Difference.Push oldArray(i)
      Next i
      For i = 0 To Count - 1
        If oldArray.Contains(Me(i)) = False Then Difference.Push Me(i)
      Next i
    Case Else
      err.Raise Number:=5, Description:="Unknown Difference return type attribute:" & vbCrLf & _
                                        "Allowed are 'A'dded/'D'eleted/'C'ombination of both"
  End Select
End Function

'DropLeft
' Remove n elements from the beginning of the mainArray. If n > count of iArray elements, all elements are removed.
' @param Long n | Number of elements to be removed
' @return iArray | Array of the removed elements
Public Function DropLeft(ByRef N As Long) As vMeterFractionList
  Set DropLeft = New vMeterFractionList
  If N > Me.Count Then N = Me.Count
  For i = 0 To N - 1
    DropLeft.Push Me(i)
  Next i
  For i = N - 1 To 0 Step -1
    Me.Remove (i)
  Next i
End Function

'DropRight
' Remove n elements from the end of the mainArray. If n > count of iArray elements, all elements are removed.
' @param Long n | Number of elements to be removed
' @return iArray | Array of the removed elements
Public Function DropRight(ByRef N As Long) As vMeterFractionList
  Set DropRight = New vMeterFractionList
  If N > Me.Count Then N = Me.Count
  For i = Me.Count - N To Me.Count - 1
    DropRight.Push Me(i)
  Next i
  For i = Me.Count - 1 To Me.Count - N Step -1
    Me.Remove (i)
  Next i
End Function

'Enqueue
' Adds an element at the end of the mainArray.
' @param Variant val | One element (String, number, ...) to add into iArray
' @return Long | Count of elements inside iArray
Public Function Enqueue(ByVal val As Variant) As Long
  Enqueue = Push(val)
End Function

'EnqueueArray
' Adds elements at the end of the iArray
' @param Variant val | Array() or iArray of elements to add into iArray
' @return Long | Count of elements inside array
Public Function EnqueueArray(ByVal val As Variant) As Long
  EnqueueArray = PushArray(val)
End Function

'First
' Returns value of the first element of the mainArray.
' @return Variant | Value of the first element or Empty if iArray is Empty
Public Function First() As vMeterFraction
  Set First = IIf(Me.Count > 0, Me(0), Empty)
End Function

'Head
' Returns all elements of iArray, except last one.
' @return iArray | Copy of original array, without last element
Public Function head() As vMeterFractionList
  Set head = Me.clone
  head.Pop
End Function

'Intersect
' Search for element that exists in both iArrays.
' @param iArray intArray | iArray to be intersected with current iArray
' @return iArray | Intersected values
Public Function Intersect(ByRef intersectedArr As vMeterFractionList) As vMeterFractionList
  Set Intersect = New vMeterFractionList
  Dim el As Variant
  For Each el In mainArray
    If intersectedArr.Contains(el) Then
      If Not Intersect.Contains(el) Then Intersect.Push (el)
    End If
  Next el
End Function

'ContainsOnlyNumeric
' Verify that all elements are numbers or convertable to numbers
' $return Boolean | True = contains only numeric values, False = contains inconvertible values
Public Function ContainsOnlyNumeric() As Boolean
  ContainsOnlyNumeric = True
  Dim el As Variant
  For Each el In mainArray
    If Not IsNumeric(el) Then ContainsOnlyNumeric = False: Exit Function
  Next el
End Function

'Join
' Joins two iArrays.
' @param iArray jArray | iArray to be joined with current iArray
' @return iArray | Joined iArray
Public Function Join(ByRef joinArr As vMeterFractionList) As vMeterFractionList
  Set Join = New vMeterFractionList
  Join.PushArray Me
  Join.PushArray joinArr
End Function

'Last
' Returns value of the last element of the mainArray.
' @return Variant | Value of the last element or Empty if iArray is Empty
Public Function Last() As vMeterFraction
  Set Last = IIf(Me.Count > 0, Me(Me.Count - 1), Empty)
End Function

'OccurrenceIndexes
' Returns all indexes of a value in mainArray.
' @return iArray | iArray containing indexes of occurrence
Public Function OccurenceIndexes(val As Variant) As vMeterFractionList
  Set OccurenceIndexes = New vMeterFractionList
  For i = 0 To Me.Count - 1
    If Me(i) = val Then
        OccurenceIndexes.Push (i)
    End If
  Next i
End Function

'Pop
' Removes an element from the end of the mainArray.
' @return Variant | Removed element or Empty, if iArray is empty
Public Function Pop() As vMeterFraction
  If mainArray.Count > 0 Then
    If VarType(Me(mainArray.Count - 1)) = vbObject Then
       Set Pop = Me(mainArray.Count - 1)
    Else
        Pop = Me(mainArray.Count - 1)
    End If
    mainArray.Remove mainArray.Count
  End If
End Function
  
  

'Push
' Adds an element at the end of the mainArray.
' @param Variant val | One element (String, number, ...) to add into iArray
' @return Long | Count of elements inside iArray
Public Function Push(ByVal val As vMeterFraction) As Long
  mainArray.Add val
  Push = mainArray.Count
End Function

'PushArray
' Adds elements at the end of the mainArray.
' @param Variant val | Array() or iArray of elements to add into iArray
' @return Long | Count of elements inside array
Public Function PushArray(ByVal val As Variant) As Long
  If TypeOf val Is vMeterFractionList Then
    For i = 0 To val.Count - 1
      Me.Push val(i)
    Next i
  Else
    For i = LBound(val) To UBound(val)
      Me.Push val(i)
    Next i
  End If
  PushArray = Me.Count
End Function

'RemoveDuplicates
' Keeps only the first occurrence of the value. Affects original array
' @return Long | Count of the removed elements
Public Function RemoveDuplicates() As Long
  RemoveDuplicates = 0
  For i = Me.Count - 1 To 0 Step -1
    If Me.CountOccurrences(Me(i)) > 1 Then
      Me.Remove i
      Inc RemoveDuplicates
    End If
  Next i
End Function

'Reverse
' Reverses the content of the iArray
' @return iArray | Reversed iArray
Public Function Reverse() As vMeterFractionList
  Set Reverse = New vMeterFractionList
  For i = 0 To Me.Count - 1
    Reverse.Unshift Me(i)
  Next i
End Function

'Shift
' Removes an element from the begining of the mainArray.
' @return Variant | Removed element or Empty, if iArray is empty
'轉移
' 從 iArray 的開頭刪除一個元素。
' @返回第一個元素 | 如果 iArray 為空，則刪除元素或為空
Public Function shift() As vMeterFraction
  shift = Empty
  If mainArray.Count > 0 Then
    If VarType(Me(0)) = vbString Then
        shift = Me(0)
    ElseIf TypeOf Me(0) Is vMeterFractionList Then
        Set shift = Me(0)
    ElseIf VarType(Me(0)) = vbArray Then
        Set shift = Me(0)
    ElseIf VarType(Me(0)) = vbObject Then
        Set shift = Me(0)
    Else
        shift = Me(0)
    End If
    
    mainArray.Remove 1
  End If
End Function

'Shuffle
' Randomly mixes content of the iArray
' @return iArray | Shuffled iArray
' 隨機播放
' 隨機混合 iArray 的內容
'@return iArray | 打亂iArray
Public Function Shuffle() As vMeterFractionList
  Set Shuffle = New vMeterFractionList
  Dim keys As New vMeterFractionList
  For i = 0 To Me.Count - 1
    keys.Push (i)
  Next i
  Dim rndNo As Long
  Do While keys.Count > 0
    rndNo = randomFromTo(0, keys.Count - 1)
    Shuffle.Push Me(keys(rndNo))
    keys.Remove (rndNo)
  Loop
End Function

'Sum
' Calculates the sum of the numeric mainArray.
' @return Variant | Sum value / "NaN" if iArray contains non-numeric value(s)
Public Function sum() As Variant
  If Not Me.ContainsOnlyNumeric Then sum = "NaN": Exit Function
  sum = 0
  Dim el As Variant
  For Each el In mainArray
    sum = sum + el
  Next el
End Function

'Tail
' Returns all elements of iArray, except first one.
' @return iArray | Copy of original array, without first element
'返回陣列中除了第一個元素的剩余元素陣列
Public Function Tail() As vMeterFractionList
  Set Tail = Me.clone
  Tail.Dequeue
End Function

Public Function ToList()
  If Me.Count = 0 Then ToList = Null: Exit Function
  Dim tarr()
  ReDim tarr(Me.Count - 1)
  For i = 0 To Me.Count - 1
    If VarType(Me(i)) = vbString Then
        tarr(i) = Me(i)
    ElseIf TypeOf Me(i) Is vMeterFractionList Then
        Set tarr(i) = Me(i)
    ElseIf VarType(Me(i)) = vbObject Then
        Set tarr(i) = Me(i)
    Else
        tarr(i) = Me(i)
    End If
  Next i
  ToList = tarr
End Function

'ToString
' Creates string representation of the mainArray.
' @param String delimiter | Optional character to separate the iArray's elements (default = " ")
' @return String | Formated representation of tha iArray
Public Function ToString(Optional ByVal delimiter As String = " ") As String
  If Me.Count = 0 Then ToString = "{}": Exit Function
  ToString = vbNullString
  For i = 0 To Me.Count - 1
    If i = 0 Then ToString = ToString + "{"
    If i > 0 Then ToString = ToString + delimiter
    If VarType(Me(i)) = vbString Then
        ToString = ToString + Chr$(34)
        ToString = ToString + CStr(Me(i))
        ToString = ToString + Chr$(34)
    ElseIf TypeOf Me(i) Is vMeterFractionList Then
        ToString = ToString + Me(i).ToString(delimiter)
    ElseIf (VarType(Me(i)) And vbArray) = vbArray Then
        ToString = ToString + "[Array]"
    ElseIf VarType(Me(i)) = vbObject Then
        ToString = ToString + "[Object]"
    Else
        ToString = ToString + CStr(Me(i))
    End If
    
    If i = mainArray.Count - 1 Then ToString = ToString + "}"
  Next i
End Function

'Union
' Combines both iArrays and removes duplicities
' @param iArray uArray | iArray to be unioned with current iArray
' @return iArray | Combined values without duplicities
Public Function Union(ByRef uArr As vMeterFractionList) As vMeterFractionList
  Set Union = Me.clone
  Union.PushArray uArr
  Union.RemoveDuplicates
End Function

'Unique
' Returns copy of iArray without duplicated values. Original array is not affected
' @return iArray | iArray with unique values
Public Function Unique() As vMeterFractionList
  Set Unique = New vMeterFractionList
  Dim el As Variant
  For Each el In mainArray
    If Not Unique.Contains(el) Then Unique.Push (el)
  Next el
End Function

'Unshift
' Add an element at the begining of the mainArray.
' @param Variant val | One element (String, number, ...) to add into iArray
' @return Long | Count of elements inside iArray
Public Function Unshift(ByVal val As Variant) As Long
  If mainArray.Count = 0 Then
    Unshift = Push(val)
  Else
    mainArray.Add val, before:=1
    Unshift = mainArray.Count
  End If
End Function

'UnshiftArray
' Add elements at the begining of the mainArray.
' @param Variant val | Array() or iArray of elements to add into iArray
' @return Long | Count of elements inside iArray
Public Function UnshiftArray(ByVal val As Variant) As Long
  If TypeOf val Is vMeterFractionList Then
    For i = val.Count - 1 To 0 Step -1
      Unshift val(i)
    Next i
  Else
    For i = UBound(val) To LBound(val) Step -1
      Unshift val(i)
    Next i
  End If
  UnshiftArray = mainArray.Count
End Function


' #####################
' # PRIVATE FUNCTIONS #
' #####################
Sub Inc(ByRef i)
   i = i + 1
End Sub

'Private Function rangeToArray(ByVal rng As Range) As Variant
'  rangeToArray = rng.Value
'End Function

Private Function randomFromTo(ByVal from As Long, ByVal upTo As Long) As Long
  Randomize
  randomFromTo = Int(from + Rnd() * (upTo - from + 1))
End Function

'比對 兩個陣列是否一樣
Private Function ArrayDifference(arr1 As Variant, arr2 As Variant) As Boolean

    Dim i As Integer
    If UBound(arr1) = UBound(arr2) Then
        For i = 0 To UBound(arr1)
            If arr1(i) = arr2(i) Then
                ArrayDifference = True
            Else
                ArrayDifference = False
                Exit Function
            End If
        Next
    Else
        ArrayDifference = False
    End If

End Function

'@Description("changes the contents of the array by removing or replacing existing elements and/or adding new elements in place.")
Public Function Splice( _
        ByVal StartIndex As Long, _
        ParamArray Args() As Variant _
    ) As Variant()
    'Dim LocalItems() As Variant
    Dim ActualStart As Long
    Dim ActualDeleteCount As Long
    Dim ArgsCount As Long
    Dim LocalLength As Long
    Dim LocalArgs() As Variant
    Dim result() As Variant
    Dim i As Long
    Dim TempArray() As Variant
    Dim ItemCount As Long
    Dim TempItems() As Variant
    
    LocalArgs = Args
    'LocalItems = mainArray
    LocalLength = Me.Count
    If StartIndex < LocalLength Then
        ActualStart = StartIndex
    Else
        ActualStart = min(StartIndex, LocalLength)
    End If
    
    ArgsCount = UBound(LocalArgs) + 1
    If ArgsCount = 0 Then
        ' only a start index has been supplied
        ' we're gonna delete everything
        ' 僅提供了起始索引
         '我們要刪除所有內容
        ItemCount = 0
        ActualDeleteCount = LocalLength - ActualStart
    Else
        ' first arg in args is delete count, second onwards are insertion items
        ' args 中的第一個參數是刪除計數，第二個之後是插入項
        ItemCount = ArgsCount - 1
        'deleteCount is first element in args.
        'deleteCount 是 args 中的第一個元素。
        ActualDeleteCount = min(max(Args(LBound(Args)), 0), LocalLength - ActualStart)
    End If
    

    ' get items to be deleted for return val
    ' 取得和刪除
    If ActualDeleteCount > 0 Then
        ReDim result(0 To ActualDeleteCount - 1)
        i = 0
        Do While i < ActualDeleteCount
            If IsObject(Me(ActualStart)) Then
                Set result(i) = Me(ActualStart)
                Me.Remove ActualStart
            Else
                result(i) = Me(ActualStart)
                Me.Remove ActualStart
            End If
            Inc i
        Loop
    Else
        ' return empty array if nothing to be deleted
        ReDim result(0)
    End If
    
    '取得要插入的陣列資料
    If ItemCount > 0 Then
        ReDim TempItems(0 To ItemCount - 1)
        For i = 0 To ItemCount - 1
            If IsObject(LocalArgs(i + 1)) Then
                Set TempItems(i) = LocalArgs(i + 1)
            Else
                TempItems(i) = LocalArgs(i + 1)
            End If
        Next
    Me.AddArrayBefore ActualStart, TempItems
    End If
    
    
    Splice = result
End Function

Attribute VB_Name = "vSlur"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public label As Integer
Public Direction As String    'up', 'down'
Public style As String 'dotted'

Attribute VB_Name = "vSlurList"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
'MIT License
'
'Copyright (c) 2019-2021 Petr Katerinak
'
'Permission is hereby granted, free of charge, to any person obtaining a copy
'of this software and associated documentation files (the "Software"), to deal
'in the Software without restriction, including without limitation the rights
'to use, copy, modify, merge, publish, distribute, sublicense, and/or sell
'copies of the Software, and to permit persons to whom the Software is
'furnished to do so, subject to the following conditions:
'
'The above copyright notice and this permission notice shall be included in all
'copies or substantial portions of the Software.
'
'THE SOFTWARE IS PROVIDED "AS IS", WITHOUT WARRANTY OF ANY KIND, EXPRESS OR
'IMPLIED, INCLUDING BUT NOT LIMITED TO THE WARRANTIES OF MERCHANTABILITY,
'FITNESS FOR A PARTICULAR PURPOSE AND NONINFRINGEMENT. IN NO EVENT SHALL THE
'AUTHORS OR COPYRIGHT HOLDERS BE LIABLE FOR ANY CLAIM, DAMAGES OR OTHER
'LIABILITY, WHETHER IN AN ACTION OF CONTRACT, TORT OR OTHERWISE, ARISING FROM,
'OUT OF OR IN CONNECTION WITH THE SOFTWARE OR THE USE OR OTHER DEALINGS IN THE
'SOFTWARE.
'
' Version of iArray: 1.0
''修正 元素從 0 開始

Private mainArray As New Collection
Private i As Long ' Counter

' #####################
' #    CONSTRUCTOR    #
' #####################
'Private Sub Class_Initialize()
'  Set mainArray = New Collection
'End Sub

' #####################
' #  Getter / Setter  #
' #####################
'Attribute Element.VB_UserMemId = 0 saved in both procedures

'@DefaultMember
Public Property Get element(ByVal index As Long) As vSlur
Attribute element.VB_UserMemId = 0
    If index + 1 < 1 Or index + 1 > mainArray.Count Then
        Set element = Nothing
        Exit Property
    End If
    If IsObject(mainArray(index + 1)) = True Then
        Set element = mainArray(index + 1)
    Else
        element = mainArray(index + 1)
    End If

 
End Property

'@DefaultMember
Public Property Let element(ByVal index As Long, ByVal val As vSlur)
Attribute element.VB_UserMemId = 0
  If index = 0 And mainArray.Count = 0 Then
    Me.Push val
  If index + 1 > mainArray.Count Then
    Dim eMsg As String
    eMsg = IIf(mainArray.Count > 0, _
               "Index (" & index + 1 & ") out of iArray bounds (1-" & mainArray.Count & ")", _
               "iArray doesn't have any indexes")
    err.Raise Number:=9, Description:=eMsg
    Exit Property
  End If
  mainArray.Remove index + 1
  mainArray.Add val, before:=index
End Property

' #############################
' # COMMON COLLECTION METHODS #
' #############################
Public Function Count() As Long
  Count = mainArray.Count
End Function
Public Sub Add(ByVal val As vSlur, Optional ByVal bef As Variant = Empty, Optional ByVal aft As Variant = Empty)
  If IsEmpty(bef) And IsEmpty(aft) Then
    mainArray.Add val
  ElseIf IsEmpty(bef) Then
    mainArray.Add val, , , aft
  ElseIf IsEmpty(aft) Then
    mainArray.Add val, , bef
  Else
    mainArray.Add val, , bef, aft
  End If
End Sub
Public Sub Remove(index As Long)
  mainArray.Remove index + 1
End Sub

' ####################
' #  PUBLIC METHODS  #
' ####################

'AddAfter
' Adds element after given index.
' {1,2,3} -> index >= 3 -> Push val
' {1,2,3} -> index < 1 -> Unshift val
' {} -> index = any -> Push val
' @param Long index | Index after which will be added an element
' @param Variant val | One element (String, number, ...) to add into iArray
' @return Long | Count of elements inside iArray
Public Function AddAfter(ByVal index As Long, ByVal val As vSlur) As Long
  If Me.Count < 1 Or index + 1 >= Me.Count Then
    Me.Push val
  ElseIf index + 1 < 1 Then
    Me.Unshift val
  Else
    Me.Add val, aft:=index + 1
  End If
  AddAfter = Me.Count
End Function

'AddArrayAfter
' Adds elements after given index.
' {1,2,3} -> index >= 3 -> PushArray val
' {1,2,3} -> index < 1 -> UnshiftArray val
' {} -> index = any -> PushArray val
' @param Long index | Index after which will be added an element
' @param Variant val | Array() or iArray of elements to add into iArray
' @return Long | Count of elements inside iArray
Public Function AddArrayAfter(ByVal index As Long, ByVal val As Variant) As Long
  If Me.Count < 1 Or index + 1 >= Me.Count Then
    Me.PushArray val
  ElseIf index + 1 < 1 Then
    Me.UnshiftArray val
  Else
    If TypeOf val Is vSlurList Then
      For i = 0 To val.Count - 1
        Me.Add val(i), aft:=index + 1
        Inc index
      Next i
    Else
      For i = LBound(val) To UBound(val)
        Me.Add val(i), aft:=index + 1
        Inc index
      Next i
    End If
  End If
  AddArrayAfter = Me.Count
End Function

'AddArrayBefore
' Adds elements before given index.
' {1,2,3} -> index > 3 -> PushArray val
' {1,2,3} -> index <= 1 -> UnshiftArray val
' {} -> index = any -> PushArray val
' @param Long index | Index after which will be added an element
' @param Variant val | Array() or iArray of elements to add into iArray
' @return Long | Count of elements inside iArray
Public Function AddArrayBefore(ByVal index As Long, ByVal val As Variant) As Long
  If Me.Count < 1 Or index + 1 > Me.Count Then
    Me.PushArray val
  ElseIf index <= 0 Then
    Me.UnshiftArray val
  Else
    If TypeOf val Is vSlurList Then
      For i = val.Count - 1 To 0 Step -1
        Me.Add val(i), bef:=index + 1
      Next i
    Else
      For i = UBound(val) To LBound(val) Step -1
        Me.Add val(i), bef:=index + 1
      Next i
    End If
  End If
  AddArrayBefore = Me.Count
End Function

'AddBefore
' Adds element before given index.
' {1,2,3} -> index > 3 -> Push val
' {1,2,3} -> index <= 1 -> Unshift val
' {} -> index = any -> Push val
' @param Long index | Index before which will be added an element
' @param Variant val | One element (String, number, ...) to add into iArray
' @return Long | Count of elements inside iArray
Public Function AddBefore(ByVal index As Long, ByVal val As vSlur) As Long
  If Me.Count < 1 Or index + 1 > Me.Count Then
    Me.Push val
  ElseIf index + 1 <= 1 Then
    Me.Unshift val
  Else
    Me.Add val, bef:=index + 1
  End If
  AddBefore = Me.Count
End Function

'Avg
' Calculates the average of the numeric mainArray.
' @return Variant | Average value / "NaN" if iArray contains non-numeric value(s)
Public Function Avg() As Variant
  If Not Me.ContainsOnlyNumeric Then Avg = "NaN": Exit Function
  Avg = Me.sum / Me.Count
End Function

'Clear
' Empties iArray
Public Function Clear() As Boolean
  For i = mainArray.Count - 1 To 0 Step -1
    mainArray.Remove i + 1
  Next i
  Clear = IIf(mainArray.Count = 0, True, False)
End Function

'Clone
' Makes a hard copy of the mainArray
' @return mainArray | Return exact copy of itself
Public Function clone() As vSlurList
  Set clone = New vSlurList
  For i = 0 To Me.Count - 1
    clone.Push Me(i)
  Next i
End Function

'Contains
' Checks if given value is used inside mainArray.
' @param Variant val | One element (String, number, ...) to by checked if it exists in iArray
' $return Boolean | True = exists, False = doesn't exists
Public Function Contains(ByVal val As vSlur) As Boolean
  Contains = False
  Dim el As Variant
  For Each el In mainArray
    If IsObject(val) = True Or VarType(val) And 8192 Then
        If (VarType(el) And 8192) And (VarType(val) And 8192) Then
            If ArrayDifference(el, val) Then
                Contains = True: Exit Function
            End If
        ElseIf IsObject(el) = True And IsObject(val) = True Then
            If el Is val Then
                Contains = True: Exit Function
            End If
        End If
    Else
        If IsObject(el) = False And (VarType(el) And 8192) <> 8192 Then
            If el = val Then
            Contains = True: Exit Function
            End If
        End If
    End If
  Next el
End Function

'ContainsAll
' Checks if all given values are used inside mainArray.
' @param Variant val | values to by checked if it exists in iArray
' $return Boolean | True = all exists, False = one ore more values doesn't exists
Public Function ContainsAll(ByVal val As vSlurList) As Boolean
  ContainsAll = False
  Dim foundOccurrences As Integer: foundOccurrences = 0
  Dim values As New vSlurList
  If Not TypeOf val Is vSlurList Then
    If IsArray(val) Then
      values.PushArray (val)
    Else
      values.Push (val)
    End If
  Else
    Set values = val
  End If
  For i = 0 To values.Count - 1
    If Me.Contains(values(i)) Then Inc foundOccurrences
  Next i
  If foundOccurrences = values.Count Then ContainsAll = True
End Function

'CountOccurrences
' Checks how many times is given value used inside mainArray.
' @param Variant val | One element (String, number, ...) to by checked
' @return Long | Count of matched occurrences
Public Function CountOccurrences(val As Variant) As Long
  CountOccurrences = 0
  Dim el As Variant
  For Each el In mainArray
  
    If IsObject(val) = True Or VarType(val) And 8192 Then
        If VarType(el) And 8192 And VarType(val) And 8192 Then
            If ArrayDifference(el, val) Then
                Inc CountOccurrences
                Exit Function
            End If
        ElseIf IsObject(el) = True And IsObject(val) = True Then
            If el Is val Then
                Inc CountOccurrences
                Exit Function
            End If
        End If
    Else
        If IsObject(el) = False And Not (VarType(el) And 8192) Then
            If el = val Then
                Inc CountOccurrences
                Exit Function
            End If
        End If
    End If
  
     'If el = val Then Inc CountOccurrences
  Next el
End Function

'Dequeue
' Removes an element from the begining of the mainArray.
' @return Variant | Removed element or Empty, if iArray is empty
'刪除開頭一個元素。
Public Function Dequeue() As vSlur
  Dequeue = Empty
  If mainArray.Count > 0 Then
    If VarType(Me(0)) = vbString Then
        Dequeue = Me(0)
    ElseIf TypeOf Me(0) Is vSlurList Then
        Set Dequeue = Me(0)
    ElseIf VarType(Me(0)) = vbArray Then
        Set Dequeue = Me(0)
    ElseIf VarType(Me(0)) = vbObject Then
        Set Dequeue = Me(0)
    Else
        Dequeue = Me(0)
    End If
    
    mainArray.Remove 1
  End If
End Function

'Difference
' Checks for number of differences between two arrays, what was added/deleted or combination.
' @param iArray oldArray | Old iArray to be compared with current iArray
' @param String retType | �dd= deleted from old iArray, �aa= added in current iArray, �cc= combination of both (default)
' @return iArray | iArray with differences found
Public Function Difference(ByRef oldArray As vSlurList, Optional ByVal retType As String = "c") As vSlurList
  Set Difference = New vSlurList
  Select Case LCase(retType)
    Case "d"
      For i = 0 To oldArray.Count - 1
        If Me.Contains(oldArray(i)) = False Then Difference.Push oldArray(i)
      Next i
    Case "a"
      For i = 0 To Count - 1
        If oldArray.Contains(Me(i)) = False Then Difference.Push Me(i)
      Next i
    Case "c"
      For i = 0 To oldArray.Count - 1
        If Me.Contains(oldArray(i)) = False Then Difference.Push oldArray(i)
      Next i
      For i = 0 To Count - 1
        If oldArray.Contains(Me(i)) = False Then Difference.Push Me(i)
      Next i
    Case Else
      err.Raise Number:=5, Description:="Unknown Difference return type attribute:" & vbCrLf & _
                                        "Allowed are 'A'dded/'D'eleted/'C'ombination of both"
  End Select
End Function

'DropLeft
' Remove n elements from the beginning of the mainArray. If n > count of iArray elements, all elements are removed.
' @param Long n | Number of elements to be removed
' @return iArray | Array of the removed elements
Public Function DropLeft(ByRef N As Long) As vSlurList
  Set DropLeft = New vSlurList
  If N > Me.Count Then N = Me.Count
  For i = 0 To N - 1
    DropLeft.Push Me(i)
  Next i
  For i = N - 1 To 0 Step -1
    Me.Remove (i)
  Next i
End Function

'DropRight
' Remove n elements from the end of the mainArray. If n > count of iArray elements, all elements are removed.
' @param Long n | Number of elements to be removed
' @return iArray | Array of the removed elements
Public Function DropRight(ByRef N As Long) As vSlurList
  Set DropRight = New vSlurList
  If N > Me.Count Then N = Me.Count
  For i = Me.Count - N To Me.Count - 1
    DropRight.Push Me(i)
  Next i
  For i = Me.Count - 1 To Me.Count - N Step -1
    Me.Remove (i)
  Next i
End Function

'Enqueue
' Adds an element at the end of the mainArray.
' @param Variant val | One element (String, number, ...) to add into iArray
' @return Long | Count of elements inside iArray
Public Function Enqueue(ByVal val As Variant) As Long
  Enqueue = Push(val)
End Function

'EnqueueArray
' Adds elements at the end of the iArray
' @param Variant val | Array() or iArray of elements to add into iArray
' @return Long | Count of elements inside array
Public Function EnqueueArray(ByVal val As Variant) As Long
  EnqueueArray = PushArray(val)
End Function

'First
' Returns value of the first element of the mainArray.
' @return Variant | Value of the first element or Empty if iArray is Empty
Public Function First() As vSlur
  Set First = IIf(Me.Count > 0, Me(0), Empty)
End Function

'Head
' Returns all elements of iArray, except last one.
' @return iArray | Copy of original array, without last element
Public Function head() As vSlurList
  Set head = Me.clone
  head.Pop
End Function

'Intersect
' Search for element that exists in both iArrays.
' @param iArray intArray | iArray to be intersected with current iArray
' @return iArray | Intersected values
Public Function Intersect(ByRef intersectedArr As vSlurList) As vSlurList
  Set Intersect = New vSlurList
  Dim el As Variant
  For Each el In mainArray
    If intersectedArr.Contains(el) Then
      If Not Intersect.Contains(el) Then Intersect.Push (el)
    End If
  Next el
End Function

'ContainsOnlyNumeric
' Verify that all elements are numbers or convertable to numbers
' $return Boolean | True = contains only numeric values, False = contains inconvertible values
Public Function ContainsOnlyNumeric() As Boolean
  ContainsOnlyNumeric = True
  Dim el As Variant
  For Each el In mainArray
    If Not IsNumeric(el) Then ContainsOnlyNumeric = False: Exit Function
  Next el
End Function

'Join
' Joins two iArrays.
' @param iArray jArray | iArray to be joined with current iArray
' @return iArray | Joined iArray
Public Function Join(ByRef joinArr As vSlurList) As vSlurList
  Set Join = New vSlurList
  Join.PushArray Me
  Join.PushArray joinArr
End Function

'Last
' Returns value of the last element of the mainArray.
' @return Variant | Value of the last element or Empty if iArray is Empty
Public Function Last() As vSlur
  Set Last = IIf(Me.Count > 0, Me(Me.Count - 1), Empty)
End Function

'OccurrenceIndexes
' Returns all indexes of a value in mainArray.
' @return iArray | iArray containing indexes of occurrence
Public Function OccurenceIndexes(val As Variant) As vSlurList
  Set OccurenceIndexes = New vSlurList
  For i = 0 To Me.Count - 1
    If Me(i) = val Then
        OccurenceIndexes.Push (i)
    End If
  Next i
End Function

'Pop
' Removes an element from the end of the mainArray.
' @return Variant | Removed element or Empty, if iArray is empty
Public Function Pop() As vSlur
  If mainArray.Count > 0 Then
    If VarType(Me(mainArray.Count - 1)) = vbObject Then
       Set Pop = Me(mainArray.Count - 1)
    Else
        Pop = Me(mainArray.Count - 1)
    End If
    mainArray.Remove mainArray.Count
  End If
End Function
  
  

'Push
' Adds an element at the end of the mainArray.
' @param Variant val | One element (String, number, ...) to add into iArray
' @return Long | Count of elements inside iArray
Public Function Push(ByVal val As vSlur) As Long
  mainArray.Add val
  Push = mainArray.Count
End Function

'PushArray
' Adds elements at the end of the mainArray.
' @param Variant val | Array() or iArray of elements to add into iArray
' @return Long | Count of elements inside array
Public Function PushArray(ByVal val As Variant) As Long
  If TypeOf val Is vSlurList Then
    For i = 0 To val.Count - 1
      Me.Push val(i)
    Next i
  Else
    For i = LBound(val) To UBound(val)
      Me.Push val(i)
    Next i
  End If
  PushArray = Me.Count
End Function

'RemoveDuplicates
' Keeps only the first occurrence of the value. Affects original array
' @return Long | Count of the removed elements
Public Function RemoveDuplicates() As Long
  RemoveDuplicates = 0
  For i = Me.Count - 1 To 0 Step -1
    If Me.CountOccurrences(Me(i)) > 1 Then
      Me.Remove i
      Inc RemoveDuplicates
    End If
  Next i
End Function

'Reverse
' Reverses the content of the iArray
' @return iArray | Reversed iArray
Public Function Reverse() As vSlurList
  Set Reverse = New vSlurList
  For i = 0 To Me.Count - 1
    Reverse.Unshift Me(i)
  Next i
End Function

'Shift
' Removes an element from the begining of the mainArray.
' @return Variant | Removed element or Empty, if iArray is empty
'轉移
' 從 iArray 的開頭刪除一個元素。
' @返回第一個元素 | 如果 iArray 為空，則刪除元素或為空
Public Function shift() As vSlur
  shift = Empty
  If mainArray.Count > 0 Then
    If VarType(Me(0)) = vbString Then
        shift = Me(0)
    ElseIf TypeOf Me(0) Is vSlurList Then
        Set shift = Me(0)
    ElseIf VarType(Me(0)) = vbArray Then
        Set shift = Me(0)
    ElseIf VarType(Me(0)) = vbObject Then
        Set shift = Me(0)
    Else
        shift = Me(0)
    End If
    
    mainArray.Remove 1
  End If
End Function

'Shuffle
' Randomly mixes content of the iArray
' @return iArray | Shuffled iArray
' 隨機播放
' 隨機混合 iArray 的內容
'@return iArray | 打亂iArray
Public Function Shuffle() As vSlurList
  Set Shuffle = New vSlurList
  Dim keys As New vSlurList
  For i = 0 To Me.Count - 1
    keys.Push (i)
  Next i
  Dim rndNo As Long
  Do While keys.Count > 0
    rndNo = randomFromTo(0, keys.Count - 1)
    Shuffle.Push Me(keys(rndNo))
    keys.Remove (rndNo)
  Loop
End Function

'Sum
' Calculates the sum of the numeric mainArray.
' @return Variant | Sum value / "NaN" if iArray contains non-numeric value(s)
Public Function sum() As Variant
  If Not Me.ContainsOnlyNumeric Then sum = "NaN": Exit Function
  sum = 0
  Dim el As Variant
  For Each el In mainArray
    sum = sum + el
  Next el
End Function

'Tail
' Returns all elements of iArray, except first one.
' @return iArray | Copy of original array, without first element
'返回陣列中除了第一個元素的剩余元素陣列
Public Function Tail() As vSlurList
  Set Tail = Me.clone
  Tail.Dequeue
End Function

Public Function ToList()
  If Me.Count = 0 Then ToList = Null: Exit Function
  Dim tarr()
  ReDim tarr(Me.Count - 1)
  For i = 0 To Me.Count - 1
    If VarType(Me(i)) = vbString Then
        tarr(i) = Me(i)
    ElseIf TypeOf Me(i) Is vSlurList Then
        Set tarr(i) = Me(i)
    ElseIf VarType(Me(i)) = vbObject Then
        Set tarr(i) = Me(i)
    Else
        tarr(i) = Me(i)
    End If
  Next i
  ToList = tarr
End Function

'ToString
' Creates string representation of the mainArray.
' @param String delimiter | Optional character to separate the iArray's elements (default = " ")
' @return String | Formated representation of tha iArray
Public Function ToString(Optional ByVal delimiter As String = " ") As String
  If Me.Count = 0 Then ToString = "{}": Exit Function
  ToString = vbNullString
  For i = 0 To Me.Count - 1
    If i = 0 Then ToString = ToString + "{"
    If i > 0 Then ToString = ToString + delimiter
    If VarType(Me(i)) = vbString Then
        ToString = ToString + Chr$(34)
        ToString = ToString + CStr(Me(i))
        ToString = ToString + Chr$(34)
    ElseIf TypeOf Me(i) Is vSlurList Then
        ToString = ToString + Me(i).ToString(delimiter)
    ElseIf (VarType(Me(i)) And vbArray) = vbArray Then
        ToString = ToString + "[Array]"
    ElseIf VarType(Me(i)) = vbObject Then
        ToString = ToString + "[Object]"
    Else
        ToString = ToString + CStr(Me(i))
    End If
    
    If i = mainArray.Count - 1 Then ToString = ToString + "}"
  Next i
End Function

'Union
' Combines both iArrays and removes duplicities
' @param iArray uArray | iArray to be unioned with current iArray
' @return iArray | Combined values without duplicities
Public Function Union(ByRef uArr As vSlurList) As vSlurList
  Set Union = Me.clone
  Union.PushArray uArr
  Union.RemoveDuplicates
End Function

'Unique
' Returns copy of iArray without duplicated values. Original array is not affected
' @return iArray | iArray with unique values
Public Function Unique() As vSlurList
  Set Unique = New vSlurList
  Dim el As Variant
  For Each el In mainArray
    If Not Unique.Contains(el) Then Unique.Push (el)
  Next el
End Function

'Unshift
' Add an element at the begining of the mainArray.
' @param Variant val | One element (String, number, ...) to add into iArray
' @return Long | Count of elements inside iArray
Public Function Unshift(ByVal val As Variant) As Long
  If mainArray.Count = 0 Then
    Unshift = Push(val)
  Else
    mainArray.Add val, before:=1
    Unshift = mainArray.Count
  End If
End Function

'UnshiftArray
' Add elements at the begining of the mainArray.
' @param Variant val | Array() or iArray of elements to add into iArray
' @return Long | Count of elements inside iArray
Public Function UnshiftArray(ByVal val As Variant) As Long
  If TypeOf val Is vSlurList Then
    For i = val.Count - 1 To 0 Step -1
      Unshift val(i)
    Next i
  Else
    For i = UBound(val) To LBound(val) Step -1
      Unshift val(i)
    Next i
  End If
  UnshiftArray = mainArray.Count
End Function


' #####################
' # PRIVATE FUNCTIONS #
' #####################
Sub Inc(ByRef i)
   i = i + 1
End Sub

'Private Function rangeToArray(ByVal rng As Range) As Variant
'  rangeToArray = rng.Value
'End Function

Private Function randomFromTo(ByVal from As Long, ByVal upTo As Long) As Long
  Randomize
  randomFromTo = Int(from + Rnd() * (upTo - from + 1))
End Function

'比對 兩個陣列是否一樣
Private Function ArrayDifference(arr1 As Variant, arr2 As Variant) As Boolean

    Dim i As Integer
    If UBound(arr1) = UBound(arr2) Then
        For i = 0 To UBound(arr1)
            If arr1(i) = arr2(i) Then
                ArrayDifference = True
            Else
                ArrayDifference = False
                Exit Function
            End If
        Next
    Else
        ArrayDifference = False
    End If

End Function

Attribute VB_Name = "vSpacingRenderer"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Public composer As Double
Public graceBefore As Double
Public graceInside As Double
Public graceAfter As Double
Public info As Double
Public lineSkipFactor As Double
Public music As Double
Public paragraphSkipFactor As Double
Public parts As Double
Public slurHeight As Double
Public staffSeparation As Double
Public stemHeight As Double
Public subtitle As Double
Public systemStaffSeparation As Double
Public text As Double
Public title As Double
Public top As Double
Public vocal As Double
Public words As Double

Attribute VB_Name = "vStaffInfo"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit


Public top As Double
Public bottom As Double
Public lines As Double
Public voices As iArray
Public specialY As Dictionary
Public absoluteY As Double
Public bottomLine As Double
Public topLine As Double

Private Sub Class_Initialize()
    Set voices = New iArray
    Set specialY = New Dictionary
End Sub

Attribute VB_Name = "vStaffInfoList"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
'MIT License
'
'Copyright (c) 2019-2021 Petr Katerinak
'
'Permission is hereby granted, free of charge, to any person obtaining a copy
'of this software and associated documentation files (the "Software"), to deal
'in the Software without restriction, including without limitation the rights
'to use, copy, modify, merge, publish, distribute, sublicense, and/or sell
'copies of the Software, and to permit persons to whom the Software is
'furnished to do so, subject to the following conditions:
'
'The above copyright notice and this permission notice shall be included in all
'copies or substantial portions of the Software.
'
'THE SOFTWARE IS PROVIDED "AS IS", WITHOUT WARRANTY OF ANY KIND, EXPRESS OR
'IMPLIED, INCLUDING BUT NOT LIMITED TO THE WARRANTIES OF MERCHANTABILITY,
'FITNESS FOR A PARTICULAR PURPOSE AND NONINFRINGEMENT. IN NO EVENT SHALL THE
'AUTHORS OR COPYRIGHT HOLDERS BE LIABLE FOR ANY CLAIM, DAMAGES OR OTHER
'LIABILITY, WHETHER IN AN ACTION OF CONTRACT, TORT OR OTHERWISE, ARISING FROM,
'OUT OF OR IN CONNECTION WITH THE SOFTWARE OR THE USE OR OTHER DEALINGS IN THE
'SOFTWARE.
'
' Version of iArray: 1.0
''修正 元素從 0 開始

Private mainArray As New Collection
Private i As Long ' Counter

' #####################
' #    CONSTRUCTOR    #
' #####################
'Private Sub Class_Initialize()
'  Set mainArray = New Collection
'End Sub

' #####################
' #  Getter / Setter  #
' #####################
'Attribute Element.VB_UserMemId = 0 saved in both procedures

'@DefaultMember
Public Property Get element(ByVal index As Long) As vStaffInfo
Attribute element.VB_UserMemId = 0
    If index + 1 < 1 Or index + 1 > mainArray.Count Then
        Set element = Nothing
        Exit Property
    End If
    If IsObject(mainArray(index + 1)) = True Then
        Set element = mainArray(index + 1)
    Else
        element = mainArray(index + 1)
    End If

 
End Property

'@DefaultMember
Public Property Let element(ByVal index As Long, ByVal val As vStaffInfo)
Attribute element.VB_UserMemId = 0
  If index = 0 And mainArray.Count = 0 Then
    Me.Push val
    Exit Property
  End If
  If index + 1 > mainArray.Count Then
    Dim eMsg As String
    eMsg = IIf(mainArray.Count > 0, _
               "Index (" & index + 1 & ") out of iArray bounds (1-" & mainArray.Count & ")", _
               "iArray doesn't have any indexes")
    err.Raise Number:=9, Description:=eMsg
    Exit Property
  End If
  mainArray.Add val, after:=index + 1
  mainArray.Remove index + 1
End Property

' #############################
' # COMMON COLLECTION METHODS #
' #############################
Public Function Count() As Long
  Count = mainArray.Count
End Function
Public Sub Add(ByVal val As vStaffInfo, Optional ByVal bef As Variant = Empty, Optional ByVal aft As Variant = Empty)
  If IsEmpty(bef) And IsEmpty(aft) Then
    mainArray.Add val
  ElseIf IsEmpty(bef) Then
    mainArray.Add val, , , aft
  ElseIf IsEmpty(aft) Then
    mainArray.Add val, , bef
  Else
    mainArray.Add val, , bef, aft
  End If
End Sub
Public Sub Remove(index As Long)
  mainArray.Remove index + 1
End Sub

' ####################
' #  PUBLIC METHODS  #
' ####################

'AddAfter
' Adds element after given index.
' {1,2,3} -> index >= 3 -> Push val
' {1,2,3} -> index < 1 -> Unshift val
' {} -> index = any -> Push val
' @param Long index | Index after which will be added an element
' @param Variant val | One element (String, number, ...) to add into iArray
' @return Long | Count of elements inside iArray
Public Function AddAfter(ByVal index As Long, ByVal val As vStaffInfo) As Long
  If Me.Count < 1 Or index + 1 >= Me.Count Then
    Me.Push val
  ElseIf index + 1 < 1 Then
    Me.Unshift val
  Else
    Me.Add val, aft:=index + 1
  End If
  AddAfter = Me.Count
End Function

'AddArrayAfter
' Adds elements after given index.
' {1,2,3} -> index >= 3 -> PushArray val
' {1,2,3} -> index < 1 -> UnshiftArray val
' {} -> index = any -> PushArray val
' @param Long index | Index after which will be added an element
' @param Variant val | Array() or iArray of elements to add into iArray
' @return Long | Count of elements inside iArray
Public Function AddArrayAfter(ByVal index As Long, ByVal val As Variant) As Long
  If Me.Count < 1 Or index + 1 >= Me.Count Then
    Me.PushArray val
  ElseIf index + 1 < 1 Then
    Me.UnshiftArray val
  Else
    If TypeOf val Is vStaffInfoList Then
      For i = 0 To val.Count - 1
        Me.Add val(i), aft:=index + 1
        Inc index
      Next i
    Else
      For i = LBound(val) To UBound(val)
        Me.Add val(i), aft:=index + 1
        Inc index
      Next i
    End If
  End If
  AddArrayAfter = Me.Count
End Function

'AddArrayBefore
' Adds elements before given index.
' {1,2,3} -> index > 3 -> PushArray val
' {1,2,3} -> index <= 1 -> UnshiftArray val
' {} -> index = any -> PushArray val
' @param Long index | Index after which will be added an element
' @param Variant val | Array() or iArray of elements to add into iArray
' @return Long | Count of elements inside iArray
Public Function AddArrayBefore(ByVal index As Long, ByVal val As Variant) As Long
  If Me.Count < 1 Or index + 1 > Me.Count Then
    Me.PushArray val
  ElseIf index <= 0 Then
    Me.UnshiftArray val
  Else
    If TypeOf val Is vStaffInfoList Then
      For i = val.Count - 1 To 0 Step -1
        Me.Add val(i), bef:=index + 1
      Next i
    Else
      For i = UBound(val) To LBound(val) Step -1
        Me.Add val(i), bef:=index + 1
      Next i
    End If
  End If
  AddArrayBefore = Me.Count
End Function

'AddBefore
' Adds element before given index.
' {1,2,3} -> index > 3 -> Push val
' {1,2,3} -> index <= 1 -> Unshift val
' {} -> index = any -> Push val
' @param Long index | Index before which will be added an element
' @param Variant val | One element (String, number, ...) to add into iArray
' @return Long | Count of elements inside iArray
Public Function AddBefore(ByVal index As Long, ByVal val As vStaffInfo) As Long
  If Me.Count < 1 Or index + 1 > Me.Count Then
    Me.Push val
  ElseIf index + 1 <= 1 Then
    Me.Unshift val
  Else
    Me.Add val, bef:=index + 1
  End If
  AddBefore = Me.Count
End Function

'Avg
' Calculates the average of the numeric mainArray.
' @return Variant | Average value / "NaN" if iArray contains non-numeric value(s)
Public Function Avg() As Variant
  If Not Me.ContainsOnlyNumeric Then Avg = "NaN": Exit Function
  Avg = Me.sum / Me.Count
End Function

'Clear
' Empties iArray
Public Function Clear() As Boolean
  For i = mainArray.Count - 1 To 0 Step -1
    mainArray.Remove i + 1
  Next i
  Clear = IIf(mainArray.Count = 0, True, False)
End Function

'Clone
' Makes a hard copy of the mainArray
' @return mainArray | Return exact copy of itself
Public Function clone() As vStaffInfoList
  Set clone = New vStaffInfoList
  For i = 0 To Me.Count - 1
    clone.Push Me(i)
  Next i
End Function

'Contains
' Checks if given value is used inside mainArray.
' @param Variant val | One element (String, number, ...) to by checked if it exists in iArray
' $return Boolean | True = exists, False = doesn't exists
Public Function Contains(ByVal val As vStaffInfo) As Boolean
  Contains = False
  Dim el As Variant
  For Each el In mainArray
    If IsObject(val) = True Or VarType(val) And 8192 Then
        If (VarType(el) And 8192) And (VarType(val) And 8192) Then
            If ArrayDifference(el, val) Then
                Contains = True: Exit Function
            End If
        ElseIf IsObject(el) = True And IsObject(val) = True Then
            If el Is val Then
                Contains = True: Exit Function
            End If
        End If
    Else
        If IsObject(el) = False And (VarType(el) And 8192) <> 8192 Then
            If el = val Then
            Contains = True: Exit Function
            End If
        End If
    End If
  Next el
End Function

'ContainsAll
' Checks if all given values are used inside mainArray.
' @param Variant val | values to by checked if it exists in iArray
' $return Boolean | True = all exists, False = one ore more values doesn't exists
Public Function ContainsAll(ByVal val As vStaffInfoList) As Boolean
  ContainsAll = False
  Dim foundOccurrences As Integer: foundOccurrences = 0
  Dim values As New vStaffInfoList
  If Not TypeOf val Is vStaffInfoList Then
    If IsArray(val) Then
      values.PushArray (val)
    Else
      values.Push (val)
    End If
  Else
    Set values = val
  End If
  For i = 0 To values.Count - 1
    If Me.Contains(values(i)) Then Inc foundOccurrences
  Next i
  If foundOccurrences = values.Count Then ContainsAll = True
End Function

'CountOccurrences
' Checks how many times is given value used inside mainArray.
' @param Variant val | One element (String, number, ...) to by checked
' @return Long | Count of matched occurrences
Public Function CountOccurrences(val As Variant) As Long
  CountOccurrences = 0
  Dim el As Variant
  For Each el In mainArray
  
    If IsObject(val) = True Or VarType(val) And 8192 Then
        If VarType(el) And 8192 And VarType(val) And 8192 Then
            If ArrayDifference(el, val) Then
                Inc CountOccurrences
                Exit Function
            End If
        ElseIf IsObject(el) = True And IsObject(val) = True Then
            If el Is val Then
                Inc CountOccurrences
                Exit Function
            End If
        End If
    Else
        If IsObject(el) = False And Not (VarType(el) And 8192) Then
            If el = val Then
                Inc CountOccurrences
                Exit Function
            End If
        End If
    End If
  
     'If el = val Then Inc CountOccurrences
  Next el
End Function

'Dequeue
' Removes an element from the begining of the mainArray.
' @return Variant | Removed element or Empty, if iArray is empty
'刪除開頭一個元素。
Public Function Dequeue() As vStaffInfo
  Dequeue = Empty
  If mainArray.Count > 0 Then
    If VarType(Me(0)) = vbString Then
        Dequeue = Me(0)
    ElseIf TypeOf Me(0) Is vStaffInfoList Then
        Set Dequeue = Me(0)
    ElseIf VarType(Me(0)) = vbArray Then
        Set Dequeue = Me(0)
    ElseIf VarType(Me(0)) = vbObject Then
        Set Dequeue = Me(0)
    Else
        Dequeue = Me(0)
    End If
    
    mainArray.Remove 1
  End If
End Function

'Difference
' Checks for number of differences between two arrays, what was added/deleted or combination.
' @param iArray oldArray | Old iArray to be compared with current iArray
' @param String retType | �dd= deleted from old iArray, �aa= added in current iArray, �cc= combination of both (default)
' @return iArray | iArray with differences found
Public Function Difference(ByRef oldArray As vStaffInfoList, Optional ByVal retType As String = "c") As vStaffInfoList
  Set Difference = New vStaffInfoList
  Select Case LCase(retType)
    Case "d"
      For i = 0 To oldArray.Count - 1
        If Me.Contains(oldArray(i)) = False Then Difference.Push oldArray(i)
      Next i
    Case "a"
      For i = 0 To Count - 1
        If oldArray.Contains(Me(i)) = False Then Difference.Push Me(i)
      Next i
    Case "c"
      For i = 0 To oldArray.Count - 1
        If Me.Contains(oldArray(i)) = False Then Difference.Push oldArray(i)
      Next i
      For i = 0 To Count - 1
        If oldArray.Contains(Me(i)) = False Then Difference.Push Me(i)
      Next i
    Case Else
      err.Raise Number:=5, Description:="Unknown Difference return type attribute:" & vbCrLf & _
                                        "Allowed are 'A'dded/'D'eleted/'C'ombination of both"
  End Select
End Function

'DropLeft
' Remove n elements from the beginning of the mainArray. If n > count of iArray elements, all elements are removed.
' @param Long n | Number of elements to be removed
' @return iArray | Array of the removed elements
Public Function DropLeft(ByRef N As Long) As vStaffInfoList
  Set DropLeft = New vStaffInfoList
  If N > Me.Count Then N = Me.Count
  For i = 0 To N - 1
    DropLeft.Push Me(i)
  Next i
  For i = N - 1 To 0 Step -1
    Me.Remove (i)
  Next i
End Function

'DropRight
' Remove n elements from the end of the mainArray. If n > count of iArray elements, all elements are removed.
' @param Long n | Number of elements to be removed
' @return iArray | Array of the removed elements
Public Function DropRight(ByRef N As Long) As vStaffInfoList
  Set DropRight = New vStaffInfoList
  If N > Me.Count Then N = Me.Count
  For i = Me.Count - N To Me.Count - 1
    DropRight.Push Me(i)
  Next i
  For i = Me.Count - 1 To Me.Count - N Step -1
    Me.Remove (i)
  Next i
End Function

'Enqueue
' Adds an element at the end of the mainArray.
' @param Variant val | One element (String, number, ...) to add into iArray
' @return Long | Count of elements inside iArray
Public Function Enqueue(ByVal val As Variant) As Long
  Enqueue = Push(val)
End Function

'EnqueueArray
' Adds elements at the end of the iArray
' @param Variant val | Array() or iArray of elements to add into iArray
' @return Long | Count of elements inside array
Public Function EnqueueArray(ByVal val As Variant) As Long
  EnqueueArray = PushArray(val)
End Function

'First
' Returns value of the first element of the mainArray.
' @return Variant | Value of the first element or Empty if iArray is Empty
Public Function First() As vStaffInfo
  Set First = IIf(Me.Count > 0, Me(0), Empty)
End Function

'Head
' Returns all elements of iArray, except last one.
' @return iArray | Copy of original array, without last element
Public Function head() As vStaffInfoList
  Set head = Me.clone
  head.Pop
End Function

'Intersect
' Search for element that exists in both iArrays.
' @param iArray intArray | iArray to be intersected with current iArray
' @return iArray | Intersected values
Public Function Intersect(ByRef intersectedArr As vStaffInfoList) As vStaffInfoList
  Set Intersect = New vStaffInfoList
  Dim el As Variant
  For Each el In mainArray
    If intersectedArr.Contains(el) Then
      If Not Intersect.Contains(el) Then Intersect.Push (el)
    End If
  Next el
End Function

'ContainsOnlyNumeric
' Verify that all elements are numbers or convertable to numbers
' $return Boolean | True = contains only numeric values, False = contains inconvertible values
Public Function ContainsOnlyNumeric() As Boolean
  ContainsOnlyNumeric = True
  Dim el As Variant
  For Each el In mainArray
    If Not IsNumeric(el) Then ContainsOnlyNumeric = False: Exit Function
  Next el
End Function

'Join
' Joins two iArrays.
' @param iArray jArray | iArray to be joined with current iArray
' @return iArray | Joined iArray
Public Function Join(ByRef joinArr As vStaffInfoList) As vStaffInfoList
  Set Join = New vStaffInfoList
  Join.PushArray Me
  Join.PushArray joinArr
End Function

'Last
' Returns value of the last element of the mainArray.
' @return Variant | Value of the last element or Empty if iArray is Empty
Public Function Last() As vStaffInfo
  Set Last = IIf(Me.Count > 0, Me(Me.Count - 1), Empty)
End Function

'OccurrenceIndexes
' Returns all indexes of a value in mainArray.
' @return iArray | iArray containing indexes of occurrence
Public Function OccurenceIndexes(val As Variant) As vStaffInfoList
  Set OccurenceIndexes = New vStaffInfoList
  For i = 0 To Me.Count - 1
    If Me(i) = val Then
        OccurenceIndexes.Push (i)
    End If
  Next i
End Function

'Pop
' Removes an element from the end of the mainArray.
' @return Variant | Removed element or Empty, if iArray is empty
Public Function Pop() As vStaffInfo
  If mainArray.Count > 0 Then
    If VarType(Me(mainArray.Count - 1)) = vbObject Then
       Set Pop = Me(mainArray.Count - 1)
    Else
        Pop = Me(mainArray.Count - 1)
    End If
    mainArray.Remove mainArray.Count
  End If
End Function
  
  

'Push
' Adds an element at the end of the mainArray.
' @param Variant val | One element (String, number, ...) to add into iArray
' @return Long | Count of elements inside iArray
Public Function Push(ByVal val As vStaffInfo) As Long
  mainArray.Add val
  Push = mainArray.Count
End Function

'PushArray
' Adds elements at the end of the mainArray.
' @param Variant val | Array() or iArray of elements to add into iArray
' @return Long | Count of elements inside array
Public Function PushArray(ByVal val As Variant) As Long
  If TypeOf val Is vStaffInfoList Then
    For i = 0 To val.Count - 1
      Me.Push val(i)
    Next i
  Else
    For i = LBound(val) To UBound(val)
      Me.Push val(i)
    Next i
  End If
  PushArray = Me.Count
End Function

'RemoveDuplicates
' Keeps only the first occurrence of the value. Affects original array
' @return Long | Count of the removed elements
Public Function RemoveDuplicates() As Long
  RemoveDuplicates = 0
  For i = Me.Count - 1 To 0 Step -1
    If Me.CountOccurrences(Me(i)) > 1 Then
      Me.Remove i
      Inc RemoveDuplicates
    End If
  Next i
End Function

'Reverse
' Reverses the content of the iArray
' @return iArray | Reversed iArray
Public Function Reverse() As vStaffInfoList
  Set Reverse = New vStaffInfoList
  For i = 0 To Me.Count - 1
    Reverse.Unshift Me(i)
  Next i
End Function

'Shift
' Removes an element from the begining of the mainArray.
' @return Variant | Removed element or Empty, if iArray is empty
'轉移
' 從 iArray 的開頭刪除一個元素。
' @返回第一個元素 | 如果 iArray 為空，則刪除元素或為空
Public Function shift() As vStaffInfo
  shift = Empty
  If mainArray.Count > 0 Then
    If VarType(Me(0)) = vbString Then
        shift = Me(0)
    ElseIf TypeOf Me(0) Is vStaffInfoList Then
        Set shift = Me(0)
    ElseIf VarType(Me(0)) = vbArray Then
        Set shift = Me(0)
    ElseIf VarType(Me(0)) = vbObject Then
        Set shift = Me(0)
    Else
        shift = Me(0)
    End If
    
    mainArray.Remove 1
  End If
End Function

'Shuffle
' Randomly mixes content of the iArray
' @return iArray | Shuffled iArray
' 隨機播放
' 隨機混合 iArray 的內容
'@return iArray | 打亂iArray
Public Function Shuffle() As vStaffInfoList
  Set Shuffle = New vStaffInfoList
  Dim keys As New vStaffInfoList
  For i = 0 To Me.Count - 1
    keys.Push (i)
  Next i
  Dim rndNo As Long
  Do While keys.Count > 0
    rndNo = randomFromTo(0, keys.Count - 1)
    Shuffle.Push Me(keys(rndNo))
    keys.Remove (rndNo)
  Loop
End Function

'Sum
' Calculates the sum of the numeric mainArray.
' @return Variant | Sum value / "NaN" if iArray contains non-numeric value(s)
Public Function sum() As Variant
  If Not Me.ContainsOnlyNumeric Then sum = "NaN": Exit Function
  sum = 0
  Dim el As Variant
  For Each el In mainArray
    sum = sum + el
  Next el
End Function

'Tail
' Returns all elements of iArray, except first one.
' @return iArray | Copy of original array, without first element
'返回陣列中除了第一個元素的剩余元素陣列
Public Function Tail() As vStaffInfoList
  Set Tail = Me.clone
  Tail.Dequeue
End Function

Public Function ToList()
  If Me.Count = 0 Then ToList = Null: Exit Function
  Dim tarr()
  ReDim tarr(Me.Count - 1)
  For i = 0 To Me.Count - 1
    If VarType(Me(i)) = vbString Then
        tarr(i) = Me(i)
    ElseIf TypeOf Me(i) Is vStaffInfoList Then
        Set tarr(i) = Me(i)
    ElseIf VarType(Me(i)) = vbObject Then
        Set tarr(i) = Me(i)
    Else
        tarr(i) = Me(i)
    End If
  Next i
  ToList = tarr
End Function

'ToString
' Creates string representation of the mainArray.
' @param String delimiter | Optional character to separate the iArray's elements (default = " ")
' @return String | Formated representation of tha iArray
Public Function ToString(Optional ByVal delimiter As String = " ") As String
  If Me.Count = 0 Then ToString = "{}": Exit Function
  ToString = vbNullString
  For i = 0 To Me.Count - 1
    If i = 0 Then ToString = ToString + "{"
    If i > 0 Then ToString = ToString + delimiter
    If VarType(Me(i)) = vbString Then
        ToString = ToString + Chr$(34)
        ToString = ToString + CStr(Me(i))
        ToString = ToString + Chr$(34)
    ElseIf TypeOf Me(i) Is vStaffInfoList Then
        ToString = ToString + Me(i).ToString(delimiter)
    ElseIf (VarType(Me(i)) And vbArray) = vbArray Then
        ToString = ToString + "[Array]"
    ElseIf VarType(Me(i)) = vbObject Then
        ToString = ToString + "[Object]"
    Else
        ToString = ToString + CStr(Me(i))
    End If
    
    If i = mainArray.Count - 1 Then ToString = ToString + "}"
  Next i
End Function

'Union
' Combines both iArrays and removes duplicities
' @param iArray uArray | iArray to be unioned with current iArray
' @return iArray | Combined values without duplicities
Public Function Union(ByRef uArr As vStaffInfoList) As vStaffInfoList
  Set Union = Me.clone
  Union.PushArray uArr
  Union.RemoveDuplicates
End Function

'Unique
' Returns copy of iArray without duplicated values. Original array is not affected
' @return iArray | iArray with unique values
Public Function Unique() As vStaffInfoList
  Set Unique = New vStaffInfoList
  Dim el As Variant
  For Each el In mainArray
    If Not Unique.Contains(el) Then Unique.Push (el)
  Next el
End Function

'Unshift
' Add an element at the begining of the mainArray.
' @param Variant val | One element (String, number, ...) to add into iArray
' @return Long | Count of elements inside iArray
Public Function Unshift(ByVal val As Variant) As Long
  If mainArray.Count = 0 Then
    Unshift = Push(val)
  Else
    mainArray.Add val, before:=1
    Unshift = mainArray.Count
  End If
End Function

'UnshiftArray
' Add elements at the begining of the mainArray.
' @param Variant val | Array() or iArray of elements to add into iArray
' @return Long | Count of elements inside iArray
Public Function UnshiftArray(ByVal val As Variant) As Long
  If TypeOf val Is vStaffInfoList Then
    For i = val.Count - 1 To 0 Step -1
      Unshift val(i)
    Next i
  Else
    For i = UBound(val) To LBound(val) Step -1
      Unshift val(i)
    Next i
  End If
  UnshiftArray = mainArray.Count
End Function


' #####################
' # PRIVATE FUNCTIONS #
' #####################
Sub Inc(ByRef i)
   i = i + 1
End Sub

'Private Function rangeToArray(ByVal rng As Range) As Variant
'  rangeToArray = rng.Value
'End Function

Private Function randomFromTo(ByVal from As Long, ByVal upTo As Long) As Long
  Randomize
  randomFromTo = Int(from + Rnd() * (upTo - from + 1))
End Function

'比對 兩個陣列是否一樣
Private Function ArrayDifference(arr1 As Variant, arr2 As Variant) As Boolean

    Dim i As Integer
    If UBound(arr1) = UBound(arr2) Then
        For i = 0 To UBound(arr1)
            If arr1(i) = arr2(i) Then
                ArrayDifference = True
            Else
                ArrayDifference = False
                Exit Function
            End If
        Next
    Else
        ArrayDifference = False
    End If

End Function

'@Description("changes the contents of the array by removing or replacing existing elements and/or adding new elements in place.")
Public Function Splice( _
        ByVal StartIndex As Long, _
        ParamArray Args() As Variant _
    ) As Variant()
    'Dim LocalItems() As Variant
    Dim ActualStart As Long
    Dim ActualDeleteCount As Long
    Dim ArgsCount As Long
    Dim LocalLength As Long
    Dim LocalArgs() As Variant
    Dim result() As Variant
    Dim i As Long
    Dim TempArray() As Variant
    Dim ItemCount As Long
    Dim TempItems() As Variant
    
    LocalArgs = Args
    'LocalItems = mainArray
    LocalLength = Me.Count
    If StartIndex < LocalLength Then
        ActualStart = StartIndex
    Else
        ActualStart = min(StartIndex, LocalLength)
    End If
    
    ArgsCount = UBound(LocalArgs) + 1
    If ArgsCount = 0 Then
        ' only a start index has been supplied
        ' we're gonna delete everything
        ' 僅提供了起始索引
         '我們要刪除所有內容
        ItemCount = 0
        ActualDeleteCount = LocalLength - ActualStart
    Else
        ' first arg in args is delete count, second onwards are insertion items
        ' args 中的第一個參數是刪除計數，第二個之後是插入項
        ItemCount = ArgsCount - 1
        'deleteCount is first element in args.
        'deleteCount 是 args 中的第一個元素。
        ActualDeleteCount = min(max(Args(LBound(Args)), 0), LocalLength - ActualStart)
    End If
    

    ' get items to be deleted for return val
    ' 取得和刪除
    If ActualDeleteCount > 0 Then
        ReDim result(0 To ActualDeleteCount - 1)
        i = 0
        Do While i < ActualDeleteCount
            If IsObject(Me(ActualStart)) Then
                Set result(i) = Me(ActualStart)
                Me.Remove ActualStart
            Else
                result(i) = Me(ActualStart)
                Me.Remove ActualStart
            End If
            Inc i
        Loop
    Else
        ' return empty array if nothing to be deleted
        ReDim result(0)
    End If
    
    '取得要插入的陣列資料
    If ItemCount > 0 Then
        ReDim TempItems(0 To ItemCount - 1)
        For i = 0 To ItemCount - 1
            If IsObject(LocalArgs(i + 1)) Then
                Set TempItems(i) = LocalArgs(i + 1)
            Else
                TempItems(i) = LocalArgs(i + 1)
            End If
        Next
    Me.AddArrayBefore ActualStart, TempItems
    End If
    
    
    Splice = result
End Function

Attribute VB_Name = "vbeamRange"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public startX As Double
Public endX As Double
Public startY As Double
Public endY As Double
Public dy As Double

Attribute VB_Name = "vbeamRangeList"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
'MIT License
'
'Copyright (c) 2019-2021 Petr Katerinak
'
'Permission is hereby granted, free of charge, to any person obtaining a copy
'of this software and associated documentation files (the "Software"), to deal
'in the Software without restriction, including without limitation the rights
'to use, copy, modify, merge, publish, distribute, sublicense, and/or sell
'copies of the Software, and to permit persons to whom the Software is
'furnished to do so, subject to the following conditions:
'
'The above copyright notice and this permission notice shall be included in all
'copies or substantial portions of the Software.
'
'THE SOFTWARE IS PROVIDED "AS IS", WITHOUT WARRANTY OF ANY KIND, EXPRESS OR
'IMPLIED, INCLUDING BUT NOT LIMITED TO THE WARRANTIES OF MERCHANTABILITY,
'FITNESS FOR A PARTICULAR PURPOSE AND NONINFRINGEMENT. IN NO EVENT SHALL THE
'AUTHORS OR COPYRIGHT HOLDERS BE LIABLE FOR ANY CLAIM, DAMAGES OR OTHER
'LIABILITY, WHETHER IN AN ACTION OF CONTRACT, TORT OR OTHERWISE, ARISING FROM,
'OUT OF OR IN CONNECTION WITH THE SOFTWARE OR THE USE OR OTHER DEALINGS IN THE
'SOFTWARE.
'
' Version of iArray: 1.0
''修正 元素從 0 開始

Private mainArray As New Collection
Private i As Long ' Counter

' #####################
' #    CONSTRUCTOR    #
' #####################
'Private Sub Class_Initialize()
'  Set mainArray = New Collection
'End Sub

' #####################
' #  Getter / Setter  #
' #####################
'Attribute Element.VB_UserMemId = 0 saved in both procedures

'@DefaultMember
Public Property Get element(ByVal index As Long) As vbeamRange
Attribute element.VB_UserMemId = 0
    If index + 1 < 1 Or index + 1 > mainArray.Count Then
        Set element = Nothing
        Exit Property
    End If
    If IsObject(mainArray(index + 1)) = True Then
        Set element = mainArray(index + 1)
    Else
        element = mainArray(index + 1)
    End If

 
End Property

'@DefaultMember
Public Property Let element(ByVal index As Long, ByVal val As vbeamRange)
Attribute element.VB_UserMemId = 0
  If index = 0 And mainArray.Count = 0 Then
    Me.Push val
    Exit Property
  End If
  If index + 1 > mainArray.Count Then
    Dim eMsg As String
    eMsg = IIf(mainArray.Count > 0, _
               "Index (" & index + 1 & ") out of iArray bounds (1-" & mainArray.Count & ")", _
               "iArray doesn't have any indexes")
    err.Raise Number:=9, Description:=eMsg
    Exit Property
  End If
  mainArray.Add val, after:=index + 1
  mainArray.Remove index + 1
End Property

' #############################
' # COMMON COLLECTION METHODS #
' #############################
Public Function Count() As Long
  Count = mainArray.Count
End Function
Public Sub Add(ByVal val As vbeamRange, Optional ByVal bef As Variant = Empty, Optional ByVal aft As Variant = Empty)
  If IsEmpty(bef) And IsEmpty(aft) Then
    mainArray.Add val
  ElseIf IsEmpty(bef) Then
    mainArray.Add val, , , aft
  ElseIf IsEmpty(aft) Then
    mainArray.Add val, , bef
  Else
    mainArray.Add val, , bef, aft
  End If
End Sub
Public Sub Remove(index As Long)
  mainArray.Remove index + 1
End Sub

' ####################
' #  PUBLIC METHODS  #
' ####################

'AddAfter
' Adds element after given index.
' {1,2,3} -> index >= 3 -> Push val
' {1,2,3} -> index < 1 -> Unshift val
' {} -> index = any -> Push val
' @param Long index | Index after which will be added an element
' @param Variant val | One element (String, number, ...) to add into iArray
' @return Long | Count of elements inside iArray
Public Function AddAfter(ByVal index As Long, ByVal val As vbeamRange) As Long
  If Me.Count < 1 Or index + 1 >= Me.Count Then
    Me.Push val
  ElseIf index + 1 < 1 Then
    Me.Unshift val
  Else
    Me.Add val, aft:=index + 1
  End If
  AddAfter = Me.Count
End Function

'AddArrayAfter
' Adds elements after given index.
' {1,2,3} -> index >= 3 -> PushArray val
' {1,2,3} -> index < 1 -> UnshiftArray val
' {} -> index = any -> PushArray val
' @param Long index | Index after which will be added an element
' @param Variant val | Array() or iArray of elements to add into iArray
' @return Long | Count of elements inside iArray
Public Function AddArrayAfter(ByVal index As Long, ByVal val As Variant) As Long
  If Me.Count < 1 Or index + 1 >= Me.Count Then
    Me.PushArray val
  ElseIf index + 1 < 1 Then
    Me.UnshiftArray val
  Else
    If TypeOf val Is vbeamRangeList Then
      For i = 0 To val.Count - 1
        Me.Add val(i), aft:=index + 1
        Inc index
      Next i
    Else
      For i = LBound(val) To UBound(val)
        Me.Add val(i), aft:=index + 1
        Inc index
      Next i
    End If
  End If
  AddArrayAfter = Me.Count
End Function

'AddArrayBefore
' Adds elements before given index.
' {1,2,3} -> index > 3 -> PushArray val
' {1,2,3} -> index <= 1 -> UnshiftArray val
' {} -> index = any -> PushArray val
' @param Long index | Index after which will be added an element
' @param Variant val | Array() or iArray of elements to add into iArray
' @return Long | Count of elements inside iArray
Public Function AddArrayBefore(ByVal index As Long, ByVal val As Variant) As Long
  If Me.Count < 1 Or index + 1 > Me.Count Then
    Me.PushArray val
  ElseIf index <= 0 Then
    Me.UnshiftArray val
  Else
    If TypeOf val Is vbeamRangeList Then
      For i = val.Count - 1 To 0 Step -1
        Me.Add val(i), bef:=index + 1
      Next i
    Else
      For i = UBound(val) To LBound(val) Step -1
        Me.Add val(i), bef:=index + 1
      Next i
    End If
  End If
  AddArrayBefore = Me.Count
End Function

'AddBefore
' Adds element before given index.
' {1,2,3} -> index > 3 -> Push val
' {1,2,3} -> index <= 1 -> Unshift val
' {} -> index = any -> Push val
' @param Long index | Index before which will be added an element
' @param Variant val | One element (String, number, ...) to add into iArray
' @return Long | Count of elements inside iArray
Public Function AddBefore(ByVal index As Long, ByVal val As vbeamRange) As Long
  If Me.Count < 1 Or index + 1 > Me.Count Then
    Me.Push val
  ElseIf index + 1 <= 1 Then
    Me.Unshift val
  Else
    Me.Add val, bef:=index + 1
  End If
  AddBefore = Me.Count
End Function



'Clear
' Empties iArray
Public Function Clear() As Boolean
  For i = mainArray.Count - 1 To 0 Step -1
    mainArray.Remove i + 1
  Next i
  Clear = IIf(mainArray.Count = 0, True, False)
End Function

'Clone
' Makes a hard copy of the mainArray
' @return mainArray | Return exact copy of itself
Public Function clone() As vbeamRangeList
  Set clone = New vbeamRangeList
  For i = 0 To Me.Count - 1
    clone.Push Me(i)
  Next i
End Function

'Contains
' Checks if given value is used inside mainArray.
' @param Variant val | One element (String, number, ...) to by checked if it exists in iArray
' $return Boolean | True = exists, False = doesn't exists
Public Function Contains(ByVal val As vbeamRange) As Boolean
  Contains = False
  Dim el As Variant
  For Each el In mainArray
    If IsObject(val) = True Or VarType(val) And 8192 Then
        If (VarType(el) And 8192) And (VarType(val) And 8192) Then
            If ArrayDifference(el, val) Then
                Contains = True: Exit Function
            End If
        ElseIf IsObject(el) = True And IsObject(val) = True Then
            If el Is val Then
                Contains = True: Exit Function
            End If
        End If
    Else
        If IsObject(el) = False And (VarType(el) And 8192) <> 8192 Then
            If el = val Then
            Contains = True: Exit Function
            End If
        End If
    End If
  Next el
End Function

'ContainsAll
' Checks if all given values are used inside mainArray.
' @param Variant val | values to by checked if it exists in iArray
' $return Boolean | True = all exists, False = one ore more values doesn't exists
Public Function ContainsAll(ByVal val As vbeamRangeList) As Boolean
  ContainsAll = False
  Dim foundOccurrences As Integer: foundOccurrences = 0
  Dim values As New vbeamRangeList
  If Not TypeOf val Is vbeamRangeList Then
    If IsArray(val) Then
      values.PushArray (val)
    Else
      values.Push (val)
    End If
  Else
    Set values = val
  End If
  For i = 0 To values.Count - 1
    If Me.Contains(values(i)) Then Inc foundOccurrences
  Next i
  If foundOccurrences = values.Count Then ContainsAll = True
End Function


'Dequeue
' Removes an element from the begining of the mainArray.
' @return Variant | Removed element or Empty, if iArray is empty
'刪除開頭一個元素。
Public Function Dequeue() As vbeamRange
  Dequeue = Empty
  If mainArray.Count > 0 Then
    If VarType(Me(0)) = vbString Then
        Dequeue = Me(0)
    ElseIf TypeOf Me(0) Is vbeamRangeList Then
        Set Dequeue = Me(0)
    ElseIf VarType(Me(0)) = vbArray Then
        Set Dequeue = Me(0)
    ElseIf VarType(Me(0)) = vbObject Then
        Set Dequeue = Me(0)
    Else
        Dequeue = Me(0)
    End If
    
    mainArray.Remove 1
  End If
End Function

'Difference
' Checks for number of differences between two arrays, what was added/deleted or combination.
' @param iArray oldArray | Old iArray to be compared with current iArray
' @param String retType | �dd= deleted from old iArray, �aa= added in current iArray, �cc= combination of both (default)
' @return iArray | iArray with differences found
Public Function Difference(ByRef oldArray As vbeamRangeList, Optional ByVal retType As String = "c") As vbeamRangeList
  Set Difference = New vbeamRangeList
  Select Case LCase(retType)
    Case "d"
      For i = 0 To oldArray.Count - 1
        If Me.Contains(oldArray(i)) = False Then Difference.Push oldArray(i)
      Next i
    Case "a"
      For i = 0 To Count - 1
        If oldArray.Contains(Me(i)) = False Then Difference.Push Me(i)
      Next i
    Case "c"
      For i = 0 To oldArray.Count - 1
        If Me.Contains(oldArray(i)) = False Then Difference.Push oldArray(i)
      Next i
      For i = 0 To Count - 1
        If oldArray.Contains(Me(i)) = False Then Difference.Push Me(i)
      Next i
    Case Else
      err.Raise Number:=5, Description:="Unknown Difference return type attribute:" & vbCrLf & _
                                        "Allowed are 'A'dded/'D'eleted/'C'ombination of both"
  End Select
End Function


'First
' Returns value of the first element of the mainArray.
' @return Variant | Value of the first element or Empty if iArray is Empty
Public Function First() As vbeamRange
  Set First = IIf(Me.Count > 0, Me(0), Empty)
End Function

'Head
' Returns all elements of iArray, except last one.
' @return iArray | Copy of original array, without last element
Public Function head() As vbeamRangeList
  Set head = Me.clone
  head.Pop
End Function

'Intersect
' Search for element that exists in both iArrays.
' @param iArray intArray | iArray to be intersected with current iArray
' @return iArray | Intersected values
Public Function Intersect(ByRef intersectedArr As vbeamRangeList) As vbeamRangeList
  Set Intersect = New vbeamRangeList
  Dim el As Variant
  For Each el In mainArray
    If intersectedArr.Contains(el) Then
      If Not Intersect.Contains(el) Then Intersect.Push (el)
    End If
  Next el
End Function

'ContainsOnlyNumeric
' Verify that all elements are numbers or convertable to numbers
' $return Boolean | True = contains only numeric values, False = contains inconvertible values
Public Function ContainsOnlyNumeric() As Boolean
  ContainsOnlyNumeric = True
  Dim el As Variant
  For Each el In mainArray
    If Not IsNumeric(el) Then ContainsOnlyNumeric = False: Exit Function
  Next el
End Function

'Join
' Joins two iArrays.
' @param iArray jArray | iArray to be joined with current iArray
' @return iArray | Joined iArray
Public Function Join(ByRef joinArr As vbeamRangeList) As vbeamRangeList
  Set Join = New vbeamRangeList
  Join.PushArray Me
  Join.PushArray joinArr
End Function

'Last
' Returns value of the last element of the mainArray.
' @return Variant | Value of the last element or Empty if iArray is Empty
Public Function Last() As vbeamRange
  Set Last = IIf(Me.Count > 0, Me(Me.Count - 1), Empty)
End Function


'Pop
' Removes an element from the end of the mainArray.
' @return Variant | Removed element or Empty, if iArray is empty
Public Function Pop() As vbeamRange
  If mainArray.Count > 0 Then
    If VarType(Me(mainArray.Count - 1)) = vbObject Then
       Set Pop = Me(mainArray.Count - 1)
    Else
        Pop = Me(mainArray.Count - 1)
    End If
    mainArray.Remove mainArray.Count
  End If
End Function
  
  

'Push
' Adds an element at the end of the mainArray.
' @param Variant val | One element (String, number, ...) to add into iArray
' @return Long | Count of elements inside iArray
Public Function Push(ByVal val As vbeamRange) As Long
  mainArray.Add val
  Push = mainArray.Count
End Function

'PushArray
' Adds elements at the end of the mainArray.
' @param Variant val | Array() or iArray of elements to add into iArray
' @return Long | Count of elements inside array
Public Function PushArray(ByVal val As Variant) As Long
  If TypeOf val Is vbeamRangeList Then
    For i = 0 To val.Count - 1
      Me.Push val(i)
    Next i
  Else
    For i = LBound(val) To UBound(val)
      Me.Push val(i)
    Next i
  End If
  PushArray = Me.Count
End Function


'Reverse
' Reverses the content of the iArray
' @return iArray | Reversed iArray
Public Function Reverse() As vbeamRangeList
  Set Reverse = New vbeamRangeList
  For i = 0 To Me.Count - 1
    Reverse.Unshift Me(i)
  Next i
End Function

'Shift
' Removes an element from the begining of the mainArray.
' @return Variant | Removed element or Empty, if iArray is empty
'轉移
' 從 iArray 的開頭刪除一個元素。
' @返回第一個元素 | 如果 iArray 為空，則刪除元素或為空
Public Function shift() As vbeamRange
  shift = Empty
  If mainArray.Count > 0 Then
    If VarType(Me(0)) = vbString Then
        shift = Me(0)
    ElseIf TypeOf Me(0) Is vbeamRangeList Then
        Set shift = Me(0)
    ElseIf VarType(Me(0)) = vbArray Then
        Set shift = Me(0)
    ElseIf VarType(Me(0)) = vbObject Then
        Set shift = Me(0)
    Else
        shift = Me(0)
    End If
    
    mainArray.Remove 1
  End If
End Function

'Shuffle
' Randomly mixes content of the iArray
' @return iArray | Shuffled iArray
' 隨機播放
' 隨機混合 iArray 的內容
'@return iArray | 打亂iArray
Public Function Shuffle() As vbeamRangeList
  Set Shuffle = New vbeamRangeList
  Dim keys As New vbeamRangeList
  For i = 0 To Me.Count - 1
    keys.Push (i)
  Next i
  Dim rndNo As Long
  Do While keys.Count > 0
    rndNo = randomFromTo(0, keys.Count - 1)
    Shuffle.Push Me(keys(rndNo))
    keys.Remove (rndNo)
  Loop
End Function



'Tail
' Returns all elements of iArray, except first one.
' @return iArray | Copy of original array, without first element
'返回陣列中除了第一個元素的剩余元素陣列
Public Function Tail() As vbeamRangeList
  Set Tail = Me.clone
  Tail.Dequeue
End Function

Public Function ToList()
  If Me.Count = 0 Then ToList = Null: Exit Function
  Dim tarr()
  ReDim tarr(Me.Count - 1)
  For i = 0 To Me.Count - 1
    If VarType(Me(i)) = vbString Then
        tarr(i) = Me(i)
    ElseIf TypeOf Me(i) Is vbeamRangeList Then
        Set tarr(i) = Me(i)
    ElseIf VarType(Me(i)) = vbObject Then
        Set tarr(i) = Me(i)
    Else
        tarr(i) = Me(i)
    End If
  Next i
  ToList = tarr
End Function

'ToString
' Creates string representation of the mainArray.
' @param String delimiter | Optional character to separate the iArray's elements (default = " ")
' @return String | Formated representation of tha iArray
Public Function ToString(Optional ByVal delimiter As String = " ") As String
  If Me.Count = 0 Then ToString = "{}": Exit Function
  ToString = vbNullString
  For i = 0 To Me.Count - 1
    If i = 0 Then ToString = ToString + "{"
    If i > 0 Then ToString = ToString + delimiter
    If VarType(Me(i)) = vbString Then
        ToString = ToString + Chr$(34)
        ToString = ToString + CStr(Me(i))
        ToString = ToString + Chr$(34)
    ElseIf TypeOf Me(i) Is vbeamRangeList Then
        ToString = ToString + Me(i).ToString(delimiter)
    ElseIf (VarType(Me(i)) And vbArray) = vbArray Then
        ToString = ToString + "[Array]"
    ElseIf VarType(Me(i)) = vbObject Then
        ToString = ToString + "[Object]"
    Else
        ToString = ToString + CStr(Me(i))
    End If
    
    If i = mainArray.Count - 1 Then ToString = ToString + "}"
  Next i
End Function

'Union
' Combines both iArrays and removes duplicities
' @param iArray uArray | iArray to be unioned with current iArray
' @return iArray | Combined values without duplicities
Public Function Union(ByRef uArr As vbeamRangeList) As vbeamRangeList
  Set Union = Me.clone
  Union.PushArray uArr
  Union.RemoveDuplicates
End Function

'Unique
' Returns copy of iArray without duplicated values. Original array is not affected
' @return iArray | iArray with unique values
Public Function Unique() As vbeamRangeList
  Set Unique = New vbeamRangeList
  Dim el As Variant
  For Each el In mainArray
    If Not Unique.Contains(el) Then Unique.Push (el)
  Next el
End Function

'Unshift
' Add an element at the begining of the mainArray.
' @param Variant val | One element (String, number, ...) to add into iArray
' @return Long | Count of elements inside iArray
Public Function Unshift(ByVal val As Variant) As Long
  If mainArray.Count = 0 Then
    Unshift = Push(val)
  Else
    mainArray.Add val, before:=1
    Unshift = mainArray.Count
  End If
End Function




' #####################
' # PRIVATE FUNCTIONS #
' #####################
Sub Inc(ByRef i)
   i = i + 1
End Sub



'比對 兩個陣列是否一樣
Private Function ArrayDifference(arr1 As Variant, arr2 As Variant) As Boolean

    Dim i As Integer
    If UBound(arr1) = UBound(arr2) Then
        For i = 0 To UBound(arr1)
            If arr1(i) = arr2(i) Then
                ArrayDifference = True
            Else
                ArrayDifference = False
                Exit Function
            End If
        Next
    Else
        ArrayDifference = False
    End If

End Function

'@Description("changes the contents of the array by removing or replacing existing elements and/or adding new elements in place.")
Public Function Splice( _
        ByVal StartIndex As Long, _
        ParamArray Args() As Variant _
    ) As Variant()
    'Dim LocalItems() As Variant
    Dim ActualStart As Long
    Dim ActualDeleteCount As Long
    Dim ArgsCount As Long
    Dim LocalLength As Long
    Dim LocalArgs() As Variant
    Dim result() As Variant
    Dim i As Long
    Dim TempArray() As Variant
    Dim ItemCount As Long
    Dim TempItems() As Variant
    
    LocalArgs = Args
    'LocalItems = mainArray
    LocalLength = Me.Count
    If StartIndex < LocalLength Then
        ActualStart = StartIndex
    Else
        ActualStart = min(StartIndex, LocalLength)
    End If
    
    ArgsCount = UBound(LocalArgs) + 1
    If ArgsCount = 0 Then
        ' only a start index has been supplied
        ' we're gonna delete everything
        ' 僅提供了起始索引
         '我們要刪除所有內容
        ItemCount = 0
        ActualDeleteCount = LocalLength - ActualStart
    Else
        ' first arg in args is delete count, second onwards are insertion items
        ' args 中的第一個參數是刪除計數，第二個之後是插入項
        ItemCount = ArgsCount - 1
        'deleteCount is first element in args.
        'deleteCount 是 args 中的第一個元素。
        ActualDeleteCount = min(max(Args(LBound(Args)), 0), LocalLength - ActualStart)
    End If
    

    ' get items to be deleted for return val
    ' 取得和刪除
    If ActualDeleteCount > 0 Then
        ReDim result(0 To ActualDeleteCount - 1)
        i = 0
        Do While i < ActualDeleteCount
            If IsObject(Me(ActualStart)) Then
                Set result(i) = Me(ActualStart)
                Me.Remove ActualStart
            Else
                result(i) = Me(ActualStart)
                Me.Remove ActualStart
            End If
            Inc i
        Loop
    Else
        ' return empty array if nothing to be deleted
        ReDim result(0)
    End If
    
    '取得要插入的陣列資料
    If ItemCount > 0 Then
        ReDim TempItems(0 To ItemCount - 1)
        For i = 0 To ItemCount - 1
            If IsObject(LocalArgs(i + 1)) Then
                Set TempItems(i) = LocalArgs(i + 1)
            Else
                TempItems(i) = LocalArgs(i + 1)
            End If
        Next
    Me.AddArrayBefore ActualStart, TempItems
    End If
    
    
    Splice = result
End Function

Attribute VB_Name = "voicNote"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Public typs As String
Public el_type As String
Public abselem As AbsoluteElement
Public beambr As Double
Public chord As iArray  ' Array<ChordProperties>
Public decoration As iArray ' Array<Decorations> ''TODO enumerate these
Public duration As Double
Public endBeam As Boolean
Public endSlur As Double
Public endTriplet As Boolean
'    fonts as {
'        annotationfont as Font,
'        gchordfont as Font,
'        measurefont as Font,
'        repeatfont as Font,
'        tripletfont as Font,
'        vocalfont As font
'    }
Public gracenotes As vgraceNotes
'    {   acciaccatura As Boolean
'        accidental As AccidentalName
'        duration As Double
'        midipitch As Double
'        name As String
'        pitch As Double
'        verticalPos As Double
'        startBeam As Boolean
'        endBeam As Boolean
'        startSlur as {
'            label As Double
'            direction as 'up', 'down'
'            style as 'dotted'
'        }[]
'        endSlur as double[]
'        startTie as {
'            direction as 'up', 'down'
'            style as 'dotted'
'        }
'        endTie As Boolean
'    }[]
    Public lyric As iArray ' Array<{ syllable: string  divider: ' ' | '-' | '_'  }>
    Public nostem As Boolean
    'Public midiPitches As iArray 'midiPitches
    'Public midiGraceNotePitches As iArray 'MidiGracePitches
    Public pitches As iArray
'    positioning as {
'        chordPosition as 'above' | 'below' | 'hidden'
'        dynamicPosition as 'above' | 'below' | 'hidden'
'        ornamentPosition as 'above' | 'below' | 'hidden'
'        vocalPosition as 'above' | 'below' | 'hidden'
'        volumePosition as 'above' | 'below' | 'hidden'
'    }
    Public rest As vrest
    
    Public startBeam As Boolean
    Public startSlur As iArray
'    {
'        label As Integer
'        direction as 'up', 'down'
'        style as 'dotted'
'    }[]
    Public startTriplet
    Public tripletMultiplier As Double
    Public tripletR As Double
    Public stemConnectsToAbove As Boolean
    Public style As Dictionary 'NoteHeadType
    Public startChar As Double
    Public endChar As Double

Attribute VB_Name = "voiceItem"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

'Declare interface ()voiceBase {
Public TS_pos As String

Public typs As Integer
Public v As Integer        ''是第幾聲部
Public soln As Boolean     ''換行 一行結束
Public nl As Boolean       ''換行 新的一行開始
Public row As Integer      ''每聲部的第幾行
Public Col As Integer
Public minspacing As Double
Public extraw As Double
Public w As Double
Public barsperstaff As Variant  ''每行要幾小節
Public dur As Double
Public time As Double
Public fmt As String 'FormationInfo,
Public p_v As String 'PageVoiceTune
Public x As Double
Public y As Double
Public wr As Double
Public wl As Double
Public st As Double
Public a_dd As New iArray 'decorationItem[]
Public a_ly As New iArray 'lyricsItem[]
Public a_gch As New iArray 'gchordItem[]
Public nexs As String 'voiceItem
Public prev As String 'voiceItem
Public ts_prev As String 'voiceItem
Public ts_next As String 'voiceItem
Public err As Boolean



'Declare interface ()voiceBar extends voiceBase {
'Public type As  0 | Double
Public bar_type As String
Public bar_num As Double
Public bar_mrep As Double
Public bar_dotted As Boolean
Public text As String
Public fname As String
Public iStart As Double
Public multi As Double
Public iend As Double
Public invis As Boolean
Public pos As Object
Public seqst As Boolean
Public notes As iArray  'as aNoteItem()
Public nhd As Double
Public Mid As Double
Public ymx As Double
Public ymn As Double
Public shrink As Double
Public space As Double
Public rbstop As Double
Public rbstart As Double
Public xsh As Double
Public norepbra As Boolean

'Declare interface ()voiceClef extends voiceBase {
'   type as  1
Public clef_line As Double
Public clef_type As String
Public clef_auto As Boolean
'Public fname As String
'Public istart As Double
'Public iend As Double
'Public ymx As Double
'Public ymn As Double
'Public seqst As Boolean
'Public shrink As Double
'Public space As Double

'Declare interface ()voiceKey extends voiceBase {
'    type as  5 | Double
'Public istart As Double
'Public iend As Double
Public k_sf As Double
Public k_map As New iArray
Public k_mode As Double
Public k_b40 As Double
'Public seqst As Boolean
Public k_old_sf As Double
Public k_y_clef As Double
'Public ymx As Double
'Public ymn As Double
'Public shrink As Double
'Public space As Double

Public k_bagpipe
Public k_drum
Public k_none As Boolean
Public exp As Boolean
Public k_a_acc As New iArray 'noteItem[]

'Declare interface ()voiceMeter extends voiceBase {
'    type as  6 | Double
Public a_Meter As New iArray '{ top as  String, bot As String }[],
'Public fname As String
'Public istart As Double
'Public iend As Double
Public wmeasure As Double
Public x_meter As New iArray 'Double[]
'Public seqst As Boolean
'Public ymx As Double
'Public ymn As Double
'Public shrink As Double
'Public space As Double
'Public pos As Object
'Public notes As New iArray 'noteItem[]
'Public nhd As Double
'Public mid As Double


'Declare interface ()voiceNote extends voiceBase {
'    type as  8
'Public fname As String
Public stem As Double
'Public multi As Double
'Public nhd As Double
'Public istart As Double        ''這是記錄這物件在文字檔的位置 開始
'Public iend As Double          ''這是記錄這物件在文字檔的位置 結束
'Public notes As New iArray 'noteItem[]
Public dur_orig As Double
'Public pos As Object
Public head As Double
Public dots As Double      ''幾個 負點音符
Public nflags As Double    ''這是拍子 有幾條拍線
Public extra As New iArray 'voiceItem[]  ''裝飾音
Public acc As Double       '' 升降記號
Public beam_end As Boolean
Public beam_st As Boolean
'Public mid As Double
Public xmx As Double
Public ys As Double
'Public ymn As Double
'Public ymx As Double
Public in_tuplet As Boolean
Public tpe As Double
'Public seqst As Boolean
Public stemless As Boolean '' 音符是否無莖的
'Public shrink As Double
'Public space As Double
Public sls
'Public soln As Boolean
Public xs As Double
Public repeat_n As Double
Public repeat_k As Double
Public play As Boolean
'Public invis As Boolean
Public slurStart As iArray
Public slurEnd As iArray


'Declare interface ()voiceRest extends voiceBase {
'    type as  10
'Public fname As String
'Public stem As Double
'Public multi As Double
'Public nhd As Double
'Public xmx As Double
'Public istart As Double
'Public dur_orig As Double
Public fmr As Double
'Public notes As New iArray 'noteItem[]
'Public pos As Object
'Public iend As Double
'Public beam_end As Boolean
'Public head As Double
'Public dots As Double
'Public nflags As Double
'Public stemless As Boolean
'Public beam_st As Boolean
'Public mid As Double
'Public ymx As Double
'Public ymn As Double
'Public invis As Boolean
Public nmes As Double
'Public repeat_n As Double
'Public repeat_k As Double
Public rep_nb As Double
'Public seqst As Boolean
'Public shrink As Double
'Public space As Double
'Public soln As Boolean
Public noplay As Boolean



'declare interface voiceStaves extends voiceBase {
 'public   type as 12 | Double
 'Public fname As String
 'Public st As Double
 Public sY As Object
 '{
 '       voices as {
 '           st as Double
 '           range as Double
 '           sep as Double
 '       }[]
 '       staves as {
 '           stafflines as string
 '           staffscale as Double
 '           staffnonote as Double
 '           maxsep as Double
 '       }[]
 '       top_voice as Double
 '       nstaff as Double
 '   }
 'Public seqst As Boolean
 Public parts As String
 'Public notes As iArray  'noteItem
 'Public nhd As Double
 'Public ymx As Double
 'Public ymn As Double
 'Public shrink As Double
 'Public space As Double


'Declare interface ()voiceTempo extends voiceBase {
'    type as  14 | Double
'Public fname As String
'Public istart As Double
'Public iend As Double
Public tempo_str1 As String
Public tempo_notes As New iArray 'Double[]
Public tempo As Double
'Public notes As New iArray 'noteItem[]
'Public nhd As Double
'Public mid As Double
'Public ymx As Double
'Public ymn As Double
Public tempo_str As String
Public tempo_str2 As String
Public tempo_ca As String
Public new_beat As Double
Public tempo_wh As New iArray  '[Double, Double]
'Public seqst As Boolean
'Public shrink As Double
'Public space As Double
'Public invis As Boolean


'Declare interface ()voiceBlock extends voiceBase {
'    type as  16
Public subtype As String
'Public fname As String
'Public istart As Double
'Public iend As Double
'Public pos As Object
'Public invis As Double
'Public play As Double
Public chn As Double
'Public notes As iArray ' noteItem[]
'Public nhd As Double
'Public mid As Double
'Public ymx As Double
'Public ymn As Double
Public instr As Double

Sub setX(x As Double)
    Me.x = x
'    for (var i = 0  i < this.children.length  i++)
'            this.children[i].setX(x)
End Sub



Public Sub ConvertVarName(key, value)

        Select Case key    ' Evaluate Number.
            Case "type":        Me.typs = value     '這個有改名
            Case "next":        Me.nexs = value     '這個有改名
            
            '' 陣列
            Case "a_dd":        Me.a_dd = value 'a_dd As New iArray 'decorationItem[]
            Case "a_ly":        Me.a_ly = value 'a_ly As New iArray 'lyricsItem[]
            Case "a_gch":       Me.a_gch = value 'a_gch As New iArray 'gchordItem[]
            Case "extra":       Me.extra = value 'extra As New iArray 'voiceItem[]  ''裝飾音
            Case "k_map":       Me.k_map = value 'k_map As New iArray
            Case "a_meter":     Me.a_Meter = value 'a_meter As New iArray '{ top as  String, bot As String }[],
            Case "k_a_acc":     Me.k_a_acc = value 'k_a_acc As New iArray 'noteItem[]
            Case "x_meter":     Me.x_meter = value 'x_meter As New iArray 'Double[]
            Case "tempo_wh":    Me.tempo_wh = value 'tempo_wh As New iArray  '[Double, Double]
            Case "tempo_notes": Me.tempo_notes = value 'tempo_notes As New iArray 'Double[]

            ''物件
            Case "fmt":         Me.fmt = value 'fmt As String 'FormationInfo,
            Case "notes":   Set Me.notes = value 'notes As aNoteItem
            Case "nexs":        Me.nexs = value 'nexs As voiceItem
            Case "pos":     Set Me.pos = value 'pos As Object
            Case "p_v":         Me.p_v = value 'p_v As String 'PageVoiceTune
            Case "prev":        Me.prev = value 'prev As voiceItem
            Case "ts_next":     Me.ts_next = value 'ts_next As voiceItem
            Case "ts_prev":     Me.ts_prev = value 'ts_prev As voiceItem

            
            ''一般
            Case "acc":         Me.acc = value 'acc As Double       '' 升降記號
            Case "bar_dotted":  Me.bar_dotted = value 'bar_dotted As Boolean
            Case "bar_mrep":    Me.bar_mrep = value 'bar_mrep As Double
            Case "bar_num":     Me.bar_num = value 'bar_num As Double
            Case "bar_type":    Me.bar_type = value 'bar_type As String
            Case "beam_end":    Me.beam_end = value 'beam_end As Boolean
            Case "beam_st":     Me.beam_st = value 'beam_st As Boolean
            Case "chn":         Me.chn = value 'chn As Double
            Case "clef_line":   Me.clef_line = value 'clef_line As Double
            Case "clef_type":   Me.clef_type = value 'clef_type As String
            Case "dots":        Me.dots = value 'dots As Double      ''幾個 負點音符
            Case "dur":         Me.dur = value 'dur As Double
            Case "dur_orig":    Me.dur_orig = value 'dur_orig As Double
            Case "err":         Me.err = value 'err As Boolean
            Case "exp":         Me.exp = value 'exp As Boolean
            Case "fmr":         Me.fmr = value 'fmr As Double
            Case "fname":       Me.fname = value 'fname As String
            Case "head":        Me.head = value 'head As Double
            Case "iend":        Me.iend = value 'iend As Double
            Case "in_tuplet":   Me.in_tuplet = value 'in_tuplet As Boolean
            Case "instr":       Me.instr = value 'instr As Double
            Case "invis":       Me.invis = value 'invis As Boolean
            Case "istart":      Me.iStart = value 'istart As Double
            Case "k_b40":       Me.k_b40 = value 'k_b40 As Double
            Case "k_bagpipe":   Me.k_bagpipe = value 'k_bagpipe
            Case "k_drum":      Me.k_drum = value 'k_drum
            Case "k_mode":      Me.k_mode = value 'k_mode As Double
            Case "k_none":      Me.k_none = value 'k_none As Boolean
            Case "k_old_sf":    Me.k_old_sf = value 'k_old_sf As Double
            Case "k_sf":        Me.k_sf = value 'k_sf As Double
            Case "k_y_clef":    Me.k_y_clef = value 'k_y_clef As Double
            Case "mid":         Me.Mid = value 'mid As Double
            Case "multi":       Me.multi = value 'multi As Double
            Case "new_beat":    Me.new_beat = value 'new_beat As Double
            Case "nflags":      Me.nflags = value 'nflags As Double    ''這是拍子 有幾條拍線
            Case "nhd":         Me.nhd = value 'nhd As Double
            Case "nmes":        Me.nmes = value 'nmes As Double
            Case "norepbra":    Me.norepbra = value 'norepbra As Boolean
            Case "play":        Me.play = value 'play As Boolean
            Case "rbstart":     Me.rbstart = value 'rbstart As Double
            Case "rbstop":      Me.rbstop = value 'rbstop As Double
            Case "rep_nb":      Me.rep_nb = value 'rep_nb As Double
            Case "repeat_k":    Me.repeat_k = value 'repeat_k As Double
            Case "repeat_n":    Me.repeat_n = value 'repeat_n As Double
            Case "seqst":       Me.seqst = value 'seqst As Boolean
            Case "shrink":      Me.shrink = value 'shrink As Double
            Case "sls":         Me.sls = value 'sls
            Case "soln":        Me.soln = value 'soln As Boolean
            Case "space":       Me.space = value 'space As Double
            Case "st":          Me.st = value 'st As Double
            Case "stem":        Me.stem = value 'stem As Double
            Case "stemless":    Me.stemless = value 'stemless As Boolean '' 音符是否無莖的
            Case "subtype":     Me.subtype = value 'subtype As String
            Case "tempo":       Me.tempo = value 'tempo As Double
            Case "tempo_ca":    Me.tempo_ca = value 'tempo_ca As String
            Case "tempo_str":   Me.tempo_str = value 'tempo_str As String
            Case "tempo_str1":  Me.tempo_str1 = value 'tempo_str1 As String
            Case "tempo_str2":  Me.tempo_str2 = value 'tempo_str2 As String
            Case "text":        Me.text = value 'text As String
            Case "time":        Me.time = value 'time As Double
            Case "tpe":         Me.tpe = value 'tpe As Double
            Case "v":           Me.v = value 'v As Double
            Case "wl":          Me.wl = value 'wl As Double
            Case "wmeasure":    Me.wmeasure = value 'wmeasure As Double
            Case "wr":          Me.wr = value 'wr As Double
            Case "x":           Me.x = value 'x As Double
            Case "xmx":         Me.xmx = value 'xmx As Double
            Case "xs":          Me.xs = value 'xs As Double
            Case "xsh":         Me.xsh = value 'xsh As Double
            Case "y":           Me.y = value 'y As Double
            Case "ymn":         Me.ymn = value 'ymn As Double
            Case "ymx":         Me.ymx = value 'ymx As Double
            Case "ys":          Me.ys = value 'ys As Double
            Case Else
                Debug.Print "沒有變數 " & key & "名"
        End Select

End Sub

Attribute VB_Name = "voidItemConfig"
Option Explicit

Public staffGroup As StaffGroupElement
Public G As Glode
Public Enum Cg
        BLEN = 1536   '預設全拍 4/4 為 1536 計時單元
        PARTITION_DEF = 384   '一拍 1/4 的計時單元

        '' symbol types
        bar = 0
        clef = 1
        CUSTOS = 2
        SM = 3    '' sequence marker (transient)
        grace = 4 ''這是裝飾音類別
        key = 5
        meter = 6
        MREST = 7
        note = 8
        part = 9
        rest = 10
        space = 11
        staves = 12
        STBRK = 13
        tempo = 14
        Block = 16
        remark = 17
        Config = 18
        Other = 19

        '' note heads
        FULL = 0
        EMPTYe = 1
        OVAL = 2
        OVALBARS = 3
        SQUARE = 4

        '' position types
        SL_ABOVE = &H1       '' position (3 bits)
        SL_BELOW = &H2
        SL_AUTO = &H3
        SL_HIDDEN = &H4
        SL_DOTTED = &H8   '' modifiers
        SL_ALI_MSK = &H70 '' align
        SL_ALIGN = &H10
        SL_CENTER = &H20
        SL_CLOSE = &H40
        
        
    
End Enum

Enum AbcObject
    noteItem
    DecorationItme
    FontItem
    GchordItem
    LyrcsItem
    VoiecItem
    KMapItem
    Number
    Booling
End Enum
Type a_Meter
    top As String * 20
    bot As String * 20
End Type

'Type StaffGroupElement
'    line As Integer
'    startx As Integer
'    w As Integer
'    height As Integer
'    getTextSize As Integer
'    voices As New iArray 'VoiceElement[]
'    staffs As Object
'    brace As Variant
'    bracket As iArray 'BraceElem[]
'End Type
Function getABC_StaffGroupElement() As StaffGroupElement
    
    Dim ts As iArray
    Dim i As Integer
    Dim v As New VoiceElement
    Set staffGroup = New StaffGroupElement
    Set ts = jsABCgetJson.getAbcJson
    
    For i = 0 To ts.Count - 1
        Set v = New VoiceElement
        Set v.children = ts(i)
        staffGroup.voices.Push v
    Next
    
    Set getABC_StaffGroupElement = staffGroup
End Function

 Function calExtraw(s1 As MusicItem) As Double
    '前綴元素的寬度 是負值
    Dim i As Integer
    Dim mus As MusicItem
    Dim c As String
    If s1 Is Nothing Then
        Exit Function
    End If
    
    '找是否有升降記號
    For i = 0 To s1.notes.Count - 1
        c = s1.notes(i).mtone
        If c = "b" Or c = "#" Or c = "o" Then
            s1.extraw = s1.extraw - 0.3 * G.fontsize
            i = s1.notes.Count '離開迴圈
        End If
    Next
    '計算 前墜字
    If Not s1.extraObjs Is Nothing Then
        s1.extraw = s1.extraw - (s1.extraObjs.Count * G.fontsize * amt.extraScale * amt.wNote)
    End If
    
    '計算 後墜字
    
    If Not s1.rightObjs Is Nothing Then
        s1.w = s1.w + (s1.rightObjs.Count * G.fontsize * amt.extraScale * amt.wNote)
    End If


    calExtraw = s1.extraw
 End Function
   
 Function calDuration(s1 As MusicItem, lastDuration As Double) As Double
 
    ' lastDuration  上一拍子長度
    Dim tmp_delaytime As Double
    Dim isDot As Boolean
    isDot = False
    Select Case (s1.notes(0).mnote)
        Case "|"
            tmp_delaytime = 0
        Case "-"
            tmp_delaytime = Cg.BLEN / G.mete2
        Case "."
            tmp_delaytime = lastDuration / 2
        Case " "
    
        Case Else
    
            Dim tempo_hj As String
            Dim tempo_ll As Variant
    
            tempo_hj = " -2=45368aAcCfFgGzZ"
            tempo_ll = Array(1, 2, 2, 4, 4, 5, 3, 6, 8, 10, 10, 12, 12, 15, 15, 16, 16, 32, 32)
    
            Dim ii As Integer
            Dim cn As String
            For ii = 0 To Len(tempo_hj) - 1
                cn = Mid(tempo_hj, ii + 1, 1)
                If cn = s1.notes(0).mtempo Then
                    tmp_delaytime = Cg.PARTITION_DEF / tempo_ll(ii)
                    Exit For
                ElseIf s1.notes(0).mtempo = "" Then
                    tmp_delaytime = Cg.PARTITION_DEF
                    Exit For
                Else
                    tmp_delaytime = 0
                End If
            Next ii
    End Select
    
    For ii = 0 To s1.dots - 1
        tmp_delaytime = tmp_delaytime * 1.5
    Next

    calDuration = tmp_delaytime
End Function

 Function calDuration2(s1 As MusicItem, lastDuration As Double) As MusicItem
 
    ' lastDuration  上一拍子長度
    Dim tmp_delaytime As Double
    Dim isDot As Boolean
    Dim outcrop As Integer
    Dim tempo_hj As String
    Dim tempo_ll As Variant
    Dim tempo_flags As Variant
    
    tempo_hj = " -2=4536789aAbBcCdDeEfFgGzZ"
    'ttaaaaaa= array( , -  2  =  4  5  3  6  7  8   9  a   A   b   B   c   C   d   D  e   E    f   F   g   G   z   Z
    tempo_ll = Array(1, 2, 2, 4, 4, 5, 3, 6, 7, 8, 9, 10, 10, 11, 11, 12, 12, 13, 13, 14, 14, 15, 15, 16, 16, 32, 32)
    tempo_flags = Array(0, 1, 1, 2, 2, 2, 1, 2, 2, 3, 3, 3, 3, 3, 3, 4, 4, 4, 4, 4, 4, 4, 4, 4, 4, 4, 5)
    
    isDot = False
    Select Case (s1.notes(0).mnote)
        Case "|"
            tmp_delaytime = 0
        Case "-"
            tmp_delaytime = Cg.BLEN / G.mete2
        Case "."
            tmp_delaytime = lastDuration / 2
        Case " "
    
        Case Else
    

    
            Dim ii As Integer
            Dim cn As String
            For ii = 0 To Len(tempo_hj) - 1
                cn = Mid(tempo_hj, ii + 1, 1)
                If cn = s1.notes(0).mtempo Then
                    outcrop = ii
                    tmp_delaytime = Cg.PARTITION_DEF / tempo_ll(outcrop)
                    Exit For
                ElseIf s1.notes(0).mtempo = "" Then
                    tmp_delaytime = Cg.PARTITION_DEF
                    Exit For
                Else
                    tmp_delaytime = 0
                End If
            Next ii
    End Select
    '找3連音
'    Select Case (s1.notes(0).mtempo)
'        Case "3", "5", "6", "7", "9", "a", "A", "c", "C", "e", "E"
'            s1.tupletCount = tempo_ll(outcrop)
'        Case Else
'            s1.tupletCount = 0
'    End Select
    
    For ii = 0 To s1.dots - 1
        tmp_delaytime = tmp_delaytime * 1.5
    Next

    s1.duration = tmp_delaytime
    s1.nflags = Int(tempo_flags(outcrop))

    Set calDuration2 = s1
End Function


Public Sub debugVoices(staffGroup As StaffGroupElement)
'debug 資料行
        Dim i As Integer
        Dim t As Integer
        Dim sst As String
        Dim c1 As String
        Dim mus As MusicItem
        
        For i = 0 To staffGroup.voices(0).children.Count - 1
            Set mus = staffGroup.voices(0).children(i)
            
            If mus.typs = Cg.bar Then
                Debug.Print Format(CStr(mus.barNumber), "@@@@") & " _ "
                Exit For
            End If
        Next
        For t = 0 To staffGroup.voices.Count - 1
            sst = ""
            For i = 0 To staffGroup.voices(t).children.Count - 1
                Set mus = staffGroup.voices(t).children(i)
                If mus.typs = Cg.note Then
                    c1 = mus.notes(0).mnote
                ElseIf mus.typs = Cg.meter Then
                    c1 = "[" & mus.mete & "/" & mus.mete2 & "]"
                ElseIf mus.typs = Cg.bar Then
                    c1 = "|"
                Else
                    c1 = "*"
                End If
                sst = sst + c1
            Next
            Debug.Print Format("ch" & CStr(t) & "_" & sst, "@@@@")
        Next
End Sub


' 函數名稱: CharToValue
' 描述: 將單一字元 (1-9, a-z/A-Z) 轉換為數值 (1-35)
' 參數: InputChar (String) - 待轉換的字元
' 返回值: Long - 轉換後的數值 (如果字元不在範圍內，則返回 -1)
Public Function CharToValue(ByVal InputChar As String) As Long

    Dim sChar As String
    Dim iAscii As Integer
    Dim lValue As Long
    
    ' 確保只處理單一字元
    If Len(InputChar) <> 1 Then
        CharToValue = -1 ' 或您可以拋出錯誤
        Exit Function
    End If
    
    ' 將輸入字元統一轉為小寫，方便判斷
    sChar = LCase(InputChar)
    iAscii = Asc(sChar) ' 取得字元的 ASCII 碼
    
    ' --- 處理數字 1 到 9 ---
    ' ASCII 碼 '1' = 49, '9' = 57
    If iAscii >= Asc("1") And iAscii <= Asc("9") Then
        ' 將字元轉換為數字 (例如 "1" 轉為 1)
        lValue = val(sChar)
        
    ' --- 處理字母 a 到 z ---
    ' ASCII 碼 'a' = 97, 'z' = 122
    ElseIf iAscii >= Asc("a") And iAscii <= Asc("z") Then
        ' 轉換邏輯: a=10, b=11, ...
        ' lValue = (目前字母的 ASCII 碼) - (字母 'a' 的 ASCII 碼) + 10
        ' 例如: 'a' -> 97 - 97 + 10 = 10
        '       'b' -> 98 - 97 + 10 = 11
        lValue = iAscii - Asc("a") + 10
        
    ' --- 其他無效字元 ---
    Else
        lValue = -1
    End If
    
    CharToValue = lValue
    
End Function

Attribute VB_Name = "vpitchesNote"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Public acciaccatura As Boolean     ''是否為碎音（acciaccatura） as 這種小字體、加上斜線的音符，意思是很快地彈過去，只占非常短的時間。
Public accidental As String 'AccidentalName //臨時記號（accidental）
Public duration As Double
Public pitch As Integer
Public Name As String
Public midipitch As Double
Public startSlur As vSlurList
'{
'    label As Integer
'    direction as 'up', 'down'
'    style as 'dotted'
'}[]
Public endSlur As iArray 'Array<double>
Public startTie As vSlur
'{
'    direction as 'up', 'down'
'    style as 'dotted'
'}

Public endTie As Boolean
Public dottedSlur As Boolean
Public verticalPos As Double
Public highestVert As Double
Public style As String

Public finge As String      '第一個指法
Public towfinge As String   '第二個指法

Attribute VB_Name = "vpitchesNoteList"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
'MIT License
'
'Copyright (c) 2019-2021 Petr Katerinak
'
'Permission is hereby granted, free of charge, to any person obtaining a copy
'of this software and associated documentation files (the "Software"), to deal
'in the Software without restriction, including without limitation the rights
'to use, copy, modify, merge, publish, distribute, sublicense, and/or sell
'copies of the Software, and to permit persons to whom the Software is
'furnished to do so, subject to the following conditions:
'
'The above copyright notice and this permission notice shall be included in all
'copies or substantial portions of the Software.
'
'THE SOFTWARE IS PROVIDED "AS IS", WITHOUT WARRANTY OF ANY KIND, EXPRESS OR
'IMPLIED, INCLUDING BUT NOT LIMITED TO THE WARRANTIES OF MERCHANTABILITY,
'FITNESS FOR A PARTICULAR PURPOSE AND NONINFRINGEMENT. IN NO EVENT SHALL THE
'AUTHORS OR COPYRIGHT HOLDERS BE LIABLE FOR ANY CLAIM, DAMAGES OR OTHER
'LIABILITY, WHETHER IN AN ACTION OF CONTRACT, TORT OR OTHERWISE, ARISING FROM,
'OUT OF OR IN CONNECTION WITH THE SOFTWARE OR THE USE OR OTHER DEALINGS IN THE
'SOFTWARE.
'
' Version of iArray: 1.0
''修正 元素從 0 開始

Private mainArray As New Collection
Private i As Long ' Counter

' #####################
' #    CONSTRUCTOR    #
' #####################
'Private Sub Class_Initialize()
'  Set mainArray = New Collection
'End Sub

' #####################
' #  Getter / Setter  #
' #####################
'Attribute Element.VB_UserMemId = 0 saved in both procedures

'@DefaultMember
Public Property Get element(ByVal index As Long) As vpitchesNote
Attribute element.VB_UserMemId = 0
    If index + 1 < 1 Or index + 1 > mainArray.Count Then
        Set element = Nothing
        Exit Property
    End If
    If IsObject(mainArray(index + 1)) = True Then
        Set element = mainArray(index + 1)
    Else
        element = mainArray(index + 1)
    End If

 
End Property

'@DefaultMember
Public Property Let element(ByVal index As Long, ByVal val As vpitchesNote)
Attribute element.VB_UserMemId = 0
  If index = 0 And mainArray.Count = 0 Then
    Me.Push val
    Exit Property
  End If
    
  If index + 1 > mainArray.Count Then
    Dim eMsg As String
    eMsg = IIf(mainArray.Count > 0, _
               "Index (" & index + 1 & ") out of iArray bounds (1-" & mainArray.Count & ")", _
               "iArray doesn't have any indexes")
    err.Raise Number:=9, Description:=eMsg
    Exit Property
  End If
  mainArray.Add val, after:=index + 1
  mainArray.Remove index + 1
End Property

' #############################
' # COMMON COLLECTION METHODS #
' #############################
Public Function Count() As Long
  Count = mainArray.Count
End Function
Public Sub Add(ByVal val As vpitchesNote, Optional ByVal bef As Variant = Empty, Optional ByVal aft As Variant = Empty)
  If IsEmpty(bef) And IsEmpty(aft) Then
    mainArray.Add val
  ElseIf IsEmpty(bef) Then
    mainArray.Add val, , , aft
  ElseIf IsEmpty(aft) Then
    mainArray.Add val, , bef
  Else
    mainArray.Add val, , bef, aft
  End If
End Sub
Public Sub Remove(index As Long)
  mainArray.Remove index + 1
End Sub

' ####################
' #  PUBLIC METHODS  #
' ####################

'AddAfter
' Adds element after given index.
' {1,2,3} -> index >= 3 -> Push val
' {1,2,3} -> index < 1 -> Unshift val
' {} -> index = any -> Push val
' @param Long index | Index after which will be added an element
' @param Variant val | One element (String, number, ...) to add into iArray
' @return Long | Count of elements inside iArray
Public Function AddAfter(ByVal index As Long, ByVal val As vpitchesNote) As Long
  If Me.Count < 1 Or index + 1 >= Me.Count Then
    Me.Push val
  ElseIf index + 1 < 1 Then
    Me.Unshift val
  Else
    Me.Add val, aft:=index + 1
  End If
  AddAfter = Me.Count
End Function

'AddArrayAfter
' Adds elements after given index.
' {1,2,3} -> index >= 3 -> PushArray val
' {1,2,3} -> index < 1 -> UnshiftArray val
' {} -> index = any -> PushArray val
' @param Long index | Index after which will be added an element
' @param Variant val | Array() or iArray of elements to add into iArray
' @return Long | Count of elements inside iArray
Public Function AddArrayAfter(ByVal index As Long, ByVal val As Variant) As Long
  If Me.Count < 1 Or index + 1 >= Me.Count Then
    Me.PushArray val
  ElseIf index + 1 < 1 Then
    Me.UnshiftArray val
  Else
    If TypeOf val Is vpitchesNoteList Then
      For i = 0 To val.Count - 1
        Me.Add val(i), aft:=index + 1
        Inc index
      Next i
    Else
      For i = LBound(val) To UBound(val)
        Me.Add val(i), aft:=index + 1
        Inc index
      Next i
    End If
  End If
  AddArrayAfter = Me.Count
End Function

'AddArrayBefore
' Adds elements before given index.
' {1,2,3} -> index > 3 -> PushArray val
' {1,2,3} -> index <= 1 -> UnshiftArray val
' {} -> index = any -> PushArray val
' @param Long index | Index after which will be added an element
' @param Variant val | Array() or iArray of elements to add into iArray
' @return Long | Count of elements inside iArray
Public Function AddArrayBefore(ByVal index As Long, ByVal val As Variant) As Long
  If Me.Count < 1 Or index + 1 > Me.Count Then
    Me.PushArray val
  ElseIf index <= 0 Then
    Me.UnshiftArray val
  Else
    If TypeOf val Is vpitchesNoteList Then
      For i = val.Count - 1 To 0 Step -1
        Me.Add val(i), bef:=index + 1
      Next i
    Else
      For i = UBound(val) To LBound(val) Step -1
        Me.Add val(i), bef:=index + 1
      Next i
    End If
  End If
  AddArrayBefore = Me.Count
End Function

'AddBefore
' Adds element before given index.
' {1,2,3} -> index > 3 -> Push val
' {1,2,3} -> index <= 1 -> Unshift val
' {} -> index = any -> Push val
' @param Long index | Index before which will be added an element
' @param Variant val | One element (String, number, ...) to add into iArray
' @return Long | Count of elements inside iArray
Public Function AddBefore(ByVal index As Long, ByVal val As vpitchesNote) As Long
  If Me.Count < 1 Or index + 1 > Me.Count Then
    Me.Push val
  ElseIf index + 1 <= 1 Then
    Me.Unshift val
  Else
    Me.Add val, bef:=index + 1
  End If
  AddBefore = Me.Count
End Function



'Clear
' Empties iArray
Public Function Clear() As Boolean
  For i = mainArray.Count - 1 To 0 Step -1
    mainArray.Remove i + 1
  Next i
  Clear = IIf(mainArray.Count = 0, True, False)
End Function

'Clone
' Makes a hard copy of the mainArray
' @return mainArray | Return exact copy of itself
Public Function clone() As vpitchesNoteList
  Set clone = New vpitchesNoteList
  For i = 0 To Me.Count - 1
    clone.Push Me(i)
  Next i
End Function

'Contains
' Checks if given value is used inside mainArray.
' @param Variant val | One element (String, number, ...) to by checked if it exists in iArray
' $return Boolean | True = exists, False = doesn't exists
Public Function Contains(ByVal val As vpitchesNote) As Boolean
  Contains = False
  Dim el As Variant
  For Each el In mainArray
    If IsObject(val) = True Or VarType(val) And 8192 Then
        If (VarType(el) And 8192) And (VarType(val) And 8192) Then
            If ArrayDifference(el, val) Then
                Contains = True: Exit Function
            End If
        ElseIf IsObject(el) = True And IsObject(val) = True Then
            If el Is val Then
                Contains = True: Exit Function
            End If
        End If
    Else
        If IsObject(el) = False And (VarType(el) And 8192) <> 8192 Then
            If el = val Then
            Contains = True: Exit Function
            End If
        End If
    End If
  Next el
End Function

'ContainsAll
' Checks if all given values are used inside mainArray.
' @param Variant val | values to by checked if it exists in iArray
' $return Boolean | True = all exists, False = one ore more values doesn't exists
Public Function ContainsAll(ByVal val As vpitchesNoteList) As Boolean
  ContainsAll = False
  Dim foundOccurrences As Integer: foundOccurrences = 0
  Dim values As New vpitchesNoteList
  If Not TypeOf val Is vpitchesNoteList Then
    If IsArray(val) Then
      values.PushArray (val)
    Else
      values.Push (val)
    End If
  Else
    Set values = val
  End If
  For i = 0 To values.Count - 1
    If Me.Contains(values(i)) Then Inc foundOccurrences
  Next i
  If foundOccurrences = values.Count Then ContainsAll = True
End Function


'Dequeue
' Removes an element from the begining of the mainArray.
' @return Variant | Removed element or Empty, if iArray is empty
'刪除開頭一個元素。
Public Function Dequeue() As vpitchesNote
  Dequeue = Empty
  If mainArray.Count > 0 Then
    If VarType(Me(0)) = vbString Then
        Dequeue = Me(0)
    ElseIf TypeOf Me(0) Is vpitchesNoteList Then
        Set Dequeue = Me(0)
    ElseIf VarType(Me(0)) = vbArray Then
        Set Dequeue = Me(0)
    ElseIf VarType(Me(0)) = vbObject Then
        Set Dequeue = Me(0)
    Else
        Dequeue = Me(0)
    End If
    
    mainArray.Remove 1
  End If
End Function

'Difference
' Checks for number of differences between two arrays, what was added/deleted or combination.
' @param iArray oldArray | Old iArray to be compared with current iArray
' @param String retType | �dd= deleted from old iArray, �aa= added in current iArray, �cc= combination of both (default)
' @return iArray | iArray with differences found
Public Function Difference(ByRef oldArray As vpitchesNoteList, Optional ByVal retType As String = "c") As vpitchesNoteList
  Set Difference = New vpitchesNoteList
  Select Case LCase(retType)
    Case "d"
      For i = 0 To oldArray.Count - 1
        If Me.Contains(oldArray(i)) = False Then Difference.Push oldArray(i)
      Next i
    Case "a"
      For i = 0 To Count - 1
        If oldArray.Contains(Me(i)) = False Then Difference.Push Me(i)
      Next i
    Case "c"
      For i = 0 To oldArray.Count - 1
        If Me.Contains(oldArray(i)) = False Then Difference.Push oldArray(i)
      Next i
      For i = 0 To Count - 1
        If oldArray.Contains(Me(i)) = False Then Difference.Push Me(i)
      Next i
    Case Else
      err.Raise Number:=5, Description:="Unknown Difference return type attribute:" & vbCrLf & _
                                        "Allowed are 'A'dded/'D'eleted/'C'ombination of both"
  End Select
End Function


'First
' Returns value of the first element of the mainArray.
' @return Variant | Value of the first element or Empty if iArray is Empty
Public Function First() As vpitchesNote
  Set First = IIf(Me.Count > 0, Me(0), Empty)
End Function

'Head
' Returns all elements of iArray, except last one.
' @return iArray | Copy of original array, without last element
Public Function head() As vpitchesNoteList
  Set head = Me.clone
  head.Pop
End Function

'Intersect
' Search for element that exists in both iArrays.
' @param iArray intArray | iArray to be intersected with current iArray
' @return iArray | Intersected values
Public Function Intersect(ByRef intersectedArr As vpitchesNoteList) As vpitchesNoteList
  Set Intersect = New vpitchesNoteList
  Dim el As Variant
  For Each el In mainArray
    If intersectedArr.Contains(el) Then
      If Not Intersect.Contains(el) Then Intersect.Push (el)
    End If
  Next el
End Function

'ContainsOnlyNumeric
' Verify that all elements are numbers or convertable to numbers
' $return Boolean | True = contains only numeric values, False = contains inconvertible values
Public Function ContainsOnlyNumeric() As Boolean
  ContainsOnlyNumeric = True
  Dim el As Variant
  For Each el In mainArray
    If Not IsNumeric(el) Then ContainsOnlyNumeric = False: Exit Function
  Next el
End Function

'Join
' Joins two iArrays.
' @param iArray jArray | iArray to be joined with current iArray
' @return iArray | Joined iArray
Public Function Join(ByRef joinArr As vpitchesNoteList) As vpitchesNoteList
  Set Join = New vpitchesNoteList
  Join.PushArray Me
  Join.PushArray joinArr
End Function

'Last
' Returns value of the last element of the mainArray.
' @return Variant | Value of the last element or Empty if iArray is Empty
Public Function Last() As vpitchesNote
  Set Last = IIf(Me.Count > 0, Me(Me.Count - 1), Empty)
End Function


'Pop
' Removes an element from the end of the mainArray.
' @return Variant | Removed element or Empty, if iArray is empty
Public Function Pop() As vpitchesNote
  If mainArray.Count > 0 Then
    If VarType(Me(mainArray.Count - 1)) = vbObject Then
       Set Pop = Me(mainArray.Count - 1)
    Else
        Pop = Me(mainArray.Count - 1)
    End If
    mainArray.Remove mainArray.Count
  End If
End Function
  
  

'Push
' Adds an element at the end of the mainArray.
' @param Variant val | One element (String, number, ...) to add into iArray
' @return Long | Count of elements inside iArray
Public Function Push(ByVal val As vpitchesNote) As Long
  mainArray.Add val
  Push = mainArray.Count
End Function

'PushArray
' Adds elements at the end of the mainArray.
' @param Variant val | Array() or iArray of elements to add into iArray
' @return Long | Count of elements inside array
Public Function PushArray(ByVal val As Variant) As Long
  If TypeOf val Is vpitchesNoteList Then
    For i = 0 To val.Count - 1
      Me.Push val(i)
    Next i
  Else
    For i = LBound(val) To UBound(val)
      Me.Push val(i)
    Next i
  End If
  PushArray = Me.Count
End Function


'Reverse
' Reverses the content of the iArray
' @return iArray | Reversed iArray
Public Function Reverse() As vpitchesNoteList
  Set Reverse = New vpitchesNoteList
  For i = 0 To Me.Count - 1
    Reverse.Unshift Me(i)
  Next i
End Function

'Shift
' Removes an element from the begining of the mainArray.
' @return Variant | Removed element or Empty, if iArray is empty
'轉移
' 從 iArray 的開頭刪除一個元素。
' @返回第一個元素 | 如果 iArray 為空，則刪除元素或為空
Public Function shift() As vpitchesNote
  shift = Empty
  If mainArray.Count > 0 Then
    If VarType(Me(0)) = vbString Then
        shift = Me(0)
    ElseIf TypeOf Me(0) Is vpitchesNoteList Then
        Set shift = Me(0)
    ElseIf VarType(Me(0)) = vbArray Then
        Set shift = Me(0)
    ElseIf VarType(Me(0)) = vbObject Then
        Set shift = Me(0)
    Else
        shift = Me(0)
    End If
    
    mainArray.Remove 1
  End If
End Function

'Shuffle
' Randomly mixes content of the iArray
' @return iArray | Shuffled iArray
' 隨機播放
' 隨機混合 iArray 的內容
'@return iArray | 打亂iArray
Public Function Shuffle() As vpitchesNoteList
  Set Shuffle = New vpitchesNoteList
  Dim keys As New vpitchesNoteList
  For i = 0 To Me.Count - 1
    keys.Push (i)
  Next i
  Dim rndNo As Long
  Do While keys.Count > 0
    rndNo = randomFromTo(0, keys.Count - 1)
    Shuffle.Push Me(keys(rndNo))
    keys.Remove (rndNo)
  Loop
End Function



'Tail
' Returns all elements of iArray, except first one.
' @return iArray | Copy of original array, without first element
'返回陣列中除了第一個元素的剩余元素陣列
Public Function Tail() As vpitchesNoteList
  Set Tail = Me.clone
  Tail.Dequeue
End Function

Public Function ToList()
  If Me.Count = 0 Then ToList = Null: Exit Function
  Dim tarr()
  ReDim tarr(Me.Count - 1)
  For i = 0 To Me.Count - 1
    If VarType(Me(i)) = vbString Then
        tarr(i) = Me(i)
    ElseIf TypeOf Me(i) Is vpitchesNoteList Then
        Set tarr(i) = Me(i)
    ElseIf VarType(Me(i)) = vbObject Then
        Set tarr(i) = Me(i)
    Else
        tarr(i) = Me(i)
    End If
  Next i
  ToList = tarr
End Function

'ToString
' Creates string representation of the mainArray.
' @param String delimiter | Optional character to separate the iArray's elements (default = " ")
' @return String | Formated representation of tha iArray
Public Function ToString(Optional ByVal delimiter As String = " ") As String
  If Me.Count = 0 Then ToString = "{}": Exit Function
  ToString = vbNullString
  For i = 0 To Me.Count - 1
    If i = 0 Then ToString = ToString + "{"
    If i > 0 Then ToString = ToString + delimiter
    If VarType(Me(i)) = vbString Then
        ToString = ToString + Chr$(34)
        ToString = ToString + CStr(Me(i))
        ToString = ToString + Chr$(34)
    ElseIf TypeOf Me(i) Is vpitchesNoteList Then
        ToString = ToString + Me(i).ToString(delimiter)
    ElseIf (VarType(Me(i)) And vbArray) = vbArray Then
        ToString = ToString + "[Array]"
    ElseIf VarType(Me(i)) = vbObject Then
        ToString = ToString + "[Object]"
    Else
        ToString = ToString + CStr(Me(i))
    End If
    
    If i = mainArray.Count - 1 Then ToString = ToString + "}"
  Next i
End Function

'Union
' Combines both iArrays and removes duplicities
' @param iArray uArray | iArray to be unioned with current iArray
' @return iArray | Combined values without duplicities
Public Function Union(ByRef uArr As vpitchesNoteList) As vpitchesNoteList
  Set Union = Me.clone
  Union.PushArray uArr
  Union.RemoveDuplicates
End Function

'Unique
' Returns copy of iArray without duplicated values. Original array is not affected
' @return iArray | iArray with unique values
Public Function Unique() As vpitchesNoteList
  Set Unique = New vpitchesNoteList
  Dim el As Variant
  For Each el In mainArray
    If Not Unique.Contains(el) Then Unique.Push (el)
  Next el
End Function

'Unshift
' Add an element at the begining of the mainArray.
' @param Variant val | One element (String, number, ...) to add into iArray
' @return Long | Count of elements inside iArray
Public Function Unshift(ByVal val As Variant) As Long
  If mainArray.Count = 0 Then
    Unshift = Push(val)
  Else
    mainArray.Add val, before:=1
    Unshift = mainArray.Count
  End If
End Function




' #####################
' # PRIVATE FUNCTIONS #
' #####################
Sub Inc(ByRef i)
   i = i + 1
End Sub



'比對 兩個陣列是否一樣
Private Function ArrayDifference(arr1 As Variant, arr2 As Variant) As Boolean

    Dim i As Integer
    If UBound(arr1) = UBound(arr2) Then
        For i = 0 To UBound(arr1)
            If arr1(i) = arr2(i) Then
                ArrayDifference = True
            Else
                ArrayDifference = False
                Exit Function
            End If
        Next
    Else
        ArrayDifference = False
    End If

End Function

'@Description("changes the contents of the array by removing or replacing existing elements and/or adding new elements in place.")
Public Function Splice( _
        ByVal StartIndex As Long, _
        ParamArray Args() As Variant _
    ) As Variant()
    'Dim LocalItems() As Variant
    Dim ActualStart As Long
    Dim ActualDeleteCount As Long
    Dim ArgsCount As Long
    Dim LocalLength As Long
    Dim LocalArgs() As Variant
    Dim result() As Variant
    Dim i As Long
    Dim TempArray() As Variant
    Dim ItemCount As Long
    Dim TempItems() As Variant
    
    LocalArgs = Args
    'LocalItems = mainArray
    LocalLength = Me.Count
    If StartIndex < LocalLength Then
        ActualStart = StartIndex
    Else
        ActualStart = min(StartIndex, LocalLength)
    End If
    
    ArgsCount = UBound(LocalArgs) + 1
    If ArgsCount = 0 Then
        ' only a start index has been supplied
        ' we're gonna delete everything
        ' 僅提供了起始索引
         '我們要刪除所有內容
        ItemCount = 0
        ActualDeleteCount = LocalLength - ActualStart
    Else
        ' first arg in args is delete count, second onwards are insertion items
        ' args 中的第一個參數是刪除計數，第二個之後是插入項
        ItemCount = ArgsCount - 1
        'deleteCount is first element in args.
        'deleteCount 是 args 中的第一個元素。
        ActualDeleteCount = min(max(Args(LBound(Args)), 0), LocalLength - ActualStart)
    End If
    

    ' get items to be deleted for return val
    ' 取得和刪除
    If ActualDeleteCount > 0 Then
        ReDim result(0 To ActualDeleteCount - 1)
        i = 0
        Do While i < ActualDeleteCount
            If IsObject(Me(ActualStart)) Then
                Set result(i) = Me(ActualStart)
                Me.Remove ActualStart
            Else
                result(i) = Me(ActualStart)
                Me.Remove ActualStart
            End If
            Inc i
        Loop
    Else
        ' return empty array if nothing to be deleted
        ReDim result(0)
    End If
    
    '取得要插入的陣列資料
    If ItemCount > 0 Then
        ReDim TempItems(0 To ItemCount - 1)
        For i = 0 To ItemCount - 1
            If IsObject(LocalArgs(i + 1)) Then
                Set TempItems(i) = LocalArgs(i + 1)
            Else
                TempItems(i) = LocalArgs(i + 1)
            End If
        Next
    Me.AddArrayBefore ActualStart, TempItems
    End If
    
    
    Splice = result
End Function

Attribute VB_Name = "vrestNote"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public typs As String  'invisible' | 'spacer' | 'rest' | 'multimeasure' | 'invisible-multimeasure' | 'whole'
Public text As Double
Public startTie As vSlur
Public endTie As Boolean

Attribute VB_Name = "vtempoProperties"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public typs As String
Public duration As iArray 'Array<double>
Public bpm As Double
Public preString As String
Public postString As String
Public startChar As Integer
Public endChar As Integer
Public suppress As Boolean
Public suppressBpm As Boolean

Private Sub Class_Initialize()
    Set Me.duration = New iArray
End Sub


Public Function ToVoiceABC() As VoiceABC
        Set ToVoiceABC = New VoiceABC
        
   
        ToVoiceABC.typs = Me.typs
        Set ToVoiceABC.duration = Me.duration
        ToVoiceABC.bpm = Me.bpm
        ToVoiceABC.preString = Me.preString
        ToVoiceABC.postString = Me.postString
        ToVoiceABC.startChar = Me.startChar
        ToVoiceABC.endChar = Me.endChar
        ToVoiceABC.suppress = Me.suppress
        ToVoiceABC.suppressBpm = Me.suppressBpm
        
End Function

Attribute VB_Name = "減字譜用"
Option Explicit


Public Sub select_qin()
On Error Resume Next
Dim k As Integer
For k = 0 To 500
    Dim ent As Object

    'Dim tmp_ent() As Variant
    
   
    Dim SSetColl As AcadSelectionSets
    Set SSetColl = ThisDrawing.SelectionSets
    
    ' Create a SelectionSet named "TEST" in the current drawing
    Dim ssetObj As AcadSelectionSet
    
  
    If SSetColl.Count > 0 Then
        SSetColl.item(0).Delete
    End If
    
    Set ssetObj = SSetColl.Add("TEST")
    

    ssetObj.SelectOnScreen
    If ssetObj.Count = 0 Then
    
       Exit Sub
    End If
    '找出圖面中的每一個選集
    ReDim tmp_ent(ssetObj.Count - 1)
    Dim lll As AcadLine
    
    
    Dim minExt As Variant
    Dim maxExt As Variant
    Dim minPT(2) As Double
    Dim maxPT(2) As Double
    Dim midPT(2) As Double
    Dim toPT(2) As Double
    Dim aa1 As AcadText
    Dim i As Integer
    Dim pos_y As Double
    i = 0
    For Each ent In ssetObj
        '取得最大最小
        ent.GetBoundingBox minExt, maxExt
        If i = 0 Then
            minPT(0) = minExt(0): minPT(1) = minExt(1)
            maxPT(0) = maxExt(0): maxPT(1) = maxExt(1)
        Else
            If minPT(0) > minExt(0) Then
                minPT(0) = minExt(0)
            End If
            If minPT(1) > minExt(1) Then
                minPT(1) = minExt(1)
            End If
            
        End If
        i = i + 1
    Next
    
    '移動
    toPT(0) = 60000 * k: toPT(1) = 20000:
    For Each ent In ssetObj
        '取得最大最小
        
        ent.Move minPT, toPT
    Next
    
Next
End Sub
