Attribute VB_Name = "AttribCode"
Option Explicit
Function ACAD_Ver() As Integer
'傳回AutoCAD 的版本號碼
    ' This example returns AutoCAD version as a string
    
    Dim VERSION As String
    VERSION = ThisDrawing.Application.VERSION
    ACAD_Ver = Val(VERSION)
    
End Function
Function GetAttribTextString(entAttrib As AcadEntity, title As String) As String
'找 屬性(titile)的文字
    Dim Array1 As Variant
    Dim Pnt As Variant
    'Dim entObj As AcadEntity
    Dim count As Integer
        With entAttrib
            '當一個塊引用表行被找到後，檢查它是否有屬性
            If StrComp(.EntityName, "AcDbBlockReference", 1) = 0 Then
                '如果有屬性
                If .HasAttributes = True Then
                    '提取塊引用中的屬性
                    Array1 = .GetAttributes
                    '這一輪迴圈用來查找標題，如果有填在第1行
                    For count = LBound(Array1) To UBound(Array1)
                        '如果還沒有標題
                        If Array1(count).TagString = title Then
                            GetAttribTextString = Array1(count).textString
                            Exit Function
                        End If
                    Next count
                    'MsgBox """" & title & """屬性未找到"
                End If
            End If
        End With
End Function

Function SetAttribTextString(entAttrib As AcadEntity, title As String, sVal As String) As String
'設定 屬性(titile)的文字
    Dim Array1 As Variant
    Dim Pnt As Variant
    'Dim entObj As AcadEntity
    Dim count As Integer
        With entAttrib
            '當一個塊引用表行被找到後，檢查它是否有屬性
            If StrComp(.EntityName, "AcDbBlockReference", 1) = 0 Then
                '如果有屬性
                If .HasAttributes = True Then
                    '提取塊引用中的屬性
                    Array1 = .GetAttributes
                    '這一輪迴圈用來查找標題，如果有填在第1行
                    For count = LBound(Array1) To UBound(Array1)
                        '如果還沒有標題
                        If Array1(count).TagString = title Then
                            Array1(count).textString = sVal
                            Exit Function
                        End If
                    Next count
                    'MsgBox """" & title & """屬性未找到"
                    SetAttribTextString = ""
                End If
            Else
                'MsgBox "這不是屬性圖元"
                SetAttribTextString = ""
            End If
        End With
End Function

Function SetTowAttrib(entAttrib As AcadEntity, towAttrib As AcadEntity) As String
'設定 屬性(titile)的文字
    Dim Array1 As Variant
    Dim Pnt As Variant
    Dim title As String
    Dim sVal As String
    'Dim entObj As AcadEntity
    Dim count As Integer
        With entAttrib
            '當一個塊引用表行被找到後，檢查它是否有屬性
            If StrComp(.EntityName, "AcDbBlockReference", 1) = 0 Then
                '如果有屬性
                If .HasAttributes = True Then
                    '提取塊引用中的屬性
                    Array1 = .GetAttributes
                    '這一輪迴圈用來查找標題，如果有填在第1行
                    For count = LBound(Array1) To UBound(Array1)
                       
                        title = Array1(count).TagString
                        sVal = Array1(count).textString
                        
                        Call SetAttribTextString(towAttrib, title, sVal)
                        
                    Next count
                    
                    
                End If
            Else
                'MsgBox "這不是屬性圖元"
            End If
        End With
End Function

Function GetAttribList(entAttrib As AcadEntity) As String
'取得 屬性列表
    Dim Array1 As Variant
    Dim Pnt As Variant
    Dim strList As String
    Dim count As Integer
    strList = ""
        With entAttrib
            '當一個塊引用表行被找到後，檢查它是否有屬性
            If StrComp(.EntityName, "AcDbBlockReference", 1) = 0 Then
                '如果有屬性
                If .HasAttributes = True Then
                    '提取塊引用中的屬性
                    Array1 = .GetAttributes
                    '這一輪迴圈用來查找標題，如果有填在第1行
                    For count = LBound(Array1) To UBound(Array1)
                        strList = strList & Array1(count).TagString & vbCrLf
                    Next count
                    GetAttribList = strList
                    Exit Function
                End If
            End If
        End With
End Function

Attribute VB_Name = "CommonFileDialog"


'CommonFileDialog 模組內容
'Description:
'
'The FileDialog class allows you to use the common dialogs "Open" and "Save" from VBA. Properties for the class include
'Multiselect, title, filter, initial directory, and hide read only.
'Also included is simple methods for finding the window to make the parent of the dialog (the one that it will center on).
'Snippet Code: - Common File Dialog Class

Option Explicit
#If VBA7 Then
'//The Win32 API Functions///
Private Declare PtrSafe Function GetSaveFileName Lib "comdlg32.dll" Alias "GetSaveFileNameA" (pOpenfilename As OPENFILENAME) As Long
Private Declare PtrSafe Function GetOpenFileName Lib "comdlg32.dll" Alias "GetOpenFileNameA" (pOpenfilename As OPENFILENAME) As Long
Private Declare PtrSafe Function FindWindow Lib "user32" Alias "FindWindowA" (ByVal lpClassName As String, ByVal lpWindowName As String) As Long
#Else
Private Declare Function GetSaveFileName Lib "comdlg32.dll" Alias "GetSaveFileNameA" (pOpenfilename As OPENFILENAME) As Long
Private Declare Function GetOpenFileName Lib "comdlg32.dll" Alias "GetOpenFileNameA" (pOpenfilename As OPENFILENAME) As Long
Private Declare Function FindWindow Lib "user32" Alias "FindWindowA" (ByVal lpClassName As String, ByVal lpWindowName As String) As Long
#End If


'//A few of the available Flags///
Private Const OFN_FILEMUSTEXIST = &H1000
Private Const OFN_ALLOWMULTISELECT = &H200
Public Const OFN_PATHMUSTEXIST = &H800
Public Const OFN_HIDEREADONLY = &H4 '隱蔽只讀複選框



'This one keeps your dialog from turning into
'A browse by folder dialog if multiselect is true!
'Not sure what I mean? Remove it from the flags
'In the "Show Open" & "Show Save" methods.
Private Const OFN_EXPLORER As Long = &H80000
'//The Structure
Private Type OPENFILENAME
    lStructSize As Long
    hwndOwner As Long '擁有對話框的窗口
    hInstance As Long
    lpstrFilter As String '裝載文件過濾器的緩衝區
    lpstrCustomFilter As String
    nMaxCustFilter As Long
    nFilterIndex As Long
    lpstrFile As String
    nMaxFile As Long
    lpstrFileTitle As String
    nMaxFileTitle As Long
    lpstrInitialDir As String
    lpstrTitle As String    '對話框的標題
    flags As Long
    nFileOffset As Integer
    nFileExtension As Integer
    lpstrDefExt As String
    lCustData As Long
    lpfnHook As Long
    lpTemplateName As String
End Type
Private lngHwnd As Long
Private strFilter As String
Private strTitle As String
Private strDir As String
Private blnHideReadOnly As Boolean
Private blnAllowMulti As Boolean
Private blnMustExist As Boolean
Private Sub Class_Initialize()
    'Set default values when
    'class is first created
    strDir = CurDir
    strTitle = "Llamas Rule"
    strFilter = "All Files" _
    & Chr$(0) & "*.*" & Chr$(0)
    lngHwnd = FindWindow(vbNullString, Application.Caption)
    'None of the flags are set here!
End Sub
Public Function FindUserForm(objForm As UserForm) As Long
    Dim lngTemp As Long
    Dim strCaption As String
    strCaption = objForm.Caption
    lngTemp = FindWindow(vbNullString, strCaption)
    If lngTemp <> 0 Then
        FindUserForm = lngTemp
    End If
End Function
Public Property Let OwnerHwnd(WindowHandle As Long)
    '//FOR YOU TODO//
    'Use the API to validate this handle
    lngHwnd = WindowHandle
    'This value is set at startup to the handle of the
    'AutoCAD Application window, if you want the owner
    'to be a user form you will need to obtain its
    'Handle by using the "FindUserForm" function in
    'This class.
End Property
Public Property Get OwnerHwnd() As Long
    OwnerHwnd = lngHwnd
End Property
Public Property Let title(Caption As String)
    'don't allow null strings
    If Not Caption = vbNullString Then
        strTitle = Caption
    End If
End Property
Public Property Get title() As String
    title = strTitle
End Property
Public Property Let Filter(ByVal FilterString As String)
    'Filters change the type of files that are
    'displayed in the dialog. I have designed this
    'validation to use the same filter format the
    'Common dialog OCX uses:
    '"All Files (*.*)|*.*"
    Dim intPos As Integer
    Do While InStr(FilterString, "|") > 0
    intPos = InStr(FilterString, "|")
    If intPos > 0 Then
        FilterString = Left$(FilterString, intPos - 1) _
        & Chr$(0) & Right$(FilterString, _
        Len(FilterString) - intPos)
    End If
    Loop
    If Right$(FilterString, 2) <> Chr$(0) & Chr$(0) Then
        FilterString = FilterString & Chr$(0)
    End If
    strFilter = FilterString
End Property
Public Property Get Filter() As String
    'Here we reverse the process and return
    'the Filter in the same format the it was
    'entered
    Dim intPos As Integer
    Dim strTemp As String
    strTemp = strFilter
    Do While InStr(strTemp, Chr$(0)) > 0
    intPos = InStr(strTemp, Chr$(0))
    If intPos > 0 Then
        strTemp = Left$(strTemp, intPos - 1) _
        & "|" & Right$(strTemp, _
        Len(strTemp) - intPos)
    End If
    Loop
    If Right$(strTemp, 1) = "|" Then
        strTemp = Left$(strTemp, Len(strTemp) - 1)
    End If
    Filter = strTemp
End Property
Public Property Let InitialDir(strFolder As String)
    'Sets the directory the dialog displays when called
    If Len(Dir(strFolder)) > 0 Then
        strDir = strFolder
        Else
        Err.Raise 514, "FileDialog", "Invalid Initial Directory"
    End If
End Property
Public Property Let HideReadOnly(blnVal As Boolean)
    blnHideReadOnly = blnVal
End Property
Public Property Let MultiSelect(blnVal As Boolean)
    'allow users to select more than one file using
    'The Shift or CTRL keys during selection
    blnAllowMulti = blnVal
End Property
Public Property Let FileMustExist(blnVal As Boolean)
    blnMustExist = blnVal
End Property
'@~~~~~~~~~~~~~~~~~~~~~~~~~~~~~~~~~~~~~~~~~~~~~~~~@
' Display and use the File open dialog
'@~~~~~~~~~~~~~~~~~~~~~~~~~~~~~~~~~~~~~~~~~~~~~~~~@
Public Function ShowOpen() As String
    Dim strTemp As String
    Dim udtStruct As OPENFILENAME
    udtStruct.lStructSize = Len(udtStruct)
    'Use our private variable
    udtStruct.hwndOwner = lngHwnd
    'Use our private variable
    udtStruct.lpstrFilter = strFilter
    udtStruct.lpstrFile = space$(254)
    udtStruct.nMaxFile = 255
    udtStruct.lpstrFileTitle = space$(254)
    udtStruct.nMaxFileTitle = 255
    'Use our private variable
    udtStruct.lpstrInitialDir = strDir
    'Use our private variable
    udtStruct.lpstrTitle = strTitle
    'Ok, here we test our booleans to
    'set the flag
    If blnHideReadOnly And blnAllowMulti And blnMustExist Then
        udtStruct.flags = OFN_HIDEREADONLY Or _
        OFN_ALLOWMULTISELECT Or OFN_EXPLORER Or OFN_FILEMUSTEXIST
        ElseIf blnHideReadOnly And blnAllowMulti Then
        udtStruct.flags = OFN_ALLOWMULTISELECT _
        Or OFN_EXPLORER Or OFN_HIDEREADONLY
        ElseIf blnHideReadOnly And blnMustExist Then
        udtStruct.flags = OFN_HIDEREADONLY Or OFN_FILEMUSTEXIST
        ElseIf blnAllowMulti And blnMustExist Then
        udtStruct.flags = OFN_ALLOWMULTISELECT Or _
        OFN_EXPLORER Or OFN_FILEMUSTEXIST
        ElseIf blnHideReadOnly Then
        udtStruct.flags = OFN_HIDEREADONLY
        ElseIf blnAllowMulti Then
        udtStruct.flags = OFN_ALLOWMULTISELECT _
        Or OFN_EXPLORER
        ElseIf blnMustExist Then
        udtStruct.flags = OFN_FILEMUSTEXIST
    End If
    If GetOpenFileName(udtStruct) Then
        strTemp = (Trim(udtStruct.lpstrFile))
        ShowOpen = Mid(strTemp, 1, Len(strTemp) - 1)
    End If
End Function
'@~~~~~~~~~~~~~~~~~~~~~~~~~~~~~~~~~~~~~~~~~~~~~~~~@
' Display and use the File Save dialog
'@~~~~~~~~~~~~~~~~~~~~~~~~~~~~~~~~~~~~~~~~~~~~~~~~@
Public Function ShowSave() As String
    Dim strTemp As String
    Dim udtStruct As OPENFILENAME
    udtStruct.lStructSize = Len(udtStruct)
    'Use our private variable
    udtStruct.hwndOwner = lngHwnd
    'Use our private variable
    udtStruct.lpstrFilter = strFilter
    udtStruct.lpstrFile = space$(254)
    udtStruct.nMaxFile = 255
    udtStruct.lpstrFileTitle = space$(254)
    udtStruct.nMaxFileTitle = 255
    'Use our private variable
    udtStruct.lpstrInitialDir = strDir
    'Use our private variable
    udtStruct.lpstrTitle = strTitle
    If blnMustExist Then
        udtStruct.flags = OFN_FILEMUSTEXIST
    End If
    If GetSaveFileName(udtStruct) Then
        strTemp = (Trim(udtStruct.lpstrFile))
        ShowSave = Mid(strTemp, 1, Len(strTemp) - 1)
    End If
End Function


Function GetFile(strTitle As String, strFilter As String, Optional strIniDir As String) As String
 
    On Error Resume Next
    Dim lntFile As Integer
    Dim FileName As String
    Dim OFileBox As OPENFILENAME
    With OFileBox
        .lpstrTitle = strTitle '對話框標題
        .lpstrInitialDir = strIniDir '初始目錄
        .lStructSize = Len(OFileBox)
        .hwndOwner = ThisDrawing.hWnd
        .flags = OFN_PATHMUSTEXIST Or OFN_FILEMUSTEXIST Or OFN_HIDEREADONLY
        .lpstrFile = String$(255, 0)
        .nMaxFile = 255
        .lpstrFileTitle = String$(255, 0)
        .nMaxFileTitle = 255
        .lpstrFilter = strFilter  '過濾器
        .nFilterIndex = 1
    End With
     
    lntFile = GetOpenFileName(OFileBox) '執行打開對話框
    If lntFile <> 0 Then
        FileName = Left(OFileBox.lpstrFile, InStr(OFileBox.lpstrFile, vbNullChar) - 1)
        GetFile = FileName
    Else
        GetFile = ""
    End If
 
End Function
Function SaveFile(strTitle As String, strFilter As String, Optional strIniDir As String) As String
 
    On Error Resume Next
    Dim lntFile As Integer
    Dim FileName As String
    Dim OFileBox As OPENFILENAME
    With OFileBox
        .lpstrTitle = strTitle '對話框標題
        .lpstrInitialDir = strIniDir '初始目錄
        .lStructSize = Len(OFileBox)
        .hwndOwner = ThisDrawing.hWnd
        .flags = OFN_PATHMUSTEXIST Or OFN_FILEMUSTEXIST Or OFN_HIDEREADONLY
        .lpstrFile = String$(255, 0)
        .nMaxFile = 255
        .lpstrFileTitle = String$(255, 0)
        .nMaxFileTitle = 255
        .lpstrFilter = strFilter  '過濾器
        .nFilterIndex = 1
    End With
     
    lntFile = GetSaveFileName(OFileBox) '執行打開對話框
    If lntFile <> 0 Then
        FileName = Left(OFileBox.lpstrFile, InStr(OFileBox.lpstrFile, vbNullChar) - 1)
        SaveFile = FileName
    Else
        SaveFile = ""
    End If
 
End Function

Attribute VB_Name = "DISC"
Attribute VB_Base = "0{179D66FD-852E-49C4-ACAE-8D750FD73DAC}{7DDB9100-27F9-4232-86B9-16DD1E51FD16}"
Attribute VB_GlobalNameSpace = False
Attribute VB_Creatable = False
Attribute VB_PredeclaredId = True
Attribute VB_Exposed = False
Attribute VB_TemplateDerived = False
Attribute VB_Customizable = False
Private Sub cbLoad_Click()
  
    Dim TrackingDictionary As AcadDictionary, TrackingXRecord As AcadXRecord
    Dim XRecordDataType As Variant, XRecordData As Variant
    Dim ArraySize As Long, iCount As Long
    Dim DataType As Integer, data As String, msg As String
    
        ' Unique identifiers to distinguish our XRecordData from other XRecordData
    Const TYPE_STRING = 1
    Const TAG_DICTIONARY_NAME = "ObjectTrackerDictionary"
    Const TAG_XRECORD_NAME = "ObjectTrackerXRecord"

    ' Connect to the dictionary we store the XRecord in
    On Error GoTo CREATE
    Set TrackingDictionary = ThisDrawing.Dictionaries(TAG_DICTIONARY_NAME)
    Set TrackingXRecord = TrackingDictionary.GetObject(TAG_XRECORD_NAME)
    On Error GoTo 0
    
 
    ' Read back all XRecordData entries
    TrackingXRecord.GetXRecordData XRecordDataType, XRecordData
    ArraySize = UBound(XRecordDataType)
    
    ' Retrieve and display stored XRecordData
    For iCount = 0 To ArraySize
        ' Get information for this element
        DataType = XRecordDataType(iCount)
        data = XRecordData(iCount)
        
        If DataType = TYPE_STRING Then
            msg = msg & data & vbCrLf
        End If
    Next
    Me.TextBox1 = msg
    ''MsgBox "The data in the XRecord is: " & vbCrLf & vbCrLf & msg, vbInformation
    
    Exit Sub

CREATE:
    ' Create the entities that hold our XRecordData
    If TrackingDictionary Is Nothing Then  ' Make sure we have our tracking object
        Set TrackingDictionary = ThisDrawing.Dictionaries.add(TAG_DICTIONARY_NAME)
        Set TrackingXRecord = TrackingDictionary.AddXRecord(TAG_XRECORD_NAME)
    End If
    
    Resume
End Sub

Private Sub CommandButton1_Click()

    ' This example creates a new XRecord if one doesn't exist,
    ' appends data to the XRecord and reads it back.  To see data being added
    ' run the example more than once.
    
    Dim TrackingDictionary As AcadDictionary, TrackingXRecord As AcadXRecord
    Dim XRecordDataType As Variant, XRecordData As Variant
    Dim ArraySize As Long, iCount As Long
    Dim DataType As Integer, data As String, msg As String
    
    ' Unique identifiers to distinguish our XRecordData from other XRecordData
    Const TYPE_STRING = 1
    Const TAG_DICTIONARY_NAME = "ObjectTrackerDictionary"
    Const TAG_XRECORD_NAME = "ObjectTrackerXRecord"

    ' Connect to the dictionary we store the XRecord in
    On Error GoTo CREATE
    Set TrackingDictionary = ThisDrawing.Dictionaries(TAG_DICTIONARY_NAME)
    Set TrackingXRecord = TrackingDictionary.GetObject(TAG_XRECORD_NAME)
    On Error GoTo 0
    
    ' Get current XRecordData
    TrackingXRecord.GetXRecordData XRecordDataType, XRecordData
    
    ' If we don't have an array already then create one
    If VarType(XRecordDataType) And vbArray = vbArray Then
        ArraySize = UBound(XRecordDataType) + 1       ' Get the size of the data elements returned
        ArraySize = ArraySize + 1                        ' Increase to hold new data
    
        ReDim Preserve XRecordDataType(0 To ArraySize)
        ReDim Preserve XRecordData(0 To ArraySize)
    Else
        ArraySize = 0
        ReDim XRecordDataType(0 To ArraySize) As Integer
        ReDim XRecordData(0 To ArraySize) As Variant
    End If
    
    ' Append new XRecord Data
    '
    ' For this sample we only append the current time to the XRecord
    XRecordDataType(ArraySize) = TYPE_STRING: XRecordData(ArraySize) = CStr(Now)
    TrackingXRecord.SetXRecordData XRecordDataType, XRecordData
    
    ' Read back all XRecordData entries
    TrackingXRecord.GetXRecordData XRecordDataType, XRecordData
    ArraySize = UBound(XRecordDataType)
    
    ' Retrieve and display stored XRecordData
    For iCount = 0 To ArraySize
        ' Get information for this element
        DataType = XRecordDataType(iCount)
        data = XRecordData(iCount)
        
        If DataType = TYPE_STRING Then
            msg = msg & data & vbCrLf
        End If
    Next
    
    MsgBox "The data in the XRecord is: " & vbCrLf & vbCrLf & msg, vbInformation
    
    Exit Sub

CREATE:
    ' Create the entities that hold our XRecordData
    If TrackingDictionary Is Nothing Then  ' Make sure we have our tracking object
        Set TrackingDictionary = ThisDrawing.Dictionaries.add(TAG_DICTIONARY_NAME)
        Set TrackingXRecord = TrackingDictionary.AddXRecord(TAG_XRECORD_NAME)
    End If
    
    Resume
End Sub

Private Sub CommandButton2_Click()
    
    Dim TrackingDictionary As AcadDictionary, TrackingXRecord As AcadXRecord
    Dim XRecordDataType As Variant, XRecordData As Variant
    Dim ArraySize As Long, iCount As Long
    Dim DataType As Integer, data As String, msg As String
    
    ' Unique identifiers to distinguish our XRecordData from other XRecordData
    Const TYPE_STRING = 1
    Const TAG_DICTIONARY_NAME = "ObjectTrackerDictionary"
    Const TAG_XRECORD_NAME = "ObjectTrackerXRecord"

    ' Connect to the dictionary we store the XRecord in
    On Error GoTo CREATE
    Set TrackingDictionary = ThisDrawing.Dictionaries(TAG_DICTIONARY_NAME)
    Set TrackingXRecord = TrackingDictionary.GetObject(TAG_XRECORD_NAME)
End Sub
Option Explicit

'使用擴展字典
'AutoCAD有兩種字典
'第一種：擴展字典——一種與具體的對象關聯的字典，每個對象僅能擁有一個擴展字典，
'                    其中可以保存與該對象有關的信息。
'第二種：命名對象字典(Named Object Dictionary)——用來保存與實體無關的數據，
'                    AutoCAD本身就使用對象命名字典來保存一些信息，例如組字典（保存編組的信息）
'                    多線樣式字典等。

'A 使用擴展字典的一般步驟：
'  保存信息的基本步驟：
'  1、使用GetExtensionDictionary方法創建一個對象的擴展字典；
'  2、使用AddXData方法向擴展字典添加一條擴展記錄；
'  3、使用SetXRecordData將數據保存在擴展記錄中。
'  讀取擴展字典的基本步驟：
'  1、使用GetExtensionDictionary獲取對象的擴展字典；
'  2、使用GetObject方法獲得指定的擴展記錄；
'  3、使用GetXRecordData讀取保存在擴展記錄中的數據。

'B 使用命名對象字典的一般步驟：
'  保存命名字典信息的基本步驟
'  1、使用Dictionaries.add添加一個命名對象字典；
'  2、同A
'  3、同A
'  讀取命名對象字典的基本步驟：
'  1、使用對象的基本操作獲得Dictionaries集合中制定的字典；
'  2、同A
'  3、同A

Public Function HasXRecord(ByVal ent As AcadEntity, ByVal key As String) As Boolean
  '判斷對象是否已經擁有擴展字典
  Dim objDict As AcadDictionary
  Dim objXRecord As AcadXRecord
 
  If ent.HasExtensionDictionary Then
    '獲得擴展字典
    Set objDict = ent.GetExtensionDictionary
   
    On Error Resume Next
    Set objXRecord = objDict.GetObject(key)
    Set objDict = Nothing
   
    If Err Then
      Err.clear
      HasXRecord = False
    Else
      HasXRecord = True
    End If
  Else
    HasXRecord = False
  End If
   
End Function

Public Sub CreateXRecord(ByRef xDataType As Variant, ByRef xData As Variant, ParamArray Filter())
  '創建擴展記錄的數據集
  Debug.Assert (UBound(Filter) Mod 2 = 1)
 
  Dim count As Integer
  count = (UBound(Filter) + 1) / 2
  Dim DataType() As Integer, data() As Variant
  ReDim DataType(count - 1)
  ReDim data(count - 1)
 
  Dim i As Integer
  For i = 0 To count - 1
    DataType(i) = Filter(2 * i)
    data(i) = Filter(2 * i + 1)
  Next i
    xDataType = DataType
    xData = data
End Sub

Public Sub AddXRecord(ByVal ent As AcadEntity, ByVal key As String, ByVal xDataType As Variant, ByVal xData As Variant)
  '向指定的實體添加擴展字典
  Dim objDict As AcadDictionary
  Dim objXRecord As AcadXRecord
 
  Set objDict = ent.GetExtensionDictionary()
  Set objXRecord = objDict.AddXRecord(key)
  objXRecord.SetXRecordData xDataType, xData
End Sub
  
Public Sub GetXRecord(ByVal ent As AcadEntity, ByVal key As String, ByRef xDataType As Variant, ByRef xData As Variant)
  '獲取擴展字典
  Dim objDict As AcadDictionary
  Dim objXRecord As AcadXRecord
 
  Set objDict = ent.GetExtensionDictionary
  Set objXRecord = objDict.GetObject(key)
  objXRecord.GetXRecordData xDataType, xData
End Sub

Public Function HasNamedDictionary(ByVal dictName As String, ByVal key As String) As Boolean
  '判斷是否已經存在鍵位dictName的字典
  On Error Resume Next
 
  Dim objDict As AcadDictionary
  Dim objXRecord As AcadXRecord
 
  Set objDict = ThisDrawing.Dictionaries(dictName)
  If Err Then
    Err.clear
    HasNamedDictionary = False
  Else
    Set objXRecord = objDict.GetObject(key)
    If Err Then
      Err.clear
      HasNamedDictionary = False
    Else
      HasNamedDictionary = True
    End If
  End If
End Function

Public Sub AddNamedDictionary(ByVal dictName As String, ByVal key As String, ByVal xDataType As Variant, ByVal xData As Variant)
  '用於向當前圖形添加指定的命名對象字典
  Dim objDict As AcadDictionary
  Dim objXRecord As AcadXRecord
 
  Set objDict = ThisDrawing.Dictionaries.add(dictName)
  Set objXRecord = objDict.AddXRecord(key)
  objXRecord.SetXRecordData xDataType, xData
End Sub

Public Sub GetNamedDictionary(ByVal dictName As String, ByVal key As String, ByRef xDataType As Variant, ByRef xData As Variant)
  '從當前圖形中獲得指定的命名對象字典
  Dim objDict As AcadDictionary
  Dim objXRecord As AcadXRecord
 
  Set objDict = ThisDrawing.Dictionaries(dictName)
  Set objXRecord = objDict.GetObject(key)
  objXRecord.GetXRecordData xDataType, xData
End Sub

 

調用類:

Option Explicit

Public Sub AddEntXRecord()
  Dim ent As AcadEntity
  Dim PickPoint As Variant
 
  ThisDrawing.Utility.GetEntity ent, PickPoint, vbCr & "請選擇對象："
 
  Dim point(0 To 2) As Double
  SetPoint3d point, 100, 100, 0
 
  Dim xRecord As New clsXRecord
  Dim DataType As Variant, data As Variant
 
  xRecord.GetXRecord ent, "EX02", DataType, data
 
  Dim s As String
  s = data(1)
 
  xRecord.CreateXRecord DataType, data, _
      1, "道路", _
      8, ent.Layer, _
      40, PickPoint(0), _
      10, point
 
  If xRecord.HasXRecord(ent, "EX02") Then
    ThisDrawing.Utility.prompt vbNewLine & "實體已經包含指定名稱的擴展記錄 "
  Else
    xRecord.AddXRecord ent, "EX02", DataType, data
    ThisDrawing.Utility.prompt vbNewLine & "成功為實體添加擴展記錄 "
  End If
 
 
 
End Sub


Public Sub SetPoint3d(ByVal pt As Variant, ByRef x As Double, ByRef Y As Double, ByRef z As Double)
  ReDim pt(0 To 2) As Double
  pt(0) = x
  pt(1) = Y
  pt(2) = z
 
End Sub

Private Sub CommandButton3_Click()
    '把 textbox1 內的多文字，轉換成多個 AcadText
    Dim returnPnt As Variant
    
    Me.Hide
    returnPnt = ThisDrawing.Utility.GetPoint(, "選擇插入點： ")
    
    
    Dim textObj As AcadMText
    Dim textString As String
    Dim insertionPoint(0 To 2) As Double
    Dim height As Double
    Dim i As Integer
    
    For i = 1 To Len(Me.TextBox1.text)
        
        textString = MidB(Me.TextBox1.text, i, 1)
        insertionPoint(0) = returnPnt(0) + i * 10
        insertionPoint(1) = returnPnt(1)
        insertionPoint(2) = 0
        height = 3
    
        ' Create the text object in model space
        Set textObj = ThisDrawing.ModelSpace.AddMText(insertionPoint, 3, textString)
    Next
 
End Sub

Private Sub CommandButton4_Click()
    Dim returnObj As AcadObject
    Dim basePnt As Variant
    Dim arrStr As Variant
    On Error Resume Next
    
    ' The following example waits for a selection from the user
    Me.Hide
    ThisDrawing.Utility.GetEntity returnObj, basePnt, "Select an object"
    arrStr = Split(returnObj.textString, "\P")
    
    Dim textObj As AcadMText
    Dim textString As String
    Dim insertionPoint(0 To 2) As Double
    Dim height As Double
    Dim i As Integer
    
    For i = 0 To UBound(arrStr)
        
        textString = arrStr(i)
        insertionPoint(0) = basePnt(0) + 30
        insertionPoint(1) = basePnt(1) - (i * 5)
        insertionPoint(2) = 0
        height = 3
    
        ' Create the text object in model space
        Set textObj = ThisDrawing.ModelSpace.AddMText(insertionPoint, 5, textString)
        textObj.height = 5
    Next
    
End Sub

Private Sub UserForm_Click()

End Sub

Private Sub UserForm_Deactivate()

End Sub

Private Sub UserForm_ QueryClose(Cancel As Integer, CloseMode As Integer)

End Sub

Attribute VB_Name = "DataBuffer"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

'2013.03.17  V3 正要修改 二胡的版本，因程式之前是用古箏的指法圖，現在改成二胡的指法圖

Const mChar As String = "*||||||"    ' 資料格式 '資料的前面字元有那些
Const TRACK_MAX As Integer = 5      '最大的音軌數

Dim mCharI() As Integer
Dim mMete As Integer        '每小節有幾拍
Dim mFontSize As Integer
Dim mTextNote() As String       '把每行資料放進來 這是有陣列的
Dim mmsa(0 To 1) As String
Dim mOpenATable_ As Boolean

Private Type t
    ln As Integer   '要記錄讀進來的資料是在文件裡的第幾 "行"
    wd As Integer   '要記錄貢進來的資料是在文件要的第幾 "字"
End Type

Private Type KeyFormat
    mfingering As String  '指法
    mnote As String           '高低音
    mscale As String          '音階
    mtempo As String         '拍子
    delay As Integer            '拍子的延遲長度
    mtow_fingering As String  '指法 第二個
    mslur As String           '連音符
    and As Boolean              '記錄合音 true為跟後面一音合音 ,false為沒有
    what As Integer             '記錄一些不一樣的指法
    
    textdata As String
    
'    mfPosition As Double    '這是看這字上下移多少
'    mnPosition As Double    '這是看這字上下移多少
'    msPosition As Double     '這是看這字上下移多少
'    mtPosition As Double    '這是看這字上下移多少
'    mtow_fPosition As Double   '這是看 指法 第二個 這字上下移多少
'    mslPosition As Double    '連音符 字上下移多少
    
    ln As Integer   '要記錄讀進來的資料是在文件裡的第幾 "行"
    wd As Integer   '要記錄貢進來的資料是在文件要的第幾 "字"
End Type


Dim mMusic() As KeyFormat                '了解嗎
Dim mSize() As Long '現在的 mMusic() as KeyFormat 的物件數量
Dim mLogSize() As Long '現在的 mMusic() 的空白陣列 的數量
Dim AUTHOR As String    '作者
Dim title As String     '標題


Property Get getTITLE() As String
    getTITLE = title
End Property




Private Sub Class_Initialize()
    ReDim mMusic(TRACK_MAX)
    ReDim mMusic(TRACK_MAX, 100)
    ReDim mSize(TRACK_MAX)
    ReDim mLogSize(TRACK_MAX)
    Dim i As Integer
    For i = 0 To TRACK_MAX
        mSize(i) = 0
        mLogSize(i) = UBound(mMusic, 2)
    Next
    
    ReDim mTextNote(amt.mHowData)
    ReDim mCharI(amt.mHowData)
End Sub
Sub clear()
    Class_Initialize
End Sub
Sub GetDataToBuf__()
    Dim i As Integer
    Dim j As Integer
'
'    Dim tab_m As Integer
'    Dim size_i As Integer

     
    'tab_m = 1
    'numPClen = 1
    
    'Dim Buf_md(0 To L_BUF_MD) As MyClassT
    Dim c As String
    Dim cc As String
    Dim mcc As String
    'Dim bufcc(0 To L_BUF_MD) As MyBufT
    
    Call ttm.setLineChar(mChar, fMete)
    Dim valText As Variant
    Dim numPC As Integer
    
    If textSss = "" Then
        MsgBox ("沒有資料")
        Exit Sub
    End If
    
    valText = Split(textSss, vbCrLf)
    
    numPC = UBound(valText)
    
   
    For i = 0 To numPC
        'Set buf_Range = ActiveDocument.Paragraphs(i).Range
        c = Mid(valText(i), 1, 1)
        mcc = valText(i)
        'mcc = Mid(valText(i), 1, Len(valText(i)) )   ' 這是把最後一個字(vbCrLf)拿掉
        If c = ">" Then
            Exit For
        End If
        ttm.setSaveString (mcc)
        
    Next i
        ttm.ShowData
        
        Selection.EndOf Unit:=wdStory, Extend:=wdMove   '用 Selection.EndOf 移到文件的尾端
    
        Call ttm.setFontSize(fSize, fOpenATable)
        ttm.TextToMusic         '資料整理中
        
        Dim cNote As String
        Dim cScale As String
        Dim cFingering As String
        Dim cTowFingering As String
        Dim cTempo As String
        Dim cSlur As String
        
        
        Dim cposScale As Double
        Dim cposFing As Double
        Dim cposTowFing As Double
        Dim cposSlur As Double
        
        Dim drawTab As New DrawTable
        
        
        Dim tmp As String
        Dim pos As Integer
        
        Call drawTab.StartSet(fMany, fMete, fBar, 10, fOpenATable) '設定表格
        
        Selection.font.size = fSize
        Selection.font.name = UserFontName
        pos = 1
        
        '第 0 個位置是看有多少物件
        For i = 1 To ttm.getMTEXT(iNote, 0)
        
            cNote = ttm.getMTEXT(iNote, i)
            cScale = ttm.getMTEXT(iScale, i)
            cFingering = ttm.getMTEXT(iFinge, i)
            cTowFingering = ttm.getMTEXT(iTowFinge, i)
            cTempo = ttm.getMTEXT(iTempo, i)
            cSlur = ttm.getMTEXT(iSlur, i)
            
            cposScale = ttm.getMTEXTPosition(iScale, i)
            cposFing = ttm.getMTEXTPosition(iFinge, i)
            cposTowFing = ttm.getMTEXTPosition(iTowFinge, i)
            cposSlur = ttm.getMTEXTPosition(iSlur, i)
            
            If cNote = "|" Then
                Call drawTab.MoveNext(1, pos, False)
                pos = pos + 1
            ElseIf cNote = "!" Then
                If fOpenATable Then
                    Call drawTab.MoveNext(1, pos, True)
                End If
            ElseIf cNote <> cScale And cNote <> cTempo And cNote <> cFingering Then
                
                Selection.Fields.add Range:=Selection.Range, Type:=wdFieldEmpty, _
                PreserveFormatting:=False                                   'Ctrl+F9
                
                Selection.MoveLeft Unit:=wdCharacter, count:=1
                Selection.Delete Unit:=wdCharacter, count:=2

                Selection.TypeText text:="eq \o(" & cNote & "," & cTempo
                
                If cScale <> "" Then  '高低音
                    Selection.TypeText text:=","
                    Selection.font.position = cposScale '這是下移的指令
                    Selection.TypeText text:=cScale
                    Selection.font.position = 0   '這是下移的指令
                End If
                
                If Not (cFingering = "" Or cFingering = " ") Then    '第一行指法
                    Selection.TypeText text:=","
                    Selection.font.position = cposFing '這是下移的指令
                    Selection.TypeText text:=cFingering
                    Selection.font.position = 0 '這是下移的指令
                
                End If
                
                If Not (cTowFingering = "" Or cTowFingering = " ") Then    '第二行指法
                    Selection.TypeText text:=","
                    Selection.font.position = cposTowFing '這是下移的指令
                    Selection.TypeText text:=cTowFingering
                    Selection.font.position = 0 '這是下移的指令
                End If
                
                If Not (cSlur = "" Or cSlur = " ") Then    '連音符行
                    Selection.TypeText text:=","
                    Selection.font.position = cposSlur '這是下移的指令
                    Selection.TypeText text:=cSlur
                    Selection.font.position = 0 '這是下移的指令
                End If
                
                
                Selection.TypeText text:=")"
                'Selection.Fields.ToggleShowCodes 'Shift+F9
                'Selection.MoveRight Unit:=wdCharacter, Count:=1
                Selection.EndKey Unit:=wdLine
            End If
            
            ''這是看是否要加入空白  或  半拍的符號
            If cTempo = ChrW(&H5D39) Then
                '現在的音符 拍號 是半拍
                '看下一個音符的主音是否為 "!", "|" 小節符號
                If ttm.getMTEXT(iNote, i + 1) = "!" Or ttm.getMTEXT(iNote, i + 1) = "|" Then
                Else
                    '如不是加入一個 半拍 字
                    Selection.TypeText text:=ChrW(&H5D39)
                End If
                
            ElseIf cTempo = "" Or cTempo = " " Then
                '現在的音符 拍號 是一拍
                '看現在及下一個音符的主音是否為 "!", "|" 小節符號
                
                If ttm.getMTEXT(iNote, i + 1) = "!" Or ttm.getMTEXT(iNote, i + 1) = "|" _
                    Or ttm.getMTEXT(iNote, i) = "!" Or ttm.getMTEXT(iNote, i) = "|" Then
                
                Else
                    '如不是加入2個 空白 字
                    Selection.TypeText text:="  "
                End If
            End If
            
            
            
        Next i
        
End Sub

Private Sub SetMusicItem(ntrack As Integer, ln As Integer, wd As Integer)
'nTrack as integer '要轉換到第幾個音軌資料
'ln As Integer   '要記錄讀進來的資料是在文件裡的第幾 "行"
'wd As Integer   '要記錄貢進來的資料是在文件要的第幾 "字"
    Dim c() As String
    ReDim c(amt.mHowData)
    Dim i As Integer
    Dim j As Integer
    Dim lsup As Integer
    Dim ilo As Integer
    
    '看陣列夠不夠
    If mSize(ntrack) + Len(mTextNote(amt.iNote)) > UBound(mMusic, 2) Then
        ReDim Preserve mMusic(TRACK_MAX, UBound(mMusic, 2) * 2)
    End If
    
    '迴圈每個字
    Dim tmp_data As String
    Dim a As String
    
    Dim objMusic As KeyFormat
    
    Dim c_TONE As String
    Dim c_Note As String
    Dim c_Finge As String
    Dim c_TowFinge As String
    Dim c_Tempo As String
    Dim c_Scale As String
    Dim c_Slur As String
    
  
    
    
    For i = 1 To Len(mTextNote(amt.iNote))
        tmp_data = ""
        For j = amt.iTONE To Len(mChar)
            c(j) = Mid(mTextNote(j), i, 1)
            a = c(j)
            If a = "" Then
                a = " "
            End If
            tmp_data = tmp_data & a
        Next j
        
        
'        c_TONE = c(AMT.iTONE)      ' * 行
'        c_Note = c(AMT.iNote)      '這為主行       1234567.|l
'        c_Finge = c(AMT.iFinge)    '這是指法行     _+)(*&
'        c_TowFinge = c(AMT.iTowFinge) '這是指法行第二行  _+)(*&
'        c_Tempo = c(AMT.iTempo)    '這是拍子       -=368acefz
'        c_Scale = c(AMT.iScale)    '這是高低音行   .,:;
'        c_Slur = c(AMT.iSlur)      '二胡連音線，(古箏是合音)
'
        
        ilo = mSize(ntrack)
        Select Case c(amt.iNote)     '這是音階
            Case "0", "1", "2", "3", "4", "5", "6", "7"
                c_Note = c(amt.iNote)
            Case "."
                c_Note = c(amt.iNote)
            Case "-"
                c_Note = c(amt.iNote)
            Case "|"
                If i = 1 Then
'lin'                    mSize(ntrack) = mSize(ntrack) - 1
                    GoTo nogood
                End If
                c_Note = c(amt.iNote)
            Case " ", ""
'lin'                mSize(ntrack) = mSize(ntrack) - 1
                GoTo nogood
            Case Else
                c_Note = c(amt.iNote)
        End Select
        
        
        Select Case c(amt.iFinge)     '這是指法
            Case " "
            Case "("
            Case "|"
            
            Case "a" To "z", "A" To "Z", "-", "="
            Case Chr(21) To Chr(125)
                c_Finge = c(amt.iFinge)
            Case Else
                c_Finge = c(amt.iFinge)
        End Select
            
        Select Case c(amt.iTowFinge)     '這是指法2 第二行
            Case "a" To "z", "A" To "Z", "-", "="
                c_TowFinge = c(amt.iTowFinge)
            Case "1" To "7"
                c_TowFinge = c(amt.iTowFinge)
            Case " ", "(", "|"
                c_TowFinge = c(amt.iTowFinge)
            Case Else
                c_TowFinge = c(amt.iTowFinge)
        End Select
        

        lsup = 0
        Select Case c(amt.iTempo)     '這是拍子
            Case " "
                c_Tempo = c(amt.iTempo)
            Case "-", "2"
                lsup = 1
                c_Tempo = c(amt.iTempo)
            Case "=", "4", "3"
                lsup = 2
                c_Tempo = c(amt.iTempo)
            Case "6", "8", "A"
                lsup = 3
                c_Tempo = c(amt.iTempo)
            Case "|"
                c_Tempo = c(amt.iTempo)
            Case Else
                c_Tempo = c(amt.iTempo)
        End Select
        
        
        c_Scale = c(amt.iScale)
        c_Slur = c(amt.iSlur)
        
        
        
        'objMusic.mTONE = c_TONE     ' * 行
        objMusic.mnote = c_Note      '這為主行       1234567.|l
        objMusic.mfingering = c_Finge    '這是指法行     _+)(*&
        objMusic.mtow_fingering = c_TowFinge  '這是指法行第二行  _+)(*&
        objMusic.mtempo = c_Tempo   '這是拍子       -=368acefz
        objMusic.mscale = c_Scale   '這是高低音行   .,:;
        objMusic.mslur = c_Slur      '二胡連音線，(古箏是合音)
        
        
        objMusic.textdata = tmp_data
        objMusic.ln = ln  '寫入第幾行
        objMusic.wd = i   '寫入第幾字
        
        
        
         mMusic(ntrack, ilo) = objMusic
        
        
        mSize(ntrack) = mSize(ntrack) + 1

    
        
nogood:
    Next i
End Sub
 Public Sub GetDataToBuf(the_data As String)
' 從檔案中讀取一列字串放到特定位置,讀到'*'離開
    Dim ntrack As Integer
    Dim tmp_ntrack As Integer
    Dim buf_i(1000) As String
    Dim i As Integer, tab_m As Integer, vol As Integer
    Dim name(256) As String
    Dim P As String
    Dim c As String
    
    
    Dim cc As String
    Dim mcc As String
    '一行一行的分開，放入 tmp_str
    Dim valText As Variant
    Dim numPC As Integer
    If the_data = "" Then
        MsgBox ("沒有資料")
        Exit Sub
    End If
    
    valText = Split(the_data, vbCrLf)
    ntrack = -1
    tmp_ntrack = -1
    numPC = UBound(valText)
    Dim pos As Integer
    Dim ko As Integer
    Dim findSt As Integer
    Dim findEnd As Integer
    
    For i = 0 To numPC
        c = Mid(valText(i), 1, 1)
        mcc = valText(i)
        
        If c = "<" Then
            If ntrack >= 0 Then
                Call SetMusicItem(ntrack, i, 1) '轉換成物件資料
                For ko = 0 To amt.mHowData
                    mTextNote(ko) = ""
                Next
            End If
            If ntrack = -1 Then
                findSt = InStr(1, mcc, "<")
                findEnd = InStr(1, mcc, ">")
                title = Mid(mcc, findSt + 1, findEnd - findSt - 1)
            End If
            ntrack = ntrack + 1
        ElseIf c = "*" Then
            Call SetMusicItem(ntrack, i, 1) '轉換成物件資料
            
            For ko = 0 To amt.mHowData
                mTextNote(ko) = ""
            Next
            
            pos = amt.iTONE
            mTextNote(pos) = mcc
        ElseIf c = "|" Then
            pos = pos + 1
            mTextNote(pos) = mcc
        End If
    Next
    
    Call SetMusicItem(ntrack, i, 1) '轉換成物件資料
    
    
    
    
End Sub
Function GetTrackSize() As Integer
'取得有多少軌
    Dim i As Integer
    For i = 0 To TRACK_MAX
        If mSize(i) < 3 Then
            GetTrackSize = i
            Exit Function
        End If
    Next
    GetTrackSize = TRACK_MAX

End Function

Function GetTrackBufferSize(the_track As Integer) As Long
'取得每軌有多少音符
    GetTrackBufferSize = mSize(the_track)
End Function
Function GetData(the_track As Integer, the_item As Long) As String
    'the_track 第幾部
    'the_item 第幾個
    Dim tmp_s As String
    Dim i As Integer
    If (mSize(the_track) > 1 And mSize(the_track) > the_item) Then
        GetData = mMusic(the_track, the_item).textdata
    End If
End Function

Attribute VB_Name = "Module1"
Option Explicit

#If VBA7 Then
Public Declare PtrSafe Function GetActiveWindow Lib "user32" () As Long '獲得活動視窗的句柄
Declare PtrSafe Function getPT Lib "CaiqsVBApinvoke.arx" Alias "getpt" (ByRef x As Double, ByRef Y As Double, ByRef z As Double) As Integer

'在Windows系統中加入一種字形資源。
Public Declare PtrSafe Function AddFontResource Lib "gdi32" Alias "AddFontResourceA" (ByVal lpFileName As String) As Long
Public Declare PtrSafe Function SendMessage Lib "user32" Alias "SendMessageA" (ByVal hWnd As Long, ByVal wMsg As Long, ByVal wParam As Long, lParam As Any) As Long
Public Const HWND_BROADCAST = &HFFFF&
Public Const WM_FONTCHANGE = &H1D

#Else

Public Declare Function GetActiveWindow Lib "user32" () As Long '獲得活動視窗的句柄
Declare  Function getPT Lib "CaiqsVBApinvoke.arx" Alias "getpt" (ByRef x As Double, ByRef Y As Double, ByRef z As Double) As Integer

'在Windows系統中加入一種字形資源。
Public Declare  Function AddFontResource Lib "gdi32" Alias "AddFontResourceA" (ByVal lpFileName As String) As Long
Public Declare  Function SendMessage Lib "user32" Alias "SendMessageA" (ByVal hWnd As Long, ByVal wMsg As Long, ByVal wParam As Long, lParam As Any) As Long
Public Const HWND_BROADCAST = &HFFFF&
Public Const WM_FONTCHANGE = &H1D

#End If

Attribute VB_Name = "ModuleTextStyle"
Option Explicit

'字體枚舉類型
Public Const LF_FACESIZE = 32

Public Type LOGFONT
        lfHeight As Long
        lfWidth As Long
        lfEscapement As Long
        lfOrientation As Long
        lfWeight As Long
        lfItalic As Byte
        lfUnderline As Byte
        lfStrikeOut As Byte
        lfCharSet As Byte
        lfOutPrecision As Byte
        lfClipPrecision As Byte
        lfQuality As Byte
        lfPitchAndFamily As Byte
        lfFaceName(LF_FACESIZE) As Byte
End Type

Public Type NEWTEXTMETRIC
        tmHeight As Long
        tmAscent As Long
        tmDescent As Long
        tmInternalLeading As Long
        tmExternalLeading As Long
        tmAveCharWidth As Long
        tmMaxCharWidth As Long
        tmWeight As Long
        tmOverhang As Long
        tmDigitizedAspectX As Long
        tmDigitizedAspectY As Long
        tmFirstChar As Byte
        tmLastChar As Byte
        tmDefaultChar As Byte
        tmBreakChar As Byte
        tmItalic As Byte
        tmUnderlined As Byte
        tmStruckOut As Byte
        tmPitchAndFamily As Byte
        tmCharSet As Byte
        ntmFlags As Long
        ntmSizeEM As Long
        ntmCellHeight As Long
        ntmAveWidth As Long
End Type

#If VBA7 Then
Public Declare PtrSafe Function EnumFontFamilies Lib "gdi32" Alias "EnumFontFamiliesA" (ByVal hDC As Long, ByVal lpszFamily As String, ByVal lpEnumFontFamProc As Long, lParam As Any) As Long
Public Declare PtrSafe Function GetDC Lib "user32" (ByVal hWnd As Long) As Long
Public Declare PtrSafe Function ReleaseDC Lib "user32" (ByVal hWnd As Long, ByVal hDC As Long) As Long
    
'複製以下代碼到一模塊中
Public Declare PtrSafe Function GetWindowsDirectory Lib "kernel32" Alias "GetWindowsDirectoryA" (ByVal lpBuffer As String, ByVal nSize As Long) As Long
Public Declare PtrSafe Function GetSystemDirectory Lib "kernel32" Alias "GetSystemDirectoryA" (ByVal lpBuffer As String, ByVal nSize As Long) As Long

#Else

Public Declare Function EnumFontFamilies Lib "gdi32" Alias "EnumFontFamiliesA" (ByVal hDC As Long, ByVal lpszFamily As String, ByVal lpEnumFontFamProc As Long, lParam As Any) As Long
Public Declare Function GetDC Lib "user32" (ByVal hWnd As Long) As Long
Public Declare Function ReleaseDC Lib "user32" (ByVal hWnd As Long, ByVal hDC As Long) As Long
    
'複製以下代碼到一模塊中
Public Declare Function GetWindowsDirectory Lib "kernel32" Alias "GetWindowsDirectoryA" (ByVal lpBuffer As String, ByVal nSize As Long) As Long
Public Declare Function GetSystemDirectory Lib "kernel32" Alias "GetSystemDirectoryA" (ByVal lpBuffer As String, ByVal nSize As Long) As Long

#End If

Public Enum FontType
    ShxFont = 0
    BigFont = 1
    TrueTypeFont = 2
End Enum

Public Function EnumFontFamProc(lpNLF As LOGFONT, lpNTM As NEWTEXTMETRIC, _
    ByVal FontType As Long, Fonts As Collection) As Long
    
    Dim FaceName As String
    Dim FullName As String
    FaceName = StrConv(lpNLF.lfFaceName, vbUnicode)
    Fonts.add Left$(FaceName, InStr(FaceName, vbNullChar) - 1)
    EnumFontFamProc = 1
End Function

'自定義兩個函數：
'獲取系統字體
Public Sub FillListWithFonts(ByVal hWnd As Long, ByRef Fonts As Collection)
    Dim hDC As Long
    hDC = GetDC(hWnd)
    EnumFontFamilies hDC, vbNullString, AddressOf EnumFontFamProc, Fonts
    ReleaseDC hWnd, hDC
End Sub

Public Function GetShxFont(ByVal bBigFont As Boolean) As Variant
    Dim strFontFileName() As String     ' 所有字體名稱的數組
    Dim strFontPath() As String     ' AutoCAD的字體文件路徑
    
    ' 獲得所有的支持文件路徑
    strFontPath = Split(ThisDrawing.Application.preferences.Files, ";")
    
    ' 遍歷所有的支持文件路徑
    Dim i As Integer
    Dim bFirst As Boolean       ' 是否是第一次查找該文件夾
    Dim strFont As String       ' 字體文件名稱
    Dim strTemp As String       ' 讀取到的字體文件的一行
    Dim intCount As Integer     ' 字體數組的維數
    Dim strFontFile As String   ' 字體文件的位置
    intCount = -1
    For i = 0 To UBound(strFontPath)
        bFirst = True
        ' 確保最後一個字符是"\"
        strFontPath(i) = IIf(Right(strFontPath(i), 1) = "\", strFontPath(i), strFontPath(i) & "\")
        
        Do
            If bFirst Then
                strFont = Dir(strFontPath(i) & "*.shx")
                bFirst = False
            Else
                strFont = Dir
            End If
            
            If Len(strFont) <> 0 Then
                ' 打開字體文件
                strFontFile = strFontPath(i) & strFont
                Open strFontFile For Input As #1
                Line Input #1, strTemp
                Close #1
                
                ' 判斷字體的類型
                If bBigFont Then
                    If Mid(strTemp, 12, 7) = "bigfont" Then
                        intCount = intCount + 1
                        ReDim Preserve strFontFileName(intCount)
                        strFontFileName(intCount) = strFont
                    End If
                Else
                    If Mid(strTemp, 12, 7) = "unifont" Or Mid(strTemp, 12, 6) = "shapes" Then
                        intCount = intCount + 1
                        ReDim Preserve strFontFileName(intCount)
                        strFontFileName(intCount) = strFont
                    End If
                End If
            Else
                Exit Do
            End If
        Loop
    Next i
    
    GetShxFont = strFontFileName
End Function
 '在程序中調用

Public Function GetWindowsFonts() As Variant
    Dim bBigFont As Boolean
    Dim WindowsDirectory As String, SystemDirectory As String, x As Long
    WindowsDirectory = space(255)       'Windows的安裝目錄
    SystemDirectory = space(255)        '系統目錄是
    x = GetWindowsDirectory(WindowsDirectory, 255)
    x = GetSystemDirectory(SystemDirectory, 255)
    
    
    Dim strFontFileName() As String     ' 所有字體名稱的數組
    Dim WinFontPath As String     ' Windows 的字體文件路徑
    
    ' 獲得所有的支持文件路徑
    WinFontPath = Left(WindowsDirectory, InStr(WindowsDirectory, Chr(0)) - 1)
    WinFontPath = Trim(WinFontPath) & "\Fonts\"
    
    ' 遍歷所有的支持文件路徑
    Dim i As Integer
    Dim bFirst As Boolean       ' 是否是第一次查找該文件夾
    Dim strFont As String       ' 字體文件名稱
    Dim strTemp As String       ' 讀取到的字體文件的一行
    Dim intCount As Integer     ' 字體數組的維數
    Dim strFontFile As String   ' 字體文件的位置
    intCount = -1
    For i = 0 To 0
        bFirst = True
        ' 確保最後一個字符是"\"
        WinFontPath = IIf(Right(WinFontPath, 1) = "\", WinFontPath, WinFontPath & "\")
        
        Do
            If bFirst Then
                strFont = Dir(WinFontPath & "*")
                bFirst = False
            Else
                strFont = Dir
            End If
            
            If Len(strFont) <> 0 Then
                ' 打開字體文件
                strFontFile = WinFontPath & strFont
                
                
                
                ' 判斷字體的類型
                If InStr(1, UCase(strFontFile), "TTF") <> 0 Then
                        intCount = intCount + 1
                        ReDim Preserve strFontFileName(intCount)
                        strFontFileName(intCount) = strFontFile
                        
                ElseIf InStr(1, UCase(strFontFile), "TTE") <> 0 Then
                        intCount = intCount + 1
                        ReDim Preserve strFontFileName(intCount)
                        strFontFileName(intCount) = strFontFile
                ElseIf InStr(1, UCase(strFontFile), "TTC") <> 0 Then
                        intCount = intCount + 1
                        ReDim Preserve strFontFileName(intCount)
                        strFontFileName(intCount) = strFontFile
                End If
            Else
                Exit Do
            End If
        Loop
    Next i
    
    GetWindowsFonts = strFontFileName
    
    
End Function

Public Function CreateTextStyle(ByVal fontName As String, ByVal styleName As String, ByVal font As FontType) As AcadTextStyle
    Dim objTextStyle As AcadTextStyle
    Set objTextStyle = ThisDrawing.TextStyles.add(styleName)
    
    Dim WindowsDirectory As String, SystemDirectory As String, x As Long
    Dim fontTemp As String
    
    If font = ShxFont Then
        objTextStyle.fontFile = fontName
    ElseIf font = BigFont Then
    
        WindowsDirectory = space(255)       'Windows的安裝目錄
        x = GetWindowsDirectory(WindowsDirectory, 255)
        
        
        Dim strFontFileName() As String     ' 所有字體名稱的數組
        Dim WinFontPath As String     ' Windows 的字體文件路徑
        
        ' 獲得所有的支持文件路徑
        WinFontPath = Left(WindowsDirectory, InStr(WindowsDirectory, Chr(0)) - 1)
        WinFontPath = Trim(WinFontPath) & "\Fonts\"
        ' 判斷字體的類型
        If InStr(1, UCase(fontName), "TTF") <> 0 Then
            fontTemp = """" & WinFontPath & fontName & """"
            objTextStyle.BigFontFile = fontTemp
            
        ElseIf InStr(1, UCase(fontName), "TTE") <> 0 Then
            fontTemp = """" & WinFontPath & fontName & """"
            objTextStyle.BigFontFile = fontTemp
        End If
    ElseIf font = TrueTypeFont Then
        ' 獲得當前字體的樣式
        Dim typeFace As String
        Dim Bold As Boolean
        Dim Italic As Boolean
        Dim charSet As Long
        Dim PitchandFamily As Long
        ThisDrawing.ActiveTextStyle.GetFont typeFace, Bold, Italic, charSet, PitchandFamily
        
        objTextStyle.SetFont fontName, Bold, Italic, charSet, PitchandFamily
    End If
    
    objTextStyle.width = 1#
    objTextStyle.ObliqueAngle = 0#
    
    Set CreateTextStyle = objTextStyle
End Function

Attribute VB_Name = "Module_sort"
Option Explicit
Option Compare Binary


Option Base 1
'陣列排序----大
Dim MaxVal As Variant
    
Function SelectionSortMaxTow(TempArray As Variant, TempArrayEnt As Variant)
    Dim MaxIndex As Double
    Dim MaxObj As Object
    Dim i, j As Integer

    ' Step through the elements in the array starting with the
    ' last element in the array.
    For i = UBound(TempArray) To 0 Step -1

        ' Set MaxVal to the element in the array and save the
        ' index of this element as MaxIndex.
        MaxVal = TempArray(i)
        MaxIndex = i

        ' Loop through the remaining elements to see if any is
        ' larger than MaxVal. If it is then set this element
        ' to be the new MaxVal.
        For j = 0 To i
            If TempArray(j) > MaxVal Then
                MaxVal = TempArray(j)
                Set MaxObj = TempArrayEnt(j)
                MaxIndex = j
            End If
        Next j

        ' If the index of the largest element is not i, then
        ' exchange this element with element i.
        If MaxIndex < i Then
            TempArray(MaxIndex) = TempArray(i)
            TempArray(i) = MaxVal
            
            Set TempArrayEnt(MaxIndex) = TempArrayEnt(i)
            Set TempArrayEnt(i) = MaxObj
            
        End If
    Next i
End Function
    
    
    
    
    
    
    
Function SelectionSortMax(TempArray As Variant)
    Dim MaxIndex As Integer
    Dim i, j As Integer

    ' Step through the elements in the array starting with the
    ' last element in the array.
    For i = UBound(TempArray) To 1 Step -1

        ' Set MaxVal to the element in the array and save the
        ' index of this element as MaxIndex.
        MaxVal = TempArray(i)
        MaxIndex = i

        ' Loop through the remaining elements to see if any is
        ' larger than MaxVal. If it is then set this element
        ' to be the new MaxVal.
        For j = 1 To i
            If TempArray(j) > MaxVal Then
                MaxVal = TempArray(j)
                MaxIndex = j
            End If
        Next j

        ' If the index of the largest element is not i, then
        ' exchange this element with element i.
        If MaxIndex < i Then
            TempArray(MaxIndex) = TempArray(i)
            TempArray(i) = MaxVal
        End If
    Next i

End Function

'陣列排序----小
Function SelectionSortMin(TempArray As Variant)
    Dim MinVal As Variant
    Dim MinIndex As Integer
    Dim i, j As Integer

    ' Step through the elements in the array starting with the
    ' last element in the array.
    For i = 1 To UBound(TempArray)
    
        ' Set MaxVal to the element in the array and save the
        ' index of this element as MaxIndex.
        MinVal = TempArray(i)
        MinIndex = i

        ' Loop through the remaining elements to see if any is
        ' larger than MaxVal. If it is then set this element
        ' to be the new MaxVal.
        For j = 1 To UBound(TempArray)
            If TempArray(i) = "" Then
            
            ElseIf TempArray(j) > TempArray(i) Then
                    MinVal = TempArray(j)
                    TempArray(j) = TempArray(i)
                    TempArray(i) = MinVal
                
            ElseIf TempArray(i) = "" Then
                    MinVal = TempArray(j)
                    TempArray(j) = TempArray(i)
                    TempArray(i) = MinVal
            End If
        Next j

    Next
End Function

Function SelectionSort(TempArray As Variant)
    Dim MaxVal As Variant
    Dim MaxIndex As Integer
    Dim i, j As Integer

    ' Step through the elements in the array starting with the
    ' last element in the array.
    For i = UBound(TempArray) To 1 Step -1

        ' Set MaxVal to the element in the array and save the
        ' index of this element as MaxIndex.
        MaxVal = TempArray(i)
        MaxIndex = i

        ' Loop through the remaining elements to see if any is
        ' larger than MaxVal. If it is then set this element
        ' to be the new MaxVal.
        For j = 1 To i
            If TempArray(j) > MaxVal Then
                MaxVal = TempArray(j)
                MaxIndex = j
            End If
        Next j

        ' If the index of the largest element is not i, then
        ' exchange this element with element i.
        If MaxIndex < i Then
            TempArray(MaxIndex) = TempArray(i)
            TempArray(i) = MaxVal
        End If
    Next i

End Function

Sub SelectionSortMyArray()
    Dim TheArray As Variant
    Dim SSS As String
    Dim i As Integer
    ' Create the array.
    TheArray = Array("one", "two", "three", "four", "five", "six", _
        "seven", "eight", "nine", "ten")

    ' Sort the Array and display the values in order.
    SelectionSort TheArray
    For i = 1 To UBound(TheArray)
        SSS = SSS & TheArray(i) & vbCrLf
    Next i
MsgBox SSS
End Sub

Attribute VB_Name = "MusicBlockGraphics"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
    

Const MAINLAYER As String = "main"     '主要的圖層
'    '音附的駐點位置
'Private Type GripPoints
'    osnPtMid(0 To 2) As Double       '在正中間
'    osnPtNode1(0 To 2) As Double     '在左下
'    osnPtNode2(0 To 2) As Double     '在中上
'    osnPtEnd1(0 To 2) As Double      '在左中
'    osnPtEnd2(0 To 2) As Double      '在右中
'    atPt(0 To 2) As Double           '備注點
'End Type
Dim gTextSize As Double
Dim gAtPt As New point
Dim MData As String

Dim MFS As MusicFing

Dim Grippt As GripPoints  '音附指法 狀態


    Dim kFing(30 To 255) As String
    Dim posFing(0 To 255) As point
    Dim kTowFing(30 To 255) As String
    Dim posTowFing(0 To 255) As point
    
Const MAX200 As Integer = 200

Function Grip() As GripPoints
      Grip = Grippt
End Function

Property Let TextSize(TSize As Double)
    gTextSize = TSize
End Property
Property Get TextSize() As Double
    TextSize = gTextSize
End Property

Property Let DataTest(dtest As String)
    MData = dtest
End Property
Property Get DataTest() As String
    DataTest = MData
End Property
Property Get copy() As MusicBlockGraphics
    Dim copy_mbg As New MusicBlockGraphics
    copy_mbg.setDataText gAtPt, MData, gTextSize
    Set copy = copy_mbg
End Property

Sub setDataText(position As point, cst As String, TextSize As Double)

    'position 插入的位置
    'cst  文字資料=指法1 八度音 主音 拍子 指法2
    '          共5筆 每筆一個字元 所以共5個字元
    'textSize  字形大小
    
    MData = cst
    
    gAtPt.x = position.x
    gAtPt.Y = position.Y
    gAtPt.z = position.z
    
    gTextSize = TextSize
    setGripPoints gAtPt
    
    
    
'Public Type MusicFing
'    sTONE As String        ' 升降記號 行
'    sFinge As String   '這是指法行     _+)(*&
'    sScale As String   '這是高低音行   .:! ,;?
'    sNote As String   '這為主行       1234567.|l
'    sTempo As String   '這是拍子       -=368acefz
'    sTowFinge As String   '這是指法行第二行  _+)(*&
'    sSlur As String
'End Type
    

    Dim cc As String
    cc = ""

    '取得關鍵字  主音 AMT.iNote
    cc = Mid(MData, amt.iNote, 1)
    Select Case cc
       Case "0": MFS.sNote = "M-NOTE0"
       Case "1": MFS.sNote = "M-NOTE1"
       Case "2": MFS.sNote = "M-NOTE2"
       Case "3": MFS.sNote = "M-NOTE3"
       Case "4": MFS.sNote = "M-NOTE4"
       Case "5": MFS.sNote = "M-NOTE5"
       Case "6": MFS.sNote = "M-NOTE6"
       Case "7": MFS.sNote = "M-NOTE7"
       Case ".": MFS.sNote = "M-NOTE."
       Case "-": MFS.sNote = "M-NOTE-"
       Case "o": MFS.sNote = "M-NOTEo"
       Case "x": MFS.sNote = "M-NOTEx"
       Case "X": MFS.sNote = "M-NOTEX2"
       Case "e": MFS.sNote = "M-NOTEe"
       Case "E": MFS.sNote = "M-NOTEE2"
       Case " ": MFS.sNote = ""
       Case Else
            MFS.sNote = ""
    End Select
    
    '取得關鍵字 拍子  -=368acefz amt.iTempo
    Dim iLe As Integer
    Dim cn As String
    
    iLe = Tempo_c2line(Mid(cst, amt.iTempo, 1))
    Select Case iLe
        Case 0: MFS.sTempo = ""
                MFS.iTempo = 0
        Case 1: MFS.sTempo = "M-TEMPO1"
                MFS.iTempo = 1
        Case 2: MFS.sTempo = "M-TEMPO2"
                MFS.iTempo = 2
        Case 3: MFS.sTempo = "M-TEMPO3"
                MFS.iTempo = 3
        Case 4: MFS.sTempo = "M-TEMPO4"
                MFS.iTempo = 4
        Case Else
             MFS.sTempo = ""
                MFS.iTempo = 0
    End Select
    
    '取得關鍵字高低音行   .:! ,;?
    '    sScale As String
    cc = Mid(MData, amt.iScale, 1)
    Select Case cc
       Case ".": MFS.sScale = "M-SCALE1"
                 MFS.iScale = 1
       Case ":": MFS.sScale = "M-SCALE2"
                 MFS.iScale = 2
       Case "!": MFS.sScale = "M-SCALE3"
                 MFS.iScale = 3
       Case ",": MFS.sScale = "M-SCALEa"
                 MFS.iScale = -1
       Case ";": MFS.sScale = "M-SCALEb"
                 MFS.iScale = -2
       Case "?": MFS.sScale = "M-SCALEc"
                 MFS.iScale = -3
       Case " ": MFS.sScale = ""
                 MFS.iScale = 0
       Case Else
            MFS.sScale = ""
                 MFS.iScale = 0
    End Select
    

'    '取得關鍵字 -指法1
    cc = Mid(cst, amt.iFinge, 1)
    MFS.sFinge = ""
    Select Case cc
        Case "a" To "z", "A" To "Z", "-", "=", "@"
            MFS.sFinge = kFing(Asc(cc))
            Set MFS.mfPosition = posFing(Asc(cc)).copy
        Case " "
        Case "("
        Case "|"
        Case Else
        MFS.sFinge = ""
            
    End Select



'    '取得關鍵字 -指法2
    cc = Mid(cst, amt.iTowFinge, 1)
    MFS.sTowFinge = ""
    Select Case cc
        Case "a" To "z", "A" To "Z", "-", "=", "@"
            MFS.sTowFinge = kTowFing(Asc(cc))
            Set MFS.mfTowPosition = posTowFing(Asc(cc)).copy
        Case " "
        Case "("
        Case "|"
        Case Else
        MFS.sTowFinge = ""
            
    End Select

'    '取得升降字 -特疏字法
    cc = Mid(cst, amt.iTONE, 1)
    MFS.sTONE = cc


'    '取得關鍵字 -指法1
'     Select Case Mid(cst, amt.iFinge, 1)
'        Case "0": tmp_erhu_fing.fing1 = tmp_erhu_fing.fing1 + amt.f空弦 '空弦
'        Case "1": tmp_erhu_fing.fing1 = tmp_erhu_fing.fing1 + amt.f一指
'        Case "2": tmp_erhu_fing.fing1 = tmp_erhu_fing.fing1 + amt.f二指
'        Case "3": tmp_erhu_fing.fing1 = tmp_erhu_fing.fing1 + amt.f三指
'        Case "4": tmp_erhu_fing.fing1 = tmp_erhu_fing.fing1 + amt.f四指
'        Case "W", "w": tmp_erhu_fing.fing1 = tmp_erhu_fing.fing1 + amt.f揉弦
'
'        Case "E", "e": tmp_erhu_fing.Push = "拉"
'        Case "V", "v": tmp_erhu_fing.Push = "推"
'        Case "Q", "q": tmp_erhu_fing.InOut = "內"
'        Case "A", "a": tmp_erhu_fing.InOut = "外"
'        Case Else
'     End Select
'
'     '取得關鍵字 -指法2
'     Select Case Mid(cst, amt.iTowFinge, 1)
'        Case "0": tmp_erhu_fing.fing1 = tmp_erhu_fing.fing1 + amt.f空弦 '空弦
'        Case "1": tmp_erhu_fing.fing1 = tmp_erhu_fing.fing1 + amt.f一指
'        Case "2": tmp_erhu_fing.fing1 = tmp_erhu_fing.fing1 + amt.f二指
'        Case "3": tmp_erhu_fing.fing1 = tmp_erhu_fing.fing1 + amt.f三指
'        Case "4": tmp_erhu_fing.fing1 = tmp_erhu_fing.fing1 + amt.f四指
'        Case "W", "w": tmp_erhu_fing.fing1 = tmp_erhu_fing.fing1 + amt.f揉弦
'
'        Case "E", "e": tmp_erhu_fing.Push = "拉"
'        Case "V", "v": tmp_erhu_fing.Push = "推"
'        Case "Q", "q": tmp_erhu_fing.InOut = "內"
'        Case "A", "a": tmp_erhu_fing.InOut = "外"
'
'        Case Else
'     End Select



End Sub

Private Sub setGripPoints(ths_aPt As point)
'駐點轉換
    'Dim Grippt As New GripPoints
    Set Grippt.atPt = ths_aPt
    Set Grippt.gptLeft = New point
    Set Grippt.gptLeftDown = New point
    Set Grippt.gptMid = New point
    Set Grippt.gptMidUp = New point
    Set Grippt.gptRight = New point
    
    
    
    '在正中間
    Grippt.gptMid.x = ths_aPt.x + (amt.A_TEXT_WIDTH * gTextSize) / 2
    Grippt.gptMid.Y = ths_aPt.Y + (amt.bkMidHight * gTextSize)
    
    '在中上
    Grippt.gptMidUp.x = ths_aPt.x + (amt.A_TEXT_WIDTH * gTextSize) / 2
    Grippt.gptMidUp.Y = ths_aPt.Y + (amt.bkMidUpHight * gTextSize)
    
    '在左下
    Set Grippt.gptLeftDown = ths_aPt
    
    '在左中
    Grippt.gptLeft.x = ths_aPt.x
    Grippt.gptLeft.Y = ths_aPt.Y + (amt.bkMidHight * gTextSize)
    '在右中
    Grippt.gptRight.x = ths_aPt.x + (amt.A_TEXT_WIDTH * gTextSize)
    Grippt.gptRight.Y = ths_aPt.Y + (amt.bkMidHight * gTextSize)
    
End Sub
Public Function InsterEnt() As AcadBlockReference '插入音附
    Dim textObj As AcadText
    Dim blockRefObj  As AcadBlockReference
    Dim textString As String
    Dim aligPoint(0 To 2) As Double
    Dim height As Double
    Dim insertionPoint(0 To 2) As Double
    
    
    Dim varAttributes As Variant
    Dim entObj As AcadEntity
    Dim pickPnt As Variant
    Dim blkRefObj As AcadBlockReference
    Dim attVars As Variant
    Dim i As Integer
    Dim TheObj As AcadEntity
    Dim towPos As Double
    Dim cc As String
    
    
    Dim point1(0 To 2) As Double
    Dim point2(0 To 2) As Double
    point1(0) = 0: point1(1) = 0: point1(2) = 0
    point2(0) = 2: point2(1) = 0: point2(2) = 0

    insertionPoint(0) = Grippt.gptMid.x
    insertionPoint(1) = Grippt.gptMid.Y
    insertionPoint(2) = Grippt.gptMid.z
    If MFS.sNote <> "" Then
        Set InsterEnt = ThisDrawing.ModelSpace.InsertBlock(insertionPoint, MFS.sNote, gTextSize, gTextSize, gTextSize, 0)
        
        InsterEnt.Layer = MAINLAYER
    
        ' Create the text object in model space
        'cc = Mid(MData, amt.iNote, 1)
        'Set textObj = ThisDrawing.ModelSpace.AddText(cc, insertionPoint, gTextSize)
        'textObj.styleName = "musictxt"
        'textObj.Alignment = acAlignmentCenter
        'Call textObj.Move(point1, insertionPoint)
    
        
'        If MFS.sTempo <> "" Then
'            Call ThisDrawing.ModelSpace.InsertBlock(insertionPoint, MFS.sTempo, gTextSize, gTextSize, gTextSize, 0)
'        End If
        
        aligPoint(0) = insertionPoint(0)
        aligPoint(1) = insertionPoint(1)
        aligPoint(2) = insertionPoint(2)
        If MFS.sScale <> "" Then
            If MFS.iScale <= 0 Then
                If MFS.iTempo >= 1 Then    '下點音附 要移下去一些
                '有線時 要下去的距離
                    aligPoint(0) = insertionPoint(0)
                    aligPoint(1) = insertionPoint(1) - (amt.DROP_ADD_LINE_INTERVAL * gTextSize * MFS.iTempo)
                    aligPoint(2) = insertionPoint(2)
                End If
            End If
            Set TheObj = ThisDrawing.ModelSpace.InsertBlock(aligPoint, MFS.sScale, gTextSize, gTextSize, gTextSize, 0)
            TheObj.Layer = MAINLAYER
        End If
        If frmEDIT.chkOption1.Value = True Then
            '古箏指法
            If MFS.sFinge <> "" Then
                
                
                aligPoint(0) = insertionPoint(0) + (gTextSize * MFS.mfPosition.x)
                aligPoint(1) = insertionPoint(1) + (gTextSize * MFS.mfPosition.Y)
                aligPoint(2) = insertionPoint(2)
                
                
                Set TheObj = ThisDrawing.ModelSpace.InsertBlock(aligPoint, MFS.sFinge, gTextSize, gTextSize, gTextSize, 0)
                TheObj.Layer = MAINLAYER
            End If
            
            towPos = 0
            If MFS.sTowFinge <> "" Then
                
                aligPoint(0) = insertionPoint(0) + (gTextSize * MFS.mfTowPosition.x)
                aligPoint(1) = insertionPoint(1) + (gTextSize * MFS.mfTowPosition.Y)
                aligPoint(2) = insertionPoint(2)
                
                '減 拍線
                towPos = (amt.DROP_ADD_LINE_INTERVAL * MFS.iTempo)
                If MFS.iScale < 0 Then
                    '減 下點音附
                    towPos = towPos + (amt.DROP_INTERVAL * (-MFS.iScale))
                End If
                If towPos > 0.3 Then
                    aligPoint(1) = aligPoint(1) - (towPos * gTextSize)
                Else
                    aligPoint(1) = aligPoint(1) - (0.3 * gTextSize)
                End If
                
                Set TheObj = ThisDrawing.ModelSpace.InsertBlock(aligPoint, MFS.sTowFinge, gTextSize, gTextSize, gTextSize, 0)
                TheObj.Layer = MAINLAYER
            End If
            
        '*****畫特疏指法*******************************************
            If MFS.sTONE = "*" Then
                InsertMusicStar insertionPoint, gTextSize
            End If
            
        ElseIf frmEDIT.chkOption2.Value = True Then
            '二胡指法用
            
            
        End If
        
        
    
        '寫入屬性
        '本段代碼從選中的圖塊中獲取屬性值，並對其修改

    If InsterEnt Is Nothing Then
        Exit Function
    End If

    '如果選擇的是塊引用，將其賦給塊引用對象
    Set blkRefObj = InsterEnt
    '判斷該塊引用是否含有屬性值
    If Not blkRefObj.HasAttributes Then
        'MsgBox "你選擇的圖塊沒有塊屬性，程序將退出！"
        '如果不含由屬性值退出
        Exit Function
    End If
    '獲取塊引用中的塊屬性對象
    attVars = blkRefObj.GetAttributes
    '對塊屬性對象進行遍歷
    For i = LBound(attVars) To UBound(attVars)
'       MsgBox "第" & I + 1 & "屬性對象的屬性值分別如下：" & Chr(13) & Chr(13) & _
'               "屬性標籤為：" & attVars(I).TagString & Chr(13) & _
'               "屬性值為：" & attVars(I).textString
        
        '將塊屬性的標籤和值進行修改
    Select Case attVars(i).TagString
        Case "ITONE"
            attVars(i).textString = Mid(MData, amt.iTONE, 1)
        Case "IFINGE"
            attVars(i).textString = Mid(MData, amt.iFinge, 1)
        Case "ISCALE"
            attVars(i).textString = Mid(MData, amt.iScale, 1)
        Case "INOTE"
            attVars(i).textString = Mid(MData, amt.iNote, 1)
        Case "ITEMPO"
            '取得關鍵字 拍子  -=368acefz amt.iTempo
            attVars(i).textString = Mid(MData, amt.iTempo, 1)
        Case "ITOWFINGE"
            attVars(i).textString = Mid(MData, amt.iTowFinge, 1)
        Case "ISLUR"
            attVars(i).textString = Mid(MData, amt.iSlur, 1)
        Case "IRE1"
        Case Else
            
    End Select

    Next
    End If
End Function

Private Function Tempo_c2line(theC As String) As Integer
'拍子的 字元 轉 成幾條線

    
    Dim tempo_hj As String
    Dim tempo_val As Variant
    Dim tempo_ll As Variant
    
    tempo_hj = " -2=45368aAcCfFgGzZ"
    tempo_ll = Array(1, 2, 2, 4, 4, 5, 3, 6, 8, 10, 10, 12, 12, 15, 15, 16, 32, 32)
    tempo_val = Array(0, 1, 1, 2, 2, 2, 2, 2, 3, 3, 3, 4, 4, 4, 4, 4, 4, 4, 4)
    

    Dim ii As Integer
    Dim cn As String
    If theC <> "" Then
    
    For ii = 0 To Len(tempo_hj) - 1
        cn = Mid(tempo_hj, ii + 1, 1)
        If cn = Mid(theC, 1, 1) Then
            Tempo_c2line = tempo_val(ii)
            Exit Function

        End If
    Next ii
    
    End If
    Tempo_c2line = 0
End Function

Private Function Tempo_c2number(cc As String) As Double
'拍子的 字元 轉成 時值

    
    Dim tempo_hj As String
    Dim tempo_val As Variant
    Dim tempo_ll As Variant
    
    tempo_hj = " -2=45368aAcCfFgGzZ"
    tempo_ll = Array(1, 2, 2, 4, 4, 5, 3, 6, 8, 10, 10, 12, 12, 15, 15, 16, 16, 32, 32)
    tempo_val = Array(0, 1, 1, 2, 2, 2, 2, 2, 3, 3, 3, 4, 4, 4, 4, 4, 4, 4, 4)
    

    Dim ii As Integer
    Dim cn As String
    For ii = 0 To Len(tempo_hj) - 1
        cn = Mid(tempo_hj, ii + 1, 1)
        If cn = Mid(theC, 1, 1) Then
            Tempo_c2line = tempo_ll(ii)
            Exit Function
        End If
    Next ii
    Tempo_c2line = 0
End Function




Public Function addMusicJoin(ByVal the_Ids As Variant)

'取得物件 MusicText
'用x 軸來鏈結
On Error Resume Next

    Dim ent As Object
    
    '排序陣列
    Dim TheArray As Variant
    Dim TheArrayEnt As Variant
    Dim coI As Integer
    Dim i As Long
    
    ' Add the dimstyle to the dimstyles collection
    coI = 0
  ' 找出圖面中的每一個選集
    For i = 0 To UBound(the_Ids, 1)
        If the_Ids(i).ObjectName = "AcDbBlockReference" Then
            coI = coI + 1
        End If
    Next

    
    '只有一個，不用排序了
    If coI < 1 Then
        Exit Function
    End If
    
    ReDim TheArray(coI - 1)
    ReDim TheArrayEnt(coI - 1)
    
    coI = 0
    'Dim MTobj As NnmText
    Dim pt As Variant
    
    For i = 0 To UBound(the_Ids, 1)
        Set ent = the_Ids(i)
        If (Mid(ent.name, 1, 6) = "M-NOTE") Then
            pt = ent.insertionPoint()
            TheArray(coI) = pt(0)
            Set TheArrayEnt(coI) = ent
            coI = coI + 1
            
            
            Dim minExt As Variant
            Dim maxExt As Variant
    
            ent.GetBoundingBox minExt, maxExt
            'Set MTobj = ent
            'minExt = MTobj.GripLeft()
            
        End If
    Next
    
    
    
    '排序開始
    SelectionSortMaxTow TheArray, TheArrayEnt
    
    
    Dim stPt As point
    Dim endPt As point
    Dim tempo_num(0 To 20) As Integer
    Dim ptTheArr(0 To 20) As point
    Dim cIT As String
    Dim insertionPoint As Variant
    Dim entArr As AcadEntity
    
    Set stPt = New point
    Set endPt = New point
    
    '取得拍子的線條數量及 物件位置
    For i = 0 To UBound(TheArray)
        Set entArr = TheArrayEnt(i)
        cIT = GetAttribTextString(entArr, "ITEMPO")
        
        tempo_num(i) = Tempo_c2line(cIT)
        insertionPoint = TheArrayEnt(i).insertionPoint
        Set ptTheArr(i) = New point
        ptTheArr(i).c insertionPoint(0), insertionPoint(1), insertionPoint(2)
    Next
    
    

    Dim x As Integer
'    for (int x =1; x<=the_lineOne; x++)
    For x = 1 To 4
        For i = 0 To UBound(TheArray)
            If tempo_num(i) >= x Then
                If stPt.x = 0 Then
                    Set stPt = ptTheArr(i).copy '取得第一個位置
                Else
                    Set endPt = ptTheArr(i).copy '取得第 後面的位置
                End If
                If i = UBound(TheArray) Then  '如是最後一個就畫出來
                    If endPt.x = 0 Then
                        Set endPt = stPt.copy
                    End If
                    line_link x - 1, stPt, endPt
                    stPt.c 0, 0, 0
                    endPt.c 0, 0, 0
                End If
            Else
                If stPt.x <> 0 Then
                    If endPt.x = 0 Then
                        Set endPt = stPt.copy
                    End If
                    line_link x - 1, stPt, endPt
                    stPt.c 0, 0, 0
                    endPt.c 0, 0, 0
                    
                End If
            
            End If
        Next
    Next
            



EndJoin:
End Function

'
'//畫拍子的線
'// num_col   要畫幾個線
'// l_pt, r_pt  左右鏈結的中點

Sub line_link(num_col As Integer, lPt As point, rPt As point)

    If num_col < 0 Then
        Exit Sub
    End If
    
    Dim xt As Double
    Dim yt As Double
    
    Dim plineObj As AcadPolyline
    Dim points(0 To 5) As Double
    
    ' Define the 2D polyline points
    points(0) = lPt.x - amt.A_TEXT_WIDTH / 2 * gTextSize
    points(1) = lPt.Y - (amt.bkInster_Line_H * gTextSize) - (num_col * amt.LINE_JUMP * gTextSize)
    points(2) = lPt.z
    
    
    points(3) = rPt.x + amt.A_TEXT_WIDTH / 2 * gTextSize
    points(4) = points(1)
    points(5) = rPt.z
        
    ' Create a lightweight Polyline object in model space
    Set plineObj = ThisDrawing.ModelSpace.AddPolyline(points)
    plineObj.SetWidth 0, gTextSize * amt.LINE_THICKNESS, gTextSize * amt.LINE_THICKNESS
    plineObj.Layer = MAINLAYER
    'Call ThisDrawing.ModelSpace.AddPolyline .InsertBlock(insertionPoint, MFS.sFinge, gTextSize, gTextSize, gTextSize, 0)

End Sub

Private Function InsertMusicStar(insertionPoint() As Double, size As Double)
'插入古箏 前音 琵音 * 號
'insertionPoint  是本音符的位置

    
    Dim textObj As AcadText
    Dim blockRefObj  As AcadBlockReference
    Dim textString As String
    Dim alignmentPoint(0 To 2) As Double
    Dim midDownPt(0 To 2) As Double
    Dim height As Double
        
    
    
    Dim xStar As Double
    Dim yStar As Double
    Dim ssize As Double
    xStar = -1.06 '星指法的 X 上增量
    yStar = 1.3 '星指法的 Y 上增量
    ssize = 0.65 '小字的比例
    

    alignmentPoint(0) = insertionPoint(0) + (size * xStar)
    alignmentPoint(1) = insertionPoint(1) + (size * yStar)
    alignmentPoint(2) = insertionPoint(2)

    
    midDownPt(0) = alignmentPoint(0) + (amt.A_TEXT_WIDTH / 2 * size * ssize)
    midDownPt(1) = alignmentPoint(1)
    midDownPt(2) = alignmentPoint(2)


'*******畫星字*****************
    
    Set blockRefObj = ThisDrawing.ModelSpace.InsertBlock(midDownPt, "M-NOTESTAR", size, size, size, 0)
    blockRefObj.Layer = "裝飾符號"
    
'*******畫拍線*****************
    Dim sMGB As New MusicBlockGraphics
    Dim ppt As New point
    Dim lPt As New point
    Dim rPt As New point
    
    sMGB.setDataText ppt, "", size * ssize
    
        
    lPt.x = midDownPt(0)
    lPt.Y = midDownPt(1) + (0.15 * size * ssize)
    lPt.z = midDownPt(2)
    
    rPt.x = lPt.x
    rPt.Y = lPt.Y
    rPt.z = lPt.z

    sMGB.line_link 1, lPt, rPt
    sMGB.line_link 2, lPt, rPt
    
'*******畫弧*****************
      
    Dim arcObj As AcadArc
    Dim centerPoint(0 To 2) As Double
    Dim radius As Double
    Dim startAngleInDegree As Double
    Dim endAngleInDegree As Double
    
    ' Define the circle
    
    radius = 0.38 * size * ssize
    centerPoint(0) = midDownPt(0) + radius
    centerPoint(1) = midDownPt(1) - 0.3 * size * ssize
    centerPoint(2) = midDownPt(2)
    startAngleInDegree = 180#
    endAngleInDegree = 275#
    
    ' Convert the angles in degrees to angles in radians
    Dim startAngleInRadian As Double
    Dim endAngleInRadian As Double
    startAngleInRadian = startAngleInDegree * 3.141592 / 180#
    endAngleInRadian = endAngleInDegree * 3.141592 / 180#
    
    ' Create the arc object in model space
    Set arcObj = ThisDrawing.ModelSpace.AddArc(centerPoint, radius, startAngleInRadian, endAngleInRadian)
    arcObj.Layer = "裝飾符號"
    
End Function


Private Sub linkGrapTempoMaray(the_lineOne As Integer)
    '畫拍子聯結
    'pW
    'lineOne 是要看，現在是第幾條線
    
'    MusicData tmp_md = this->m_MusicData ;
'
'    string cst;
'    cst += "MT::linkGrapTempoMaray";
'    cst += tmp_md.strNnmTextData ;
'
'    LOG1W(cst.c_str(),(long )__LINE__);
'
'
'    AcGePoint3d stPt, endPt;
'    stPt = AcGePoint3d(0,0,0);
'    endPt = AcGePoint3d(0,0,0);
'
'    MusicText *tmp_objMTXT;
'
'    deque<structMT> sDeque;
'    deque<structMT>::iterator  tmp_iterSDeque;
'
'    //mapData::iterator pos;
'
'    structMT tmp_sMT;
'    //Acad::ErrorStatus es;
'
'    tmp_sMT.pt = tmp_md.point_;
'    tmp_sMT.m_tempo = tmp_md.tempo;
'
'    sDeque.push_back(tmp_sMT);
'
'
'    if (tmp_md.LlinkobjId != NULL)
'    {
'        return;
'    }
'    else if (tmp_md.RlinkobjId != NULL)
'    {
'        while(tmp_md.RlinkobjId != NULL )
'        {
'
'            if (acdbOpenObject((AcDbObject*&)tmp_objMTXT, tmp_md.RlinkobjId,
'                AcDb::kForWrite) == Acad::eOk)
'            {
'
'                tmp_md = tmp_objMTXT->m_MusicData ;
'
'                tmp_sMT.pt = tmp_md.point_;
'                tmp_sMT.m_tempo = tmp_md.tempo ;
'
'                sDeque.push_back(tmp_sMT);
'                tmp_objMTXT->close();
'            }
'            Else
'            {
'
'                cst = "";
'                cst += "未取得 id- pu438";
'                LOG1W(cst.c_str(),(long )__LINE__);
'
'                acutPrintf( "\n 未取得 id- pu438" );
'                tmp_md.RlinkobjId = NULL;
'
'            }
'        }
'    }
'
'    LOG1W(cst.c_str(),(long )__LINE__);
'
'    for (int x =1; x<=the_lineOne; x++)
'    {
'        for( tmp_iterSDeque = sDeque.begin(); tmp_iterSDeque != sDeque.end(); tmp_iterSDeque++)
'        {
'            if(((*tmp_iterSDeque).m_tempo) >= x)
'            {
'                if(stPt.x == 0)
'                {
'                    stPt = (*tmp_iterSDeque).pt;    //取得第一個位置
'                }
'                Else
'                {
'                    endPt = (*tmp_iterSDeque).pt;   //取得第後面的位置
'                }
'                if(tmp_iterSDeque == (sDeque.end()-1))//如是最後一個就畫出來
'                {
'                    if (endPt.x == 0)
'                    {
'                        endPt = stPt;
'                    }
'                    m_pGObject->line_link(pW, x-1, stPt, endPt);
'                    stPt = AcGePoint3d(0,0,0);
'                    endPt = AcGePoint3d(0,0,0);
'                }
'
'            }
'            Else
'            {
'                if(stPt.x != 0)
'                {
'                    if (endPt.x == 0)
'                    {
'                        endPt = stPt;
'                    }
'                    m_pGObject->line_link(pW, x-1, stPt, endPt);
'                    stPt = AcGePoint3d(0,0,0);
'                    endPt = AcGePoint3d(0,0,0);
'                }
'            }
'        }
'    }
'
'
'}

End Sub


Private Sub Class_Initialize()

    
    Dim kNUM1 As String, kNUM2 As String, kNUM3 As String, kNUM4 As String
    Dim kNUM5 As String, kNUM6 As String, kNUM7 As String, kNUM0 As String
    Dim k延長一拍 As String
    Dim kLIN1 As String: Dim kLIN2 As String: Dim kLIN3 As String
    Dim kUP1 As String
    Dim kUP2 As String
    Dim kDOW1 As String
    Dim kDOW2 As String
    Dim kAdot As String
    Dim kBarLine As String
    'Dim kFing(30 To 255) As String
    'Dim posFing(0 To 255) As point
    Dim posLinDown As Variant
    
    posLinDown = Array(0, 12, 26, 40)   '這是看低音下點要移多少下去，是當200字型時計算
    
    kNUM1 = ChrW(&H4E52)
    kNUM2 = ChrW(&H4E53)
    kNUM3 = ChrW(&H4E56)
    kNUM4 = ChrW(&H4E58)
    kNUM5 = ChrW(&H4E59)
    kNUM6 = ChrW(&H4E5C)
    kNUM7 = ChrW(&H4E5D)
    kNUM0 = ChrW(&H5D4C)
    k延長一拍 = ChrW(&H5D1F)
    kLIN1 = ChrW(&H5D39): kLIN2 = ChrW(&H5D3A): kLIN3 = ChrW(&H5D3C)
    kUP1 = ChrW(&H66E0): kUP2 = ChrW(&H66E3): kDOW1 = ChrW(&H66E6): kDOW2 = ChrW(&H66E8)
    kAdot = ChrW(&H5D3D)            '符點音符
    kBarLine = ChrW(&H601D)
    kFing(Asc("z")) = "MT" & Format(Asc("z"), "0000") 'ASC_z 122 ChrW(&H6416)  ' z 大指
    kFing(Asc("x")) = "MT" & Format(Asc("x"), "0000") 'ASC_x 120 ChrW(&H641A)  ' x 食指
    kFing(Asc("c")) = "MT" & Format(Asc("c"), "0000") 'ASC_c 99 ChrW(&H641C)  ' c 中指
    kFing(Asc("v")) = "MT" & Format(Asc("v"), "0000") 'ASC_v 118 ChrW(&H641F)  ' v 無名指
    kFing(Asc("a")) = "MT" & Format(Asc("a"), "0000") 'ASC_a 97 ChrW(&H6421)  ' a 八度
    kFing(Asc("s")) = "MT" & Format(Asc("s"), "0000") 'ASC_s 115 ChrW(&H66FC)  ' s 王字指法
    kFing(Asc("d")) = "MT" & Format(Asc("d"), "0000") 'ASC_d 100 ChrW(&H6700)  ' d 搖指
    'kFing(Asc("p")) = "MT" & Format(Asc("p"), "0000") 'ASC_p 112 ChrW(&H6381)  ' p 卜指法
    kFing(Asc("Z")) = "MT" & Format(Asc("Z"), "0000") 'ASC_Z 90 ChrW(&H6418)  ' 大寫Z 反大指法
    kFing(Asc("A")) = "MT" & Format(Asc("A"), "0000") 'ASC_A 65 ChrW(&H6413)  ' 大寫A 反八度
    kFing(Asc("-")) = "MT" & Format(Asc("-"), "0000") 'ASC_- 45 ChrW(&H66F7)  ' - 間一旋
    kFing(Asc("=")) = "MT" & Format(Asc("="), "0000") 'ASC_= 61 ChrW(&H66F8)  ' = 間二旋
    'kFing(Asc("t")) = "MT" & Format(Asc("t"), "0000") 'ASC_t 116 ChrW(&H670B)  ' t 打圓 托勾
    kFing(Asc("w")) = "MT" & Format(Asc("w"), "0000") 'ASC_w 119 ChrW(&H670B)  ' w 柔音
    kFing(Asc("@")) = "MT" & Format(Asc("@"), "0000") 'ASC_w 119 ChrW(&H670B)  '
    
    
    kTowFing(Asc("z")) = "MT" & Format(Asc("z"), "0000") 'ASC_z 122 ChrW(&H6416)  ' z 大指
    kTowFing(Asc("x")) = "MT" & Format(Asc("x"), "0000") 'ASC_x 120 ChrW(&H641A)  ' x 食指
    kTowFing(Asc("c")) = "MT" & Format(Asc("c"), "0000") 'ASC_c 99 ChrW(&H641C)  ' c 中指
    kTowFing(Asc("v")) = "MT" & Format(Asc("v"), "0000") 'ASC_v 118 ChrW(&H641F)  ' v 無名指
    kTowFing(Asc("a")) = "MT" & Format(Asc("a"), "0000") 'ASC_a 97 ChrW(&H6421)  ' a 八度
    kTowFing(Asc("s")) = "MT" & Format(Asc("s"), "0000") 'ASC_s 115 ChrW(&H66FC)  ' s 王字指法
    kTowFing(Asc("d")) = "MT" & Format(Asc("d"), "0000") 'ASC_d 100 ChrW(&H6700)  ' d 搖指
    'kTowFing(Asc("p")) = "MT" & Format(Asc("p"), "0000") 'ASC_p 112 ChrW(&H6381)  ' p 卜指法
    kTowFing(Asc("Z")) = "MT" & Format(Asc("Z"), "0000") 'ASC_Z 90 ChrW(&H6418)  ' 大寫Z 反大指法
    kTowFing(Asc("A")) = "MT" & Format(Asc("A"), "0000") 'ASC_A 65 ChrW(&H6413)  ' 大寫A 反八度
    kTowFing(Asc("-")) = "MT" & Format(Asc("-"), "0000") 'ASC_- 45 ChrW(&H66F7)  ' - 間一旋
    kTowFing(Asc("=")) = "MT" & Format(Asc("="), "0000") 'ASC_= 61 ChrW(&H66F8)  ' = 間二旋
    kTowFing(Asc("t")) = "MT" & Format(Asc("t"), "0000") 'ASC_t 116 ChrW(&H670B)  ' t 打圓 托勾
    kTowFing(Asc("w")) = "MT" & Format(Asc("w"), "0000") 'ASC_w 119 ChrW(&H670B)  ' w 柔音
    kTowFing(Asc("m")) = "MT" & Format(Asc("m"), "0000") 'ASC_w 119 ChrW(&H670B)  '
    kTowFing(Asc("e")) = "MT" & Format(Asc("e"), "0000") 'ASC_w 119 ChrW(&H670B)  '
    kTowFing(Asc("r")) = "MT" & Format(Asc("r"), "0000") 'ASC_w 119 ChrW(&H670B)  '
    kTowFing(Asc("k")) = "MT" & Format(Asc("k"), "0000") 'ASC_w 119 ChrW(&H670B)  '
    kTowFing(Asc("n")) = "MT" & Format(Asc("n"), "0000") 'ASC_t 116 ChrW(&H670B)  ' n 按音
    kTowFing(Asc("f")) = "MT" & Format(Asc("f"), "0000") 'ASC_t 116 ChrW(&H670B)  ' f 吟音
    
    '要上下移多少
    Dim ip As Integer
    For ip = 0 To 255
        Set posFing(ip) = New point
        Set posTowFing(ip) = New point
        
    Next
    
    posFing(Asc("z")).c -0.363, 1.57, 0 ' z 大指
    posFing(Asc("x")).c -0.363, 1.65, 0 ' x 食指
    posFing(Asc("c")).c -0.363, 1.57, 0 ' c 中指
    posFing(Asc("v")).c -0.363, 1.57, 0 ' v 無名指
    posFing(Asc("a")).c -0.363, 1.57, 0 ' a 八度
    posFing(Asc("s")).c -0.363, 1.57, 0 ' s 王字指法
    posFing(Asc("d")).c -0.363, -0.85, 0 ' d 搖指
    posFing(Asc("p")).c -0.363, -0.01, 0 ' p 卜指法
    posFing(Asc("Z")).c -0.363, 1.57, 0 ' 大寫Z 反大指法
    posFing(Asc("A")).c -0.363, 1.57, 0 ' 大寫A 反八度
    posFing(Asc("-")).c -0.363, 1.57, 0 ' - 間一旋
    posFing(Asc("=")).c -0.363, 1.57, 0 ' = 間二旋
    posFing(Asc("t")).c -0.363, 1.6, 0 ' t 打圓 托勾
    posFing(Asc("@")).c -0.363, 1.57, 0 ' w
    
    
    posTowFing(Asc("z")).c -0.363, -0.7, 0 ' z 大指
    posTowFing(Asc("x")).c -0.363, -0.7, 0 ' x 食指
    posTowFing(Asc("c")).c -0.363, -0.7, 0 ' c 中指
    posTowFing(Asc("v")).c -0.363, -0.7, 0 ' v 無名指
    posTowFing(Asc("a")).c -0.363, -0.7, 0 ' a 八度
    posTowFing(Asc("s")).c -0.363, -0.7, 0 ' s 王字指法
    'posTowFing(Asc("d")).c -0.363, -0.85, 0 ' d 搖指
    'posTowFing(Asc("p")).c -0.363, -0.01, 0 ' p 卜指法
    posTowFing(Asc("Z")).c -0.363, -0.7, 0 ' 大寫Z 反大指法
    posTowFing(Asc("A")).c -0.363, -0.7, 0 ' 大寫A 反八度
    posTowFing(Asc("-")).c -0.363, -0.7, 0 ' - 間一旋
    posTowFing(Asc("=")).c -0.363, -0.7, 0 ' = 間二旋
    posTowFing(Asc("t")).c -0.363, -0.7, 0 ' t 打圓 托勾
    posTowFing(Asc("w")).c -0.363, -0.7, 0 ' m
    posTowFing(Asc("m")).c -0.363, -0.7, 0 ' w
    posTowFing(Asc("e")).c -0.363, -0.7, 0 ' w
    posTowFing(Asc("r")).c -0.363, -0.7, 0 ' w
    posTowFing(Asc("k")).c -0.363, -0.7, 0 ' w
    posTowFing(Asc("n")).c -0.363, -0.7, 0 ' w
    posTowFing(Asc("f")).c -0.363, -0.7, 0 ' w
    
    
End Sub

Attribute VB_Name = "PointList"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Dim pntList() As point
Dim mSize As Long
Dim mLogSize As Long
Sub clean()
    mSize = 0
End Sub
Function size() As Long
    size = mSize
End Function
Function list() As Double()
    If mSize <= 0 Then
        Exit Function
    End If

    Dim tmplist() As Double
    ReDim tmplist(0 To (mSize * 3) - 1)
    Dim i As Long
    For i = 0 To mSize - 1
        tmplist(i * 3) = pntList(i).x
        tmplist(i * 3 + 1) = pntList(i).Y
        tmplist(i * 3 + 2) = pntList(i).z
    Next
    list = tmplist
End Function
Function at(ln As Long) As point
    Dim item  As New point
    If ln < mSize Then
        Set item = pntList(ln)
    Else
        Set item = New point
    End If
    Set at = item
End Function

Sub add(xi As Variant, yi As Variant, zi As Variant)
    If UBound(pntList) < mSize + 1 Then
        '陣列不夠，在延伸
        ReDim Preserve pntList(UBound(pntList) + 100)
    End If
    
    Set pntList(mSize) = New point
    pntList(mSize).x = xi
    pntList(mSize).Y = yi
    pntList(mSize).z = zi
    mSize = mSize + 1
    
End Sub

Sub addpt(Pnt As point)

    If UBound(pntList) < mSize + 1 Then
        '陣列不夠，在延伸
        ReDim Preserve pntList(UBound(pntList) + 100)
    End If
    
    Set pntList(mSize) = New point
    Set pntList(mSize) = Pnt
    mSize = mSize + 1
    
End Sub

Private Sub Class_Initialize()
    ReDim pntList(8)
End Sub

Attribute VB_Name = "TestDll_Print"
Attribute VB_Base = "0{1A211BC4-FE8B-4A19-BF55-1ECA99AEA6F1}{C7B86FD9-0F88-4D7F-A3E3-B5E5E7320B13}"
Attribute VB_GlobalNameSpace = False
Attribute VB_Creatable = False
Attribute VB_PredeclaredId = True
Attribute VB_Exposed = False
Attribute VB_TemplateDerived = False
Attribute VB_Customizable = False
Option Explicit

Private Sub CommandButton1_Click()
    Dim inss As INS_Object
    Dim ii As Double
    Dim hWnd As Long
    Set inss = New INS_Object
    ii = inss.AddLine(33, 99, 77, 44)
    hWnd = GetActiveWindow
    MsgBox "VBA is GetActiveWindow  : " & hWnd
    
    inss.aPaint hWnd
    
    
End Sub

Private Sub CommandButton2_Click()
    On Error Resume Next
    Dim oApp As Object  ' AcadApplication
    ' Try to connect to a running instance of AutoCAD.
    
    Set oApp = GetObject(, "AutoCAD.Application")
    If Err Then
        ' Failed to get AutoCAD.
        MsgBox ("Could not connect to AutoCAD.")
        Err.clear
        Exit Sub
    End If
     
    
    Dim myCom As myCustomCom
    Dim vvv As Variant
    'myCom = oApp.GetInterfaceObject("comArxProject1Lib.myCustomCom1")
    
    Set myCom = New myCustomCom
    Dim x As Single
    Dim Y As Single
    Dim z As Single
    Call myCom.getPosition(x, Y, z)
    myCom.addMuiscText
    MsgBox x & ":" & Y & ":" & z & ":"
  
End Sub
'Imports asdkcomServerFromArxLib
'Imports Autodesk.AutoCAD.Interop
'Imports System.Windows.Forms
'Public Class Form1
'
'Private Sub Button1_Click(ByVal sender As System.Object, ByVal e As System.EventArgs) Handles Button1.Click
'Dim oApp As AcadApplication
'' Try to connect to a running instance of AutoCAD.
'Try
'oApp = GetObject(, "AutoCAD.Application")
'' Failed to get AutoCAD.
'MsgBox ("Could not connect to AutoCAD.")
'Exit Sub
'
'
'End Try
'
'Dim myCom As myCustomCom
'myCom = oApp.GetInterfaceObject("comServerFromArx.myCustomCom")
'
'Dim x As Single
'Dim y As Single
'Dim z As Single
'myCom.getPosition(x, y, z)
'MessageBox.Show ("(" + x.ToString() + "," + y.ToString() + "," + z.ToString() + ")")
'End Sub
'End Class
'
Private Sub CommandButton3_Click()

    Dim returnObj As Object
    Dim basePnt As Variant
    Dim i As Integer
    Dim j As Integer
  
    Dim SEOBJ As SmileyEntity
    
    ThisDrawing.Utility.GetEntity returnObj, basePnt, "選擇要插入有屬性的圖元："
    
    returnObj.Center = basePnt
End Sub

Private Sub CommandButton4_Click()
    
    Dim SEOBJ As SmileyEntity
    Dim basePnt(0 To 2) As Double
    Dim cenPnt(0 To 2) As Double
    Dim returnPnt As Variant
    Dim rad As Integer
    
    Me.Hide
    returnPnt = ThisDrawing.Utility.GetPoint(basePnt, "\n選擇要插入的點")
    

    'Set SEOBJ = New SmileyEntity
    Dim SSS As New SmileyApplication
    Dim ss As SmileyUi.SmileyApplication
    
    Set SEOBJ = ThisDrawing.ModelSpace.AddCustomObject("ASDKSMILEY")
    Call SEOBJ.setNewObject(returnPnt, 255)
    
    'sss.CreateSmiley
    
    'Dim aaa As Variant
    'aaa = SEOBJ.MouthCenter
    Me.Show
End Sub

Attribute VB_Name = "TextToMusic"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Dim mHowData As Integer      '有多少行資料
Dim mChar As String          '資料的前面字元有那些
Dim mCharI() As Integer
Dim mMete As Integer        '每小節有幾拍
Dim mFontSize As Integer
Dim mTextNote() As String       '把每行資料放進來 這是有陣列的
Dim mmsa(0 To 1) As String

Dim i As Integer
Dim j As Integer
Private Type KeyFormat
        mfingering As String  '指法
        mnote As String           '高低音
        mscale As String          '音階
        mtempo As String         '拍子
        mfPosition As Double    '這是看這字上下移多少
        mnPosition As Double    '這是看這字上下移多少
        msPosition As Double     '這是看這字上下移多少
        mtPosition As Double    '這是看這字上下移多少
End Type

Dim mMusic() As KeyFormat                '了解嗎
Public Sub setLineChar(Char As String, Mete As Integer)
    'Char 設定資料的前面字元有那些
    'Mete 每小節有幾拍
    mChar = Char
    mMete = Mete
    ReDim mCharI(Len(mChar))
    mHowData = Len(mChar)
    ReDim mTextNote(mHowData + 1)    ' 陳述式將重新調整陣列的大小，且將所有元素內容清除。
                                     ' 因為它從 0 開始 所以要加 1
End Sub

Public Sub setFontSize(FontSize As Integer)
    mFontSize = FontSize
End Sub

Public Sub TextToMusic()
    Dim kNUM1 As String, kNUM2 As String, kNUM3 As String, kNUM4 As String
    Dim kNUM5 As String, kNUM6 As String, kNUM7 As String, kNUM0 As String
    Dim k延長一拍 As String
    Dim kLIN1 As String: Dim kLIN2 As String: Dim kLIN3 As String
    Dim kUP1 As String
    Dim kUP2 As String
    Dim kDOW1 As String
    Dim kDOW2 As String
    Dim kAdot As String
    Dim kBarLine As String
    Dim kFing(30 To 255) As String
    Dim posLinDown As Variant
    Dim posFing(0 To 255) As Integer
    Const MAX200 As Integer = 200
    posLinDown = Array(0, 12, 26, 40)   '這是看低音下點要移多少下去，是當200字型時計算
    
    kNUM1 = ChrW(&H4E52)
    kNUM2 = ChrW(&H4E53)
    kNUM3 = ChrW(&H4E56)
    kNUM4 = ChrW(&H4E58)
    kNUM5 = ChrW(&H4E59)
    kNUM6 = ChrW(&H4E5C)
    kNUM7 = ChrW(&H4E5D)
    kNUM0 = ChrW(&H5D4C)
    k延長一拍 = ChrW(&H5D1F)
    kLIN1 = ChrW(&H5D39): kLIN2 = ChrW(&H5D3A): kLIN3 = ChrW(&H5D3C)
    kUP1 = ChrW(&H66E0): kUP2 = ChrW(&H66E3): kDOW1 = ChrW(&H66E6): kDOW2 = ChrW(&H66E8)
    kAdot = ChrW(&H5D3D)            '符點音符
    kBarLine = ChrW(&H601D)
    kFing(Asc("z")) = ChrW(&H6416)  ' z 大指
    kFing(Asc("x")) = ChrW(&H641A)  ' x 食指
    kFing(Asc("c")) = ChrW(&H641C)  ' c 中指
    kFing(Asc("v")) = ChrW(&H641F)  ' v 無名指
    kFing(Asc("a")) = ChrW(&H6421)  ' a 八度
    kFing(Asc("s")) = ChrW(&H66FC)  ' s 王字指法
    kFing(Asc("d")) = ChrW(&H6700)  ' d 搖指
    kFing(Asc("p")) = ChrW(&H6381)  ' p 卜指法
    kFing(Asc("Z")) = ChrW(&H6418)  ' 大寫Z 反大指法
    kFing(Asc("A")) = ChrW(&H6413)  ' 大寫A 反八度
    kFing(Asc("-")) = ChrW(&H66F7)  ' - 間一旋
    kFing(Asc("=")) = ChrW(&H66F8)  ' = 間二旋
    kFing(Asc("t")) = ChrW(&H670B)  ' t 打圓 托勾
    
    posFing(Asc("z")) = 157  ' z 大指
    posFing(Asc("x")) = 165  ' x 食指
    posFing(Asc("c")) = 157  ' c 中指
    posFing(Asc("v")) = 157  ' v 無名指
    posFing(Asc("a")) = 157  ' a 八度
    posFing(Asc("s")) = 157  ' s 王字指法
    posFing(Asc("d")) = 0  ' d 搖指
    posFing(Asc("p")) = -10  ' p 卜指法
    posFing(Asc("Z")) = 157  ' 大寫Z 反大指法
    posFing(Asc("A")) = 157  ' 大寫A 反八度
    posFing(Asc("-")) = 157  ' - 間一旋
    posFing(Asc("=")) = 157  ' = 間二旋
    posFing(Asc("t")) = 160  ' t 打圓 托勾

    
    Dim c() As String
    ReDim c(Len(mChar))
    ReDim mMusic(Len(mTextNote(MkDoc.iNote)) * 2)
    Dim lsup As Integer
    Dim pos As Integer
    pos = 1
    Call atImputer(mMete)  '這是要加入小節線 ,排拍子
    For i = 1 To Len(mTextNote(MkDoc.iNote))  ' 迴圈每個字
        For j = 1 To Len(mChar)
            c(j) = Mid(mTextNote(j), i, 1)
        Next j
        
        Select Case c(MkDoc.iFinge)     '這是指法
            Case "a" To "z", "A" To "Z", "-", "="
                mMusic(pos).mfingering = kFing(Asc(LCase(c(MkDoc.iFinge))))
                mMusic(pos).mfPosition = posFing(Asc(LCase(c(MkDoc.iFinge)))) _
                                        * mFontSize / MAX200
            Case " "
            Case "("
            Case "|"
            Case Else
                mMusic(pos).mfingering = c(MkDoc.iFinge)
        End Select
        
        lsup = 0
        Select Case c(MkDoc.iTempo)     '這是拍子
            Case " "
            Case "-", "2"
                lsup = 1
                mMusic(pos).mtempo = kLIN1
            Case "=", "4", "3"
                lsup = 2
                mMusic(pos).mtempo = kLIN2
            Case "6", "8", "A"
                lsup = 3
                mMusic(pos).mtempo = kLIN3
            Case "|"
            Case Else
                mMusic(pos).mtempo = c(MkDoc.iTempo)
        End Select
        
                
        Select Case c(MkDoc.iScale)     '這是 八度音
            Case " "
            Case "."        '上一點
                mMusic(pos).mscale = kUP1
                mMusic(pos).msPosition = 0
            Case ":"        '上二點
                mMusic(pos).mscale = kUP2
                mMusic(pos).msPosition = 0
            Case ","        '下一點
                mMusic(pos).mscale = kDOW1
                mMusic(pos).msPosition = -mFontSize * posLinDown(lsup) / MAX200   '這是下移的指令
            Case ";"        '上二點
                mMusic(pos).mscale = kDOW2
                mMusic(pos).msPosition = -mFontSize * posLinDown(lsup) / MAX200   '這是下移的指令
            Case "|"
            Case Else
                mMusic(pos).mscale = c(MkDoc.iScale)
        End Select
        
        
        Select Case c(MkDoc.iNote)     '這是音階
            Case "0"
                mMusic(pos).mnote = kNUM0
            Case "1"
                mMusic(pos).mnote = kNUM1
            Case "2"
                mMusic(pos).mnote = kNUM2
            Case "3"
                mMusic(pos).mnote = kNUM3
            Case "4"
                mMusic(pos).mnote = kNUM4
            Case "5"
                mMusic(pos).mnote = kNUM5
            Case "6"
                mMusic(pos).mnote = kNUM6
            Case "7"
                mMusic(pos).mnote = kNUM7
            Case "."
                mMusic(pos).mnote = kAdot
            Case "-"
                mMusic(pos).mnote = k延長一拍
            Case "|"
                mMusic(pos).mnote = "|"
            Case Else
                mMusic(pos).mnote = c(MkDoc.iNote)
                
        End Select

        pos = pos + 1
    Next i
    mMusic(0).mnote = pos
    
End Sub
Private Sub atImputer(iMete As Integer)
    '排成有小節線的文字
    'iMete 每小節裡有幾拍
    Dim testTXT() As String
    ReDim testTXT(Len(Me.TextNote(MkDoc.iNote)))
    Dim c() As String
    ReDim c(Len(mChar))
    
    Dim i As Integer
    Dim j As Integer
    Dim num As Integer
    Dim nownum As Integer
    Dim chackFor As Boolean
    Const A_TEMPO As Integer = 240  '一拍的數值
    
    For i = 1 To Len(mTextNote(MkDoc.iNote))  ' 迴圈每個字
        For j = 1 To Len(mChar)
            c(j) = Mid(mTextNote(j), i, 1)
        Next j
        
        If num >= A_TEMPO * iMete Then
            If c(MkDoc.iNote) <> "|" Then
                num = 0
                For j = 1 To Len(mChar)
                    testTXT(j) = testTXT(j) & "|"
                Next j
            End If
        End If
        
        Select Case c(MkDoc.iNote)
            Case "|":
                num = 0
                nownum = 0
                chackFor = True
            Case "-":
                nownum = A_TEMPO
                chackFor = True
            Case ".":
                nownum = nownum / 2
                chackFor = True
                
            Case " ":
            Case Else:
                Select Case c(MkDoc.iTempo)
                    Case " ", "":
                        nownum = A_TEMPO
                    Case "-", "2":
                        nownum = A_TEMPO / 2
                    Case "=", "4":
                        nownum = A_TEMPO / 4
                    Case "3":
                        nownum = A_TEMPO / 3
                    Case "6":
                        nownum = A_TEMPO / 6
                    Case "8":
                        nownum = A_TEMPO / 8
                    Case "a":
                        nownum = A_TEMPO / 10
                    Case "":
                        
                End Select
                
                chackFor = True
            
        End Select
        If chackFor = True Then
            For j = 1 To Len(mChar)
                If c(j) = "" Then
                    testTXT(j) = testTXT(j) & " "
                Else
                    testTXT(j) = testTXT(j) & c(j)
                End If
            Next j
        End If
        chackFor = False
        num = num + nownum
        
    Next i
    
    For j = 1 To Len(mChar)
        mTextNote(j) = testTXT(j)
    Next j
End Sub
Private Function intComp(myInt1 As Integer, myInt2 As Integer) As Integer
    '比較數值
    '傳回值 = 較大的數值
    If myInt1 >= myInt2 Then
        intComp = myInt1
    Else
        intComp = myInt2
    End If
End Function
Private Sub mTextNoteLenAdd()
    '這函式是要 mTextNote(?) 中的每個長度一樣，不一樣補空白
    Dim x As Integer
    Dim str As String
    Dim BigInt As Integer
    BigInt = 0
    For x = 1 To mHowData
        BigInt = intComp(BigInt, Len(mTextNote(x)))
    Next
    If BigInt <> 0 Then
        
        For x = 1 To mHowData
            str = space(BigInt)
            LSet str = mTextNote(x)
            mTextNote(x) = str
        Next
    
    End If
End Sub

Public Sub setSaveString(tObject As String)
    '這是看進來什麼格式的資料 要放在 mTextNote 的第幾個
    Dim c As String     '記現在是什麼格式的資料
    Static cl As String    '記前一個是什麼格式的資料
    Static num As Integer   ' 記錄著一樣格式的標記 看以經有幾個了 如 |||||
    c = Mid(tObject, 1, 1)
    For i = 1 To mHowData
        If c = Mid(mChar, i, 1) Then
            If i = 1 Then
                ReDim mCharI(Len(mChar))
                Call mTextNoteLenAdd    '這函式是要 mTextNote(?) 中的每個長度一樣，不一樣補空白
            End If
            If mCharI(i) <> 1 Then
                mTextNote(i) = mTextNote(i) + tObject
                mCharI(i) = 1
                Exit For
            End If
        End If
    Next i
    
   
End Sub

Public Property Get TextNote(ii As Integer) As String
    TextNote = mTextNote(ii)
End Property

Public Sub Show()
    Dim ccc As String
    For i = 1 To mHowData
        ccc = ccc + vbCrLf
        ccc = ccc + Mid(mChar, i, 1)
    Next i
    MsgBox "有 " & mHowData & " 個資料   資料的格式是" & ccc
End Sub

Public Sub ShowData()
    Dim ccc As String
    
    For i = 1 To mHowData
        ccc = ccc + vbCrLf
        ccc = ccc & mTextNote(i)
    Next i
    MsgBox " 全部資料的 內容是" & ccc

End Sub
Public Function getMFingering(ii As Integer) As String
    getMFingering = mMusic(ii).mfingering
End Function
Public Function getMNote(ii As Integer) As String
    getMNote = mMusic(ii).mnote
End Function
Public Function getMScale(ii As Integer) As String
    getMScale = mMusic(ii).mscale
End Function
Public Function getMTempo(ii As Integer) As String
    getMTempo = mMusic(ii).mtempo
End Function
Public Function getMScalePosition(ii As Integer) As Double
    getMScalePosition = mMusic(ii).msPosition
End Function
Public Function getMFingPosition(ii As Integer) As Double
    getMFingPosition = mMusic(ii).mfPosition
End Function

Public Function getSaveString(ii As Integer) As String
    getSaveString = mTextNote(ii)
End Function

Attribute VB_Name = "ThisDrawing"
Attribute VB_Base = "0{6A221957-2D85-42A7-8E19-BE33950D1DEB}"
Attribute VB_GlobalNameSpace = False
Attribute VB_Creatable = False
Attribute VB_PredeclaredId = True
Attribute VB_Exposed = True
Attribute VB_TemplateDerived = False
Attribute VB_Customizable = True
Option Explicit
Sub sq()
    MsgBox square(21)
End Sub
Sub AllLineAdd()
'計算線的總長度
' Have the user enter a point

    
    ' Create the selection set
    Dim ssetObj As AcadSelectionSet
    'Set ssetObj = ThisDrawing.SelectionSets.Add("TEST_SSET")
    If ThisDrawing.SelectionSets.count = 0 Then
        Set ssetObj = ThisDrawing.SelectionSets.add("TEST_SSET")
    Else
        Set ssetObj = ThisDrawing.SelectionSets.item(0)
        ssetObj.clear
    
    End If
    
    ' Add objects to a selection set by prompting user to select on the screen
    ssetObj.SelectOnScreen
    ssetObj.item (0)
    
    Dim returnPnt As Variant
    Dim str As String
    Dim strAll As String
    Dim i As Integer
    Dim ina As Integer
    Dim counta As Integer
    Dim obj As AcadLine
    Dim allLine As Double
    counta = ssetObj.count()
    
    
    ' Return a point using a prompt
    ' Translate the point into UCS coordinates
    allLine = 0
    For i = 0 To counta - 1
        Set obj = ssetObj.item(i)
        allLine = allLine + obj.Length
    Next
    

    
    ThisDrawing.Utility.prompt ("Line all length= " & allLine)

End Sub
Sub InsText()
    'frmInsText.Show 0
    frmInsText.Show
End Sub

Sub MM()
    TestDll_Print.Show 1
End Sub
Sub frmMusic()
    frmMusical.Show 1
End Sub
Sub frmMusicEdit()
    frmEDIT.Show 1
End Sub
Sub easeMusicJoin()
'清除 MusicText 的鏈結
On Error Resume Next
    Dim ent As Object

   
    Dim SSetColl As AcadSelectionSets
    Set SSetColl = ThisDrawing.SelectionSets
    
    ' Create a SelectionSet named "TEST" in the current drawing
    Dim ssetObj As AcadSelectionSet
  
    If SSetColl.count > 0 Then
        SSetColl.item(0).Delete
    End If
    Set ssetObj = SSetColl.add("TEST")
    ssetObj.SelectOnScreen
    
    '排序陣列
    Dim TheArray As Variant
    Dim TheArrayEnt As Variant
    Dim coI As Integer
    Dim i As Long
    
    ' Add the dimstyle to the dimstyles collection
    coI = 0
  ' 找出圖面中的每一個選集
    For Each ent In ssetObj
        If (ent.ObjectName = "MusicText") Then
            ent.RightLink = 0
            ent.LeftLink = 0
            ent.data = "b=!3=c"
            MsgBox ent.data
        End If
    Next
End Sub
Sub addMusicJoin()
'取得物件 MusicText
'用x 軸來鏈結
On Error Resume Next

    Dim ent As Object

   
    Dim SSetColl As AcadSelectionSets
    Set SSetColl = ThisDrawing.SelectionSets
    
    ' Create a SelectionSet named "TEST" in the current drawing
    Dim ssetObj As AcadSelectionSet
  
    If SSetColl.count > 0 Then
        SSetColl.item(0).Delete
    End If
    Set ssetObj = SSetColl.add("TEST")
    ssetObj.SelectOnScreen
    
    '排序陣列
    Dim TheArray As Variant
    Dim TheArrayEnt As Variant
    Dim coI As Integer
    Dim i As Long
    
    ' Add the dimstyle to the dimstyles collection
    coI = 0
  ' 找出圖面中的每一個選集
    For Each ent In ssetObj
        If (ent.ObjectName = "AsdkSmiley") Then
            coI = coI + 1
        End If
    Next
    ReDim TheArray(coI - 1)
    ReDim TheArrayEnt(coI - 1)
    
    coI = 0
    Dim MTobj As SmileyEntity
    Dim pt As Variant
    For Each ent In ssetObj
        If (ent.ObjectName = "AsdkSmiley") Then
            pt = ent.insertionPoint()
            TheArray(coI) = pt(0)
            Set TheArrayEnt(coI) = ent
            coI = coI + 1
        End If
    Next
    
    
    '只有一個，不用排序了
    If UBound(TheArray) = 1 Then
        Exit Sub
    End If
    
    '排序開始
    SelectionSortMaxTow TheArray, TheArrayEnt
    
    For i = 0 To UBound(TheArray)
        If i = 0 Then
            TheArrayEnt(i).LeftLink = 0
            TheArrayEnt(i).RightLink = TheArrayEnt(i + 1).ObjectID
        ElseIf i = UBound(TheArray) Then
            TheArrayEnt(i).LeftLink = TheArrayEnt(i - 1).ObjectID
            TheArrayEnt(i).RightLink = 0
        Else
            TheArrayEnt(i).RightLink = TheArrayEnt(i + 1).ObjectID
        End If
    Next
      
End Sub




Sub asdfqwe()
    Dim aas As AcadDatabase
    'Set aas = New Aprint.INS_Object
    Dim SEOBJ As SmileyEntity
    Dim entObj As AcadObject
    Dim basePnt(0 To 2) As Double
    
    ThisDrawing.Utility.GetEntity entObj, basePnt, "\n請選擇要修改的物件"
    If (entObj.ObjectName = "AsdkSmiley") Then
        Set SEOBJ = entObj
        Call SEOBJ.setData(SEOBJ.insertionPoint(), "b !5=z", "MMP2005", 44)
    End If
    'Call aas.AddLine(234, 11, 33, 55)
End Sub

Sub linkRight()
    Dim SEOBJ As SmileyEntity
    Dim basePnt(0 To 2) As Double
    Dim cenPnt(0 To 2) As Double
    Dim returnPnt As Variant
    Dim rad As Integer
    
    returnPnt = ThisDrawing.Utility.GetPoint(basePnt, "\n選擇要插入的點")
    

    'Set SEOBJ = New SmileyEntity
    Dim SSS As New SmileyApplication
    Dim ss As SmileyUi.SmileyApplication
    
    Set SEOBJ = ThisDrawing.ModelSpace.AddCustomObject("ASDKSMILEY")
    Call SEOBJ.setNewObject(returnPnt, 1)
    Call SEOBJ.setData(returnPnt, "#f?2=m", "MMP2005", 44)
    
    Dim entObj As AcadObject
    ThisDrawing.Utility.GetEntity entObj, basePnt, "\n請選擇要鏈結的物件"
    SEOBJ.RightLink = entObj.ObjectID
    
    MsgBox Hex(SEOBJ.RightLink)
End Sub

Sub getlinkRight()
    Dim SEOBJ As SmileyEntity
    Dim basePnt(0 To 2) As Double
    Dim cenPnt(0 To 2) As Double
    Dim returnPnt As Variant
    Dim rad As Integer


    Dim entObj As AcadObject
goUP:
    ThisDrawing.Utility.GetEntity entObj, basePnt, "\n請選擇要鏈結的物件"
    Set SEOBJ = entObj
    MsgBox SEOBJ.ObjectID
    
    MsgBox "這物件的 id- " & Hex(SEOBJ.ObjectID) & vbCrLf & _
        " LeftLink 的id- " & Hex(SEOBJ.LeftLink) & vbCrLf & _
        " RightLink 的id- " & Hex(SEOBJ.RightLink)
    GoTo goUP
End Sub

Sub aa()
    Dim moda As Integer
    mymode = 0
    
    Dim x, Y, z As Double
    Dim ret As Integer
    
    ret = getPT(x, Y, z)
    
    Dim abc As AcadEntity
    Dim pt As Variant
    ThisDrawing.ActiveSelectionSet.SelectOnScreen
    
    Dim oldpt As Variant
    Dim newpt(2) As Double
    oldpt = ThisDrawing.Utility.GetPoint(, "\n指定移?起?: ")
    
    Dim mylne As AcadLine
    ret = getPT(x, Y, z)
    Dim startPt(2) As Double
    Dim endPt(2) As Double
    
    endPt(0) = x: endPt(1) = Y: endPt(2) = z
    Set mylne = ThisDrawing.ModelSpace.AddLine(oldpt, endPt)
    Dim tmp(0) As Double
    
    Do While ret = 1
    
    ret = getPT(x, Y, z)
    newpt(0) = x: newpt(1) = Y: newpt(2) = z
    mylne.EndPoint = newpt
    For Each ent In ThisDrawing.ActiveSelectionSet
    ent.Move oldpt, newpt

Next
oldpt(0) = newpt(0): oldpt(1) = newpt(1): oldpt(2) = newpt(2)
Loop
mylne.Delete
End Sub



Option Explicit


''設置指定詞典擴展記錄
'
Public Function Dhvb_SetXrecord(objDict As AcadDictionary, _
        XRecordName As String, _
        XRecordData As Variant) _
        As AcadXRecord
        
    Dim objXRecord As AcadXRecord
    Dim XRecordType As Variant
    Dim i As Long
    '檢察對象詞典是否有該名擴展記錄,如果已經存在則刪除
    On Error Resume Next
    Set objXRecord = objDict.GetObject(XRecordName)
    If Not objXRecord Is Nothing Then
        objDict.Remove XRecordName
    End If
    On Error GoTo 0
        '建立擴展記錄數據
    ReDim XRecordType(0 To UBound(XRecordData)) As Integer
    
    For i = 0 To UBound(XRecordData)
        Select Case VarType(XRecordData(i))
        Case vbInteger, vbLong
            XRecordType(i) = 90    '整數組碼=90
        Case vbSingle, vbDouble
            XRecordType(i) = 40    '實數組碼=40
        Case vbString
            XRecordType(i) = 2    '字符組碼=2
        End Select
    Next    '添加擴展記錄到對象詞典
    Set objXRecord = objDict.AddXRecord(XRecordName)
    objXRecord.SetXRecordData XRecordType, XRecordData    '返回擴展記錄對象
    Set Dhvb_SetXrecord = objXRecord
End Function

Sub Test()
' 創建直線
    Dim lineObj As AcadLine
    Dim startPt(0 To 2) As Double, endPt(0 To 2) As Double
    startPt(0) = 1#: startPt(1) = 1#: startPt(2) = 0#
    endPt(0) = 5#: endPt(1) = 5#: endPt(2) = 0#
    Set lineObj = ThisDrawing.ModelSpace.AddLine(startPt, endPt)
    ' 創建擴展數據
    Dim DataType(0 To 1) As Integer
    Dim data(0 To 1) As Variant
    Dim reals3(0 To 2) As Double
    Dim worldPos(0 To 2) As Double
    DataType(0) = 1001: data(0) = "Test_Application" '應用程序名
    DataType(1) = 1000: data(1) = "This is a test for xdata" '字符串類型
    lineObj.SetXData DataType, data '設置擴展數據
    ' 返回直線的擴展數據
    Dim xdataOut As Variant
    Dim xtypeOut As Variant
    lineObj.GetXData "Test_Application", xtypeOut, xdataOut
    
    
    
    
End Sub


'以下是一些在開發人員手冊中的關於擴展數據的示例。
'將擴展數據指定給選擇集中的所有對象
'本例提示用戶選擇圖形中的對象，然後將選定的對象置於選擇集中，並且指定的擴展數據將附著到該選擇集中的所有對象。
Sub Ch10_AttachXDataToSelectionSetObjects()
   'On Error Resume Next
    ' 創建選擇集
    
    Dim sset As AcadSelectionSet
    Dim i As Integer
    'sset.Item(1).Delete
    
    'For i = 0 To ThisDrawing.SelectionSets.Count - 1
        ThisDrawing.SelectionSets.item("SS1").Delete
    'Next
    Set sset = ThisDrawing.SelectionSets.add("SS1")
    
    ' 提示用戶選擇對象
    sset.SelectOnScreen
    
    ' 定義擴展數據
    Dim appName As String, xdataStr As String
    
    appName = "MY_APP"
    xdataStr = "This is some xdata"
    
    Dim xDataType(0 To 2) As Integer
    Dim xData(0 To 2) As Variant
    
    ' 為每個數組定義值
    '1001 指示 appName
    xDataType(0) = 1001
    xData(0) = appName
    
    '1000 指示字符串值
    xDataType(1) = 1000
    xData(1) = xdataStr
    
    ' 遍歷選擇集中的所有圖元
    ' 將擴展數據設置和指定給每個圖元
    Dim ent As Object
    
    For Each ent In sset
        '1000 指示字符串值
        xDataType(2) = 1000
        xData(2) = ent.ObjectName
        
        ent.SetXData xDataType, xData
    Next ent

End Sub

'查看選擇集中所有對象的擴展數據
'本例顯示上例所附著的擴展數據。如果附著的擴展數據不是字符串（類型 1000）類型，則需要修改此代碼。
Sub Ch10_ViewXData()

    ' 查找上例中創建的選擇集
    
    Dim sset As Object
    Set sset = ThisDrawing.SelectionSets.item("SS1")
    
    ' 定義擴展數據變量以保存擴展數據信息
    
    Dim xDataType As Variant
    Dim xData As Variant
    Dim xd As Variant
    
    '定義索引計數器
    Dim xdi As Integer
    xdi = 0
    
    ' 遍歷選擇集中的對象
    ' 並檢索對象的擴展數據
    Dim msgstr As String
    Dim appName As String
    Dim ent As AcadEntity
    
    appName = "MY_APP"
    For Each ent In sset
        msgstr = ""
        xdi = 0
        
        ' 檢索 appName 擴展數據類型和值
        ent.GetXData appName, xDataType, xData
        ' 如果未初始化 xdataType 變量，
        ' 則沒有可供該圖元檢索的 appName 擴展數據
        If VarType(xDataType) <> vbEmpty Then
        
            For Each xd In xData
                msgstr = msgstr & vbCrLf & xDataType(xdi) _
                & ": " & xd
                xdi = xdi + 1
            Next xd

        End If
    
        ' 如果 msgstr 變量為 NULL，則沒有擴展數據
        
        If msgstr = "" Then msgstr = vbCrLf & "NONE"
        
        MsgBox appName & " xdata on " & ent.ObjectName & _
        ":" & vbCrLf & msgstr

    Next ent

End Sub

'選擇包含擴展數據的圓
'下例過濾包含由「MY_APP」應用程序添加的擴展數據的圓：
Sub Ch4_FilterXdata()
    'On Error Resume Next
    Dim sstext As AcadSelectionSet
    Dim mode As Integer
    Dim pointsArray(0 To 11) As Double
    
    mode = acSelectionSetWindowPolygon
    pointsArray(0) = -12#: pointsArray(1) = -7#: pointsArray(2) = 0
    pointsArray(3) = -12#: pointsArray(4) = 10#: pointsArray(5) = 0
    pointsArray(6) = 10#: pointsArray(7) = 10#: pointsArray(8) = 0
    pointsArray(9) = 10#: pointsArray(10) = -7#: pointsArray(11) = 0
    
    Dim FilterType(1) As Integer
    Dim FilterData(1) As Variant
    ThisDrawing.SelectionSets.item("SS9").Delete
    Set sstext = ThisDrawing.SelectionSets.add("SS9")

    FilterType(0) = 0
    FilterData(0) = "Circle"
    FilterType(1) = 1001
    FilterData(1) = "MY_APP"
    sstext.SelectByPolygon mode, pointsArray, FilterType, FilterData

End Sub


Sub Day15_1_FIX()
    
    Dim Rng As Object
    Dim strData
    
    Dim dvbPath As String
    Dim acadPath As String
    acadPath = ThisDrawing.Application.Path
    dvbPath = GetDVBThis("MusicalAprintf")
    
    '使用 Open 陳述式，配合Print寫入資料
    '使用&連接自訂的「相隔符號」，取代內建的功能
    
    Open "c:\temp\acad.lsp" For Output As #1
    
    Print #1, "(defun S::STARTUP ()"
    Print #1, "(command ""_vbaload"" "
    Print #1, """" & dvbPath & """"
    Print #1, ")"
    
    

    Print #1, acadPath
    Close #1
'(load "Lispfile1" "nLispfile1 not loaded")
'(load "Lispfile2" "nLispfile2 not loaded")
'(load "Lispfile3" "nLispfile3 not loaded")
    
End Sub
Public Function GetDVBThis(DVBFileName As String) As String
    Dim i As Integer
    Dim strFileName As String
    
    For i = 1 To ThisDrawing.Application.VBE.VBprojects.count
        strFileName = ThisDrawing.Application.VBE.VBprojects.item(i).FileName
        If InStr(UCase(strFileName), UCase(DVBFileName)) > 0 Then
            GetDVBThis = strFileName
            Exit For
        End If
    
    Next i

End Function
Public Function GetDVBPath(DVBFileName As String) As String
    Dim i As Integer
    Dim strFileName As String
    
    For i = 1 To ThisDrawing.Application.VBE.VBprojects.count
        strFileName = ThisDrawing.Application.VBE.VBprojects.item(i).FileName
        If InStr(UCase(strFileName), UCase(DVBFileName)) > 0 Then
            GetDVBPath = GetPath(strFileName)
            Exit For
        End If
    
    Next i

End Function
Function GetPath(strFileName As String) As String
    Dim CPath As String
    CPath = Left(strFileName, InStrRev(strFileName, "\") - 1)
    GetPath = CPath '< sure wish it was return, I like that better, this makes me think it is redefining the function
End Function

Private Sub AcadDocument_Activate()
    SetMusicTextToolsBar
    'Example_SetTools
    'Example_SetMusicTextTools
End Sub

Private Sub AcadDocument_BeginLisp(ByVal FirstLine As String)
    Dim ppt As New point
    Call ppt.c(4, 4, 0)
    Select Case FirstLine
        Case "(C:LL)"
            lineAndWline
        Case "(C:2L)"
            line2line
        Case "(C:L2)"
            line2
        Case "(C:ZZ)"
            Call donut(ppt, 0, 0.95)
        Case Else
    End Select


End Sub
Private Function donut(tcen As point, o1 As Double, o2 As Double) As AcadLWPolyline
'tcen 環的圓心
'o1 環的內徑
'o2 環的外徑
       '聚合線 畫弧
       Dim plineSlur As AcadLWPolyline
       Dim points(0 To 3) As Double
       Dim lenght As Double '環的距離
       Dim width As Double  '環的寬度
       Dim islurAddX As Integer
       Dim islurAddY As Integer
       lenght = (Abs(o1) + Abs(o2)) / 4
       width = Abs(o1 - o2) / 2
       ' Define the 2D polyline points
       points(0) = tcen.x - lenght
       points(1) = tcen.Y
       points(2) = tcen.x + lenght
       points(3) = tcen.Y
           
       ' Create a lightweight Polyline object in model space
       Set plineSlur = ThisDrawing.ModelSpace.AddLightWeightPolyline(points)

       ' Change the bulge of the third segment
       plineSlur.SetBulge 0, 1
       plineSlur.SetBulge 1, 1
       plineSlur.SetWidth 0, width, width
       plineSlur.SetWidth 1, width, width
       plineSlur.Closed = True
       
       
       
       plineSlur.Update
                                    
       Set donut = plineSlur
                    
End Function
Private Sub lineAndWline()
On Error Resume Next
    Dim ent As Object

   
    Dim SSetColl As AcadSelectionSets
    Set SSetColl = ThisDrawing.SelectionSets
    
    ' Create a SelectionSet named "TEST" in the current drawing
    Dim ssetObj As AcadSelectionSet
  
    If SSetColl.count > 0 Then
        SSetColl.item(0).Delete
    End If
    Set ssetObj = SSetColl.add("TEST")
    ssetObj.SelectOnScreen
    
    '排序陣列
    Dim TheArray As Variant
    Dim TheArrayEnt As Variant
    Dim coI As Integer
    Dim i As Long
    Dim oLine As AcadPolyline
    Dim startPt As New point
    Dim endPt As New point
    Dim ptlist As New PointList
    Dim retCoord As Variant


    ' Add the dimstyle to the dimstyles collection
    coI = 0
  ' 找出圖面中的每一個選集
    For Each ent In ssetObj
        If (ent.ObjectName = "AcDb2dPolyline") Then
            
            retCoord = ent.Coordinates
            startPt.x = retCoord(0): startPt.Y = retCoord(1): startPt.z = retCoord(2)
            endPt.x = retCoord(3): endPt.Y = retCoord(4): endPt.z = retCoord(5)
            startPt.x = startPt.x + 1
            endPt.x = endPt.x + 1
            ptlist.addpt startPt
            ptlist.addpt endPt
            Set oLine = ThisDrawing.ModelSpace.AddPolyline(ptlist.list)
            oLine.Layer = ent.Layer
            oLine.ConstantWidth = 0.6
            
        End If
    Next
End Sub
Private Sub line2line()
On Error Resume Next
    Dim ent As Object

   
    Dim SSetColl As AcadSelectionSets
    Set SSetColl = ThisDrawing.SelectionSets
    
    ' Create a SelectionSet named "TEST" in the current drawing
    Dim ssetObj As AcadSelectionSet
  
    If SSetColl.count > 0 Then
        SSetColl.item(0).Delete
    End If
    Set ssetObj = SSetColl.add("TEST")
    ssetObj.SelectOnScreen
    
    '排序陣列
    Dim TheArray As Variant
    Dim TheArrayEnt As Variant
    Dim coI As Integer
    Dim i As Long
    Dim oLine As AcadPolyline
    Dim startPt As New point
    Dim endPt As New point
    Dim ptlist As New PointList
    Dim retCoord As Variant
    Dim objDonut As AcadLWPolyline


    ' Add the dimstyle to the dimstyles collection
    coI = 0
  ' 找出圖面中的每一個選集
    For Each ent In ssetObj
        If (ent.ObjectName = "AcDb2dPolyline") Then
            
            retCoord = ent.Coordinates
            startPt.x = retCoord(0): startPt.Y = retCoord(1): startPt.z = retCoord(2)
            endPt.x = retCoord(3): endPt.Y = retCoord(4): endPt.z = retCoord(5)
            startPt.x = startPt.x + 1
            endPt.x = endPt.x + 1
            ptlist.addpt startPt
            ptlist.addpt endPt
            Set oLine = ThisDrawing.ModelSpace.AddPolyline(ptlist.list)
            oLine.Layer = ent.Layer
            oLine.ConstantWidth = 0.6
            
            '畫第一點
            startPt.x = startPt.x - 1.39 - 1
            startPt.Y = startPt.Y - 3.55
            Set objDonut = donut(startPt, 0, 0.95)
            objDonut.Layer = ent.Layer
            
            '畫第二點
            startPt.Y = startPt.Y - 3.47
            Set objDonut = donut(startPt, 0, 0.95)
            objDonut.Layer = ent.Layer
        End If
    Next
End Sub
Private Sub line2()
On Error Resume Next
    Dim ent As Object

   
    Dim SSetColl As AcadSelectionSets
    Set SSetColl = ThisDrawing.SelectionSets
    
    ' Create a SelectionSet named "TEST" in the current drawing
    Dim ssetObj As AcadSelectionSet
  
    If SSetColl.count > 0 Then
        SSetColl.item(0).Delete
    End If
    Set ssetObj = SSetColl.add("TEST")
    ssetObj.SelectOnScreen
    
    '排序陣列
    Dim TheArray As Variant
    Dim TheArrayEnt As Variant
    Dim coI As Integer
    Dim i As Long
    Dim oLine As AcadPolyline
    Dim startPt As New point
    Dim endPt As New point
    Dim ptlist As New PointList
    Dim retCoord As Variant
    Dim objDonut As AcadLWPolyline
    


    ' Add the dimstyle to the dimstyles collection
    coI = 0
  ' 找出圖面中的每一個選集
    For Each ent In ssetObj
        If (ent.ObjectName = "AcDb2dPolyline") Then
            
            retCoord = ent.Coordinates
            startPt.x = retCoord(0): startPt.Y = retCoord(1): startPt.z = retCoord(2)
            endPt.x = retCoord(3): endPt.Y = retCoord(4): endPt.z = retCoord(5)
            startPt.x = startPt.x - 1
            endPt.x = endPt.x - 1
            ptlist.addpt startPt
            ptlist.addpt endPt
            Set oLine = ThisDrawing.ModelSpace.AddPolyline(ptlist.list)
            oLine.Layer = ent.Layer
            oLine.ConstantWidth = 0.6
            '畫第一點
            startPt.x = startPt.x + 1.39 + 1
            startPt.Y = startPt.Y - 3.55
            Set objDonut = donut(startPt, 0, 0.95)
            objDonut.Layer = ent.Layer
            
            '畫第二點
            startPt.Y = startPt.Y - 3.47
            Set objDonut = donut(startPt, 0, 0.95)
            objDonut.Layer = ent.Layer
        End If
    Next
End Sub

Private Sub AcadDocument_Deactivate()

    'Example_SetTools
    'Example_SetMusicTextTools
End Sub

Sub Load_TTF_QuGin()
    Call AddFontResource("e:\GuQinKai03.ttf")
    Call AddFontResource("e:\QIN01.ttf")
    Call AddFontResource("e:\QIN02.ttf")
    Call AddFontResource("e:\QIN03.ttf")
    Call SendMessage(HWND_BROADCAST, WM_FONTCHANGE, 0, 0)
End Sub




Sub Example_GetBulge()
    ' This example creates a lightweight polyline in model space.
    ' It then finds and changes the bulge for a given segment.
    '聚合線 畫弧
    Dim plineObj As AcadLWPolyline
    Dim points(0 To 7) As Double
    Dim lenght As Double
    lenght = 51
    
    ' Define the 2D polyline points
    points(0) = 0: points(1) = 0
    points(2) = 1.9 * 2: points(3) = 1.3755 * 2
    points(4) = points(2) + lenght: points(5) = points(3)
    points(6) = points(4) + points(2): points(7) = points(1)
        
    ' Create a lightweight Polyline object in model space
    Set plineObj = ThisDrawing.ModelSpace.AddLightWeightPolyline(points)
    ZoomAll
    
    ' Find the bulge of the third segment
    Dim currentBulge As Double
    currentBulge = plineObj.GetBulge(3)
    ' Change the bulge of the third segment
'    plineObj.SetBulge 0, -0.32401
'    plineObj.SetBulge 2, -0.32401
    plineObj.SetBulge 0, -0.7
    plineObj.SetBulge 2, -0.32401
    plineObj.Update
    
End Sub
Sub Example_GetFont()
    ' This example find the font information for the active text style.
    
    Dim typeFace As String
    Dim Bold As Boolean
    Dim Italic As Boolean
    Dim charSet As Long
    Dim PitchandFamily As Long
    
    ThisDrawing.ActiveTextStyle.GetFont typeFace, Bold, Italic, charSet, PitchandFamily
    
    MsgBox "The current text style has the following font properties:" & vbCrLf _
            & "Typeface: " & typeFace & vbCrLf _
            & "Bold: " & Bold & vbCrLf _
            & "Italic: " & Italic & vbCrLf _
            & "Character set: " & charSet & vbCrLf _
            & "Pitch and Family: " & PitchandFamily
    
End Sub


Sub Ch4_ImportingAndExporting()

    '創建圓用於直觀顯示
    
    Dim circleObj As AcadCircle
    
    Dim centerPt(0 To 2) As Double
    
    Dim radius As Double
    
    centerPt(0) = 2: centerPt(1) = 2: centerPt(2) = 0
    
    radius = 1
    
    Set circleObj = ThisDrawing.ModelSpace.AddCircle(centerPt, radius)
    
    ThisDrawing.Application.ZoomAll
    
    '創建空的選擇集
    
    Dim sset As AcadSelectionSet
    
    Set sset = ThisDrawing.SelectionSets.add("NEWSSET")
    
    '將當前圖形輸出到AutoCAD 臨時文件目錄下的 DXF 文件
    
    Dim tempPath As String
    
    Dim exportFile As String
    
    Const dxfname As String = "DXFExprt"
    
    tempPath = ThisDrawing.Application.preferences.Files.TempFilePath
    
    exportFile = tempPath & dxfname
    
    ThisDrawing.Export exportFile, "DXF", sset
    
    '刪除空的選擇集
    
    ThisDrawing.SelectionSets.item("NEWSSET").Delete
    
    '打開新圖形
    
    ThisDrawing.Application.Documents.add "acad.dwt"
    
    '定義輸入
    
    Dim importFile As String
    
    Dim insertPoint(0 To 2) As Double
    
    Dim scalefactor As Double
    
    importFile = tempPath & dxfname & ".dxf"
    
    insertPoint(0) = 0: insertPoint(1) = 0: insertPoint(2) = 0
    
    scalefactor = 2#
    
    '輸入文件
    
    ThisDrawing.Import importFile, insertPoint, scalefactor
    
    ThisDrawing.Application.ZoomAll

End Sub



Sub Ch4_ZoomWindow()
'將當前圖形縮放至兩點定義的窗口。
Dim point1(0 To 2) As Double

Dim point2(0 To 2) As Double

point1(0) = 1.3: point1(1) = 7.8: point1(2) = 0

point2(0) = 13.7: point2(1) = -2.6: point2(2) = 0

ThisDrawing.Application.ZoomWindow point1, point2

End Sub

Sub Ch4_PositionApplicationWindow()
'將 AutoCAD應用程序窗口放在屏幕的左上角，並將其大小調整為寬 400 像素、高 400 像素。
ThisDrawing.Application.WindowTop = 0

ThisDrawing.Application.WindowLeft = 0

ThisDrawing.Application.width = 400

ThisDrawing.Application.height = 400

End Sub


'設置Application對象的WindowState屬性 （acMax、asMin或acNorm）

Sub Ch4_MaximizeApplicationWindow()
'height= 537
'width =315

'將當前圖形縮放至兩點定義的窗口。
    Dim point1(0 To 2) As Double
    
    Dim point2(0 To 2) As Double

    ' Return a point using a base point and a prompt
    Dim onePnt As Variant
    Dim towPnt As Variant
    Dim xx As Double
    Dim yy As Double
    Dim meScale As Double
    Dim ptScale As Double
    
    onePnt = ThisDrawing.Utility.GetPoint(, "第一點: ")
    towPnt = ThisDrawing.Utility.GetPoint(onePnt, "第二點: ")
    point1(0) = onePnt(0): point1(1) = onePnt(1): point1(2) = onePnt(2)
    
    point2(0) = towPnt(0): point2(1) = towPnt(1): point2(2) = towPnt(2)

    '改變應用程序窗口 大小。
    With ThisDrawing
        .Application.WindowState = acMax
        .WindowState = acNorm
        .width = 800
        .height = 580
        xx = Abs(point1(0) - point2(0))
        yy = Abs(point1(1) - point2(1))
        meScale = .width / .height
        ptScale = xx / yy
        
        If (meScale <= ptScale) Then
            .height = yy * (.width / xx)
        .width = 800
            .height = yy * (.width / xx)
        Else
            .width = xx * (.height / yy)
        .height = 580
            .width = xx * (.height / yy)
        End If
        

        .Application.ZoomWindow point1, point2
       
    End With


    Dim SSetColl As AcadSelectionSets
    Set SSetColl = ThisDrawing.SelectionSets
    
    ' Create a SelectionSet named "TEST" in the current drawing
    Dim ssetObj As AcadSelectionSet
  
    If SSetColl.count = 2 Then
        SSetColl.item(0).Delete
        SSetColl.item(1).Delete
    ElseIf SSetColl.count > 0 Then
        SSetColl.item(0).Delete
    End If
    Set ssetObj = SSetColl.add("TEST")

    Call ssetObj.Select(acSelectionSetWindow, point1, point2)
    
    
    ' Define the name for the exported file
    Dim exportFile As String

    exportFile = SaveFile("哀哀", _
    "WMF Files (*.WMF)" & Chr$(0) & "*.WMF" & Chr$(0) _
    & "X Files (*.x)" & Chr$(0) & "*.x" & Chr$(0) _
    & "XMesh Files (*.xms)" & Chr$(0) & "*.xms" & Chr$(0) _
    & "All Files (*.*)" + Chr$(0) + "*.*" + Chr$(0))
        
        
    ' Export the current drawing to the file specified above.
    ThisDrawing.Export exportFile, "WMF", ssetObj

'若最小化應用程序窗口 , 則按下列語句:

'ThisDrawing.Application.WindowState = acMin
End Sub
Public Sub GetAttribute()
    '本段代碼從選中的圖塊中獲取屬性值，並對其修改
    Dim entObj As AcadEntity
    Dim pickPnt As Variant
    Dim blkRefObj As AcadBlockReference
    '選擇圖元
    ThisDrawing.Utility.GetEntity entObj, pickPnt
    '判斷是否為塊引用
    If StrComp(entObj.ObjectName, "AcDbBlockReference", 1) <> 0 Then
        MsgBox "你選擇的不是一個圖塊，程序將退出！"
        '如果選擇的不是一個塊引用則程序退出運行
        Exit Sub
    End If
    '如果選擇的是塊引用，將其賦給塊引用對象
    Set blkRefObj = entObj
    '判斷該塊引用是否含有屬性值
    If Not blkRefObj.HasAttributes Then
        MsgBox "你選擇的圖塊沒有塊屬性，程序將退出！"
        '如果不含由屬性值退出
        Exit Sub
    End If
    Dim attVars As Variant
    Dim i As Integer
    Dim SSATT As String
    '獲取塊引用中的塊屬性對象
    attVars = blkRefObj.GetAttributes
    '對塊屬性對象進行遍歷
    SSATT = ""
    For i = 0 To UBound(attVars)
        SSATT = SSATT & vbCrLf & _
           "Case """ & attVars(i).TagString & """"
'        MsgBox "第" & I + 1 & "屬性對象的屬性值分別如下：" & Chr(13) & Chr(13) & _
'               "屬性標籤為：" & attVars(I).TagString & Chr(13) & _
'               "屬性值為：" & attVars(I).textString
    Next
    ThisDrawing.Utility.prompt SSATT
    '將塊屬性的標籤和值進行修改
    'attVars(0).TagString = "New Tag"
    'attVars(0).textString = "New Value"
    'ThisDrawing.Regen True
End Sub

Attribute VB_Name = "ToolsSet"
Option Explicit

Sub SetMusicTextToolsBar()
    ' This example uses MenuGroups to obtain a reference to the AutoCAD main menu.
    ' It then creates a new Toolbar (TestMenu) and inserts a ToolBarButton
    ' with a custom icon. The menu is automatically shown.
    '
    ' * NOTE: The paths of the icons for the new toolbar should be updated
    ' before running this example.
        
    Dim currMenuGroup As AcadMenuGroup
    Dim newToolBar As AcadToolbar, newToolBarButton As AcadToolbarItem
    Dim loadMusic As String
    Dim unloadMusic As String
    Dim loadMusicdvb As String
    Dim ShowMusic As String
    Dim ShowMusicEdit As String
    Dim SetWindowSaveWmf As String
    Dim ToBWMFWmf As String
    Dim SmallBitmapName  As String, LargeBitmapName  As String
    
    On Error GoTo ERRORTRAP
    
    ' Use MenuGroups property to obtain reference to main AutoCAD menu
    Set currMenuGroup = ThisDrawing.Application.MenuGroups.item("ACAD")
    
    ' Create the new Toolbar in this group
    Set newToolBar = currMenuGroup.Toolbars.add("MenuToolsBar")
    

    ShowMusicEdit = Chr(3) & Chr(3) & Chr(95) & "-vbarun frmMusicEdit" & vbCr
    Set newToolBarButton = newToolBar.AddToolbarButton(newToolBar.count + 1, "開起 MusicEdit 介面", "開起 MusicEdit 介面", ShowMusicEdit, False)
    

   
    ' Read icon paths for this Toolbar button
'    GoSub READPATHS
    
'    ' Change the default icon (smile face) for the new toolbar button
'    SmallBitmapName = "c:\images\16x16.bmp"     ' Use a 16x16 pixel .BMP image
'    LargeBitmapName = "c:\images\32x32.bmp"     ' Use a 32x32 pixel .BMP image
'    newToolBarButton.SetBitmaps SmallBitmapName, LargeBitmapName
'
    ' Read icon paths for this Toolbar button
'    GoSub READPATHS
    
    Exit Sub
    
READPATHS:
    ' Read icon paths for this Toolbar button
    newToolBarButton.GetBitmaps SmallBitmapName, LargeBitmapName
'    MsgBox "The new Toolbar uses the following icon files: " & _
'           vbCrLf & vbCrLf & "Small Bitmap: " & SmallBitmapName & vbCrLf & _
'           "Large Bitmap: " & LargeBitmapName
    Return

ERRORTRAP:
'    MsgBox "The following error has occurred: " & Err.Description
End Sub

Sub Example_SetTools()
    ' This example uses MenuGroups to obtain a reference to the AutoCAD main menu.
    ' It then creates a new Toolbar (TestMenu) and inserts a ToolBarButton
    ' with a custom icon. The menu is automatically shown.
    '
    ' * NOTE: The paths of the icons for the new toolbar should be updated
    ' before running this example.
        
    Dim currMenuGroup As AcadMenuGroup
    Dim newToolBar As AcadToolbar, newToolBarButton As AcadToolbarItem
    Dim loadMusic As String
    Dim unloadMusic As String
    Dim loadMusicdvb As String
    Dim ShowMusic As String
    Dim ShowMusicEdit As String
    Dim SetWindowSaveWmf As String
    Dim ToBWMFWmf As String
    Dim SmallBitmapName  As String, LargeBitmapName  As String
    
    On Error GoTo ERRORTRAP
    
    ' Use MenuGroups property to obtain reference to main AutoCAD menu
    Set currMenuGroup = ThisDrawing.Application.MenuGroups.item("ACAD")
    
    ' Create the new Toolbar in this group
    Set newToolBar = currMenuGroup.Toolbars.add("TestMenu")
    
    ' Add an item to the new Toolbar and assign an Open macro
    ' (VBA equivalent of: "ESC ESC _open ")
    loadMusic = Chr(3) & Chr(3) & Chr(95) & "_arx l " & """Z:/download/備份簡譜/Musical/debug/AsdkMusicalDb.dbx""" & Chr(32)

    Set newToolBarButton = newToolBar.AddToolbarButton(newToolBar.count + 1, "載入 Musical.dbx", "載入 Musical.dbx", loadMusic, False)
   
    unloadMusic = Chr(3) & Chr(3) & Chr(95) & "_arx U asdkmusicaldb.dbx" & vbCr
    Set newToolBarButton = newToolBar.AddToolbarButton(newToolBar.count + 1, "釋放 Musical.dbx", "釋放 Musical.dbx", unloadMusic, False)
    
    loadMusicdvb = Chr(3) & Chr(3) & Chr(95) & "-vbaload " & """Z:/download/備份簡譜/Musical/debug/MusicalAprintf.dvb""" & Chr(32)
    Set newToolBarButton = newToolBar.AddToolbarButton(newToolBar.count + 1, "截入 MusicalAprintf.dvb", "截入 MusicalAprintf.dvb", loadMusicdvb, False)
    
    ShowMusic = Chr(3) & Chr(3) & Chr(95) & "-vbarun frmMusic" & vbCr
    Set newToolBarButton = newToolBar.AddToolbarButton(newToolBar.count + 1, "開起 Music 介面", "開起 Music 介面", ShowMusic, False)
    
    ShowMusicEdit = Chr(3) & Chr(3) & Chr(95) & "-vbarun frmMusicEdit" & vbCr
    Set newToolBarButton = newToolBar.AddToolbarButton(newToolBar.count + 1, "開起 MusicEdit 介面", "開起 MusicEdit 介面", ShowMusicEdit, False)
    
    SetWindowSaveWmf = Chr(3) & Chr(3) & Chr(95) & "-vbarun Ch4_MaximizeApplicationWindow" & vbCr
    Set newToolBarButton = newToolBar.AddToolbarButton(newToolBar.count + 1, "將當前圖形縮放至兩點定義的窗口", "將當前圖形縮放至兩點定義的窗口", SetWindowSaveWmf, False)
   
    ToBWMFWmf = Chr(3) & Chr(3) & Chr(95) & "bwmfout" & vbCr
    Set newToolBarButton = newToolBar.AddToolbarButton(newToolBar.count + 1, "BWMF 兩點定義的窗口", "BWMF 兩點定義的窗口", ToBWMFWmf, False)
   
   
   
    ' Read icon paths for this Toolbar button
'    GoSub READPATHS
    
'    ' Change the default icon (smile face) for the new toolbar button
'    SmallBitmapName = "c:\images\16x16.bmp"     ' Use a 16x16 pixel .BMP image
'    LargeBitmapName = "c:\images\32x32.bmp"     ' Use a 32x32 pixel .BMP image
'    newToolBarButton.SetBitmaps SmallBitmapName, LargeBitmapName
'
    ' Read icon paths for this Toolbar button
'    GoSub READPATHS
    
    Exit Sub
    
READPATHS:
    ' Read icon paths for this Toolbar button
    newToolBarButton.GetBitmaps SmallBitmapName, LargeBitmapName
'    MsgBox "The new Toolbar uses the following icon files: " & _
'           vbCrLf & vbCrLf & "Small Bitmap: " & SmallBitmapName & vbCrLf & _
'           "Large Bitmap: " & LargeBitmapName
    Return

ERRORTRAP:
'    MsgBox "The following error has occurred: " & Err.Description
End Sub

Sub Example_exTools()
'匯出工具列
    ' This example uses MenuGroups to obtain a reference to the AutoCAD main menu.
    ' It then creates a new Toolbar (TestMenu) and inserts a ToolBarButton
    ' with a custom icon. The menu is automatically shown.
    '
    ' * NOTE: The paths of the icons for the new toolbar should be updated
    ' before running this example.
        
    Dim currMenuGroup As AcadMenuGroup
    Dim newToolBar As AcadToolbar, newToolBarButton As AcadToolbarItem
    Dim loadMusic As String
    Dim unloadMusic As String
    Dim ShowMusic As String
    Dim ShowMusicEdit As String
    Dim SmallBitmapName  As String, LargeBitmapName  As String
    
    'On Error GoTo ERRORTRAP
    On Error Resume Next
    
    ' Use MenuGroups property to obtain reference to main AutoCAD menu
    Set currMenuGroup = ThisDrawing.Application.MenuGroups.item("ACAD")
    
    ' Create the new Toolbar in this group
    Set newToolBar = currMenuGroup.Toolbars.item("MusicText")
    
    ' Add an item to the new Toolbar and assign an Open macro
    ' (VBA equivalent of: "ESC ESC _open ")
    
    Dim help1 As String
    Dim code As String
    Dim i As Integer
    For i = 1 To newToolBar.count - 1
        help1 = newToolBar.item(i).name
        code = newToolBar.item(i).Macro
        ThisDrawing.Utility.prompt "\n第" & i & "個," & help1 & "," & code
    Next
'
'    loadMusic = Chr(3) & Chr(3) & Chr(95) & "_arx l " & """E:/games/AutoCad_Arx/samples/entity/Musical/debug/AsdkMusicalDb.dbx""" & Chr(32)
'    Set newToolBarButton = newToolBar.AddToolbarButton(newToolBar.count + 1, "載入 Musical.dbx", "載入 Musical.dbx", loadMusic, False)
'
'    'unloadMusic = Chr(3) & Chr(3) & Chr(95) & "_arx U " & "AsdkMusicalDb.dbx;"
'    unloadMusic = Chr(3) & Chr(3) & Chr(95) & "_arx U asdkmusicaldb.dbx" & vbCr
'    Set newToolBarButton = newToolBar.AddToolbarButton(newToolBar.count + 1, "釋放 Musical.dbx", "釋放 Musical.dbx", unloadMusic, False)
'
'    ShowMusic = Chr(3) & Chr(3) & Chr(95) & "-vbarun frmMusic" & vbCr
'    Set newToolBarButton = newToolBar.AddToolbarButton(newToolBar.count + 1, "開起 Music 介面", "開起 Music 介面", ShowMusic, False)
'
'    ShowMusicEdit = Chr(3) & Chr(3) & Chr(95) & "-vbarun frmMusicEdit" & vbCr
'    Set newToolBarButton = newToolBar.AddToolbarButton(newToolBar.count + 1, "開起 MusicEdit 介面", "開起 MusicEdit 介面", ShowMusicEdit, False)
'
    ' Read icon paths for this Toolbar button
'    GoSub READPATHS
    
'    ' Change the default icon (smile face) for the new toolbar button
'    SmallBitmapName = "c:\images\16x16.bmp"     ' Use a 16x16 pixel .BMP image
'    LargeBitmapName = "c:\images\32x32.bmp"     ' Use a 32x32 pixel .BMP image
'    newToolBarButton.SetBitmaps SmallBitmapName, LargeBitmapName
'
    ' Read icon paths for this Toolbar button
'    GoSub READPATHS
    
    Exit Sub
    
READPATHS:
    ' Read icon paths for this Toolbar button
    newToolBarButton.GetBitmaps SmallBitmapName, LargeBitmapName
'    MsgBox "The new Toolbar uses the following icon files: " & _
'           vbCrLf & vbCrLf & "Small Bitmap: " & SmallBitmapName & vbCrLf & _
'           "Large Bitmap: " & LargeBitmapName
    Return

ERRORTRAP:
    'MsgBox "The following error has occurred: " & Err.Description
End Sub


Sub Example_SetMusicTextTools()
    ' This example uses MenuGroups to obtain a reference to the AutoCAD main menu.
    ' It then creates a new Toolbar (TestMenu) and inserts a ToolBarButton
    ' with a custom icon. The menu is automatically shown.
    '
    ' * NOTE: The paths of the icons for the new toolbar should be updated
    ' before running this example.
        
    Dim currMenuGroup As AcadMenuGroup
    Dim newToolBar As AcadToolbar, newToolBarButton As AcadToolbarItem
    Dim loadMusic As String
    Dim unloadMusic As String
    Dim ShowMusic As String
    Dim ShowMusicEdit As String
    Dim SmallBitmapName  As String, LargeBitmapName  As String
    
    On Error GoTo ERRORTRAP
    
    ' Use MenuGroups property to obtain reference to main AutoCAD menu
    Set currMenuGroup = ThisDrawing.Application.MenuGroups.item("ACAD")
    
    ' Create the new Toolbar in this group
    Set newToolBar = currMenuGroup.Toolbars.add("MusicText")
    Dim i As Integer
    Dim Marco(10, 2) As String
    Dim vbaPATH As String
    Dim imagePATH As String
    Dim pos As Integer
Marco(0, 0) = "Unload 釋放AsdkMusicText"
Marco(1, 0) = "Load 載入AsdkMusicText"
Marco(2, 0) = "開起 Edit 介面"
Marco(3, 0) = "加入符號"
Marco(4, 0) = "開起 PageMusic 頁面"
Marco(5, 0) = "連結拍子"
Marco(6, 0) = "移除連結"
Marco(7, 0) = "IsSet"
Marco(8, 0) = "SelectDraw"

Marco(0, 1) = Chr(3) & Chr(3) & Chr(95) & "_arx u AsdkMusicText.arx" & vbCr
Marco(1, 1) = Chr(3) & Chr(3) & Chr(95) & "_arx l " & """AsdkMusicText.arx""" & Chr(32)
Marco(2, 1) = Chr(3) & Chr(3) & Chr(95) & "_musicsample "
Marco(3, 1) = Chr(3) & Chr(3) & Chr(95) & "_addmusictext "
Marco(4, 1) = Chr(3) & Chr(3) & Chr(95) & "_addMusicTextPage "
Marco(5, 1) = Chr(3) & Chr(3) & Chr(95) & "_addMusicJoinMany "
Marco(6, 1) = Chr(3) & Chr(3) & Chr(95) & "_addMusicEraseMany "
Marco(7, 1) = Chr(3) & Chr(3) & Chr(95) & "_IsSet "
Marco(8, 1) = Chr(3) & Chr(3) & Chr(95) & "_-vbarun ThisDrawing.Example_SelectOnScreen "

    vbaPATH = ThisDrawing.Application.VBE.ActiveVBProject.FileName
    pos = InStrRev(vbaPATH, "\")
    imagePATH = Mid(vbaPATH, 1, pos) & "image\"
Marco(0, 2) = imagePATH & "UnLoad.BMP"
Marco(1, 2) = imagePATH & "Load.BMP"
Marco(2, 2) = imagePATH & "SEdit.BMP"
Marco(3, 2) = imagePATH & "AddMusicText.BMP"
Marco(4, 2) = imagePATH & "PageMusic.BMP"
Marco(5, 2) = imagePATH & "JoinMany.BMP"
Marco(6, 2) = imagePATH & "EraseMany.BMP"
Marco(7, 2) = imagePATH & "IsSet.BMP"
Marco(8, 2) = imagePATH & "IsSet.BMP"
    
    For i = 0 To 8
        Set newToolBarButton = newToolBar.AddToolbarButton(newToolBar.count + 1, Marco(i, 0), Marco(i, 0), Marco(i, 1), False)
        
        newToolBarButton.SetBitmaps Marco(i, 2), Marco(i, 2)
    Next
    ' Add an item to the new Toolbar and assign an Open macro
    ' (VBA equivalent of: "ESC ESC _open ")
    'loadMusic = Chr(3) & Chr(3) & Chr(95) & "_arx l " & """E:/games/AutoCad_Arx/samples/entity/Musical/debug/AsdkMusicalDb.dbx""" & Chr(32)
    'Set newToolBarButton = newToolBar.AddToolbarButton(newToolBar.count + 1, "載入 Musical.dbx", "載入 Musical.dbx", loadMusic, False)
    
'    ' Change the default icon (smile face) for the new toolbar button
    'SmallBitmapName = "c:\images\16x16.bmp"     ' Use a 16x16 pixel .BMP image
    'LargeBitmapName = "c:\images\32x32.bmp"     ' Use a 32x32 pixel .BMP image
    'newToolBarButton.SetBitmaps SmallBitmapName, LargeBitmapName
'
    ' Read icon paths for this Toolbar button
'    GoSub READPATHS
    
    Exit Sub
    
READPATHS:
    ' Read icon paths for this Toolbar button
    newToolBarButton.GetBitmaps SmallBitmapName, LargeBitmapName
'    MsgBox "The new Toolbar uses the following icon files: " & _
'           vbCrLf & vbCrLf & "Small Bitmap: " & SmallBitmapName & vbCrLf & _
'           "Large Bitmap: " & LargeBitmapName
    Return

ERRORTRAP:
    'MsgBox "The following error has occurred: " & Err.Description
End Sub

Attribute VB_Name = "frmEDIT"
Attribute VB_Base = "0{3B65EE3A-C4FA-4E1E-BCD4-137F36AE456F}{910AE999-BB72-48DA-8845-73FD75ADC3B8}"
Attribute VB_GlobalNameSpace = False
Attribute VB_Creatable = False
Attribute VB_PredeclaredId = True
Attribute VB_Exposed = False
Attribute VB_TemplateDerived = False
Attribute VB_Customizable = False

Option Explicit
'2013.03.17  V3 正要修改 二胡的版本，因程式之前是用古箏的指法圖，現在改成二胡的指法圖
'2017.09.28  V8 寫入要midi 檔的
Const VERSION  As String = "v1.65" '軟體號碼
Const C1 As Integer = 60   'C調1的鍵名值
Const FOURPAINUM   As Integer = 64 '1/4音符計數
Const MIDICLOCK As Integer = 24   '每1/64音符的MIDICLOCK數
Const TEMPO_DEF As Integer = 90   '預設每分鐘90拍
Const PARTITION_DEF As Integer = 240   '預設每拍分割為120計時單元
Const VOLUME_DEF As Integer = 64
Const MAINLAYER As String = "MAIN"    '主要的圖層


Private Type Glode
    check1 As Boolean
    fontName As String
    FontSize As Double
    Many As Integer
    Bar As Integer
    Mete As Integer
    Mete2 As Integer
    
    PageWidth As Double
    LeftSpace As Double
    RightSpace As Double
    BarToNote As Double
    TrackToTrack As Double
    LineToLine As Double
    MIN_X As Double
    Beat_MIN_X As Double
End Type

'二胡指法 狀態
Private Type ErhuFing
    fing1 As Integer    'Ⅰ Ⅱ Ⅲ Ⅳ "b空絃"
    fing2 As String  'Ⅰ Ⅱ Ⅲ Ⅳ "b空絃"
    Push As String      '拉∩ 推V
    InOut As String     '內   外
End Type


Dim G As Glode
Dim m_Buf As New DataBuffer

'1 在vb工程中引用autocad的��
'2 定�鏇utocad�褻H
Private acadApp As AcadApplication
Private acadDoc As AcadDocument
'3 �壎��{���筠utocad的函�菕A以下是我�尷�
'--------------------------------------------------------------
'�盛湣ad
'-------------------------------------------------------------
Private Function AcadConnect() As Boolean
Dim flag As Boolean
On Error Resume Next
    Set acadApp = GetObject(, "AutoCAD.Application")
    flag = True
    If Err Then
       Err.clear
       Set acadApp = CreateObject("AutoCAD.Application")
       flag = True
       If Err Then
          flag = False
          MsgBox "不能�b行AutoCAD,�[�銢d是否安�E！", vbOKCancel, "警告！"
          Exit Function
       End If
    End If
    AcadConnect = flag
    Set acadDoc = acadApp.ActiveDocument
    'acadDoc.Close False
End Function


Private Sub cbCANCLE_Click()
    Me.Hide
End Sub


Private Sub cmOK_Click()
    G.fontName = Me.cobFontName.text
    G.FontSize = Me.cobFontSize.text
    
    Dim mete_mete As Variant
    mete_mete = Split(Me.cobMete, "/")
    G.Mete = mete_mete(0)
    G.Mete2 = mete_mete(1)
    
    G.Many = Me.cobMany
    G.Bar = Me.cobBar.text
    
    G.PageWidth = Me.tbPageWidth '寬度
    G.LeftSpace = Me.tbLeftSpace  '左空白
    G.RightSpace = Me.tbRightSpace  '右空白
    G.BarToNote = Me.tbBarToNote    '小節到音符
    G.TrackToTrack = Me.tbTrackToTrack  '聲部間距
    G.LineToLine = Me.tbLineToLine      '每行間距
    G.check1 = True
    G.MIN_X = Me.tbMIN_X            '微調
    G.Beat_MIN_X = Me.tbBeat_min_x  '拍微調

    m_Buf.clear
    Call m_Buf.GetDataToBuf(Me.TextBox8.text)
    'MsgBox Me.TextBox8.text
    Me.Hide
    database
    Call put_many_text3
    
    
    
End Sub
Private Sub database()
    ' Create new layer
    Dim layerObj As AcadLayer
    Dim datalayer(20, 2) As String
    
    datalayer(1, 1) = "FIGE":
    datalayer(1, 2) = 6
    datalayer(2, 1) = "TEXT":
    datalayer(2, 2) = 2
    datalayer(3, 1) = "bar":
    datalayer(3, 2) = 181
    datalayer(4, 1) = "裝飾符號":
    datalayer(4, 2) = 4
    datalayer(5, 1) = "自繪線":
    datalayer(5, 2) = 1
    datalayer(6, 1) = "main":
    datalayer(6, 2) = 7
    datalayer(7, 1) = "TEMP":
    datalayer(7, 2) = 1
    datalayer(8, 1) = "SimpErhu符號":
    datalayer(8, 2) = 151
    
    Dim i As Integer
    
    Dim color(0 To 8) As AcadAcCmColor
    
    For i = 1 To 8
        Set layerObj = ThisDrawing.Layers.add(datalayer(i, 1))
        Set color(i) = AcadApplication.GetInterfaceObject("AutoCAD.AcCmColor." & ACAD_Ver)
        


        
        
        color(i).ColorIndex = datalayer(i, 2)
        layerObj.TrueColor = color(i) 'datalayer(i, 2)
    Next


   
    ' Create a Text style named "TEST" in the current drawing
    Dim textStyle As AcadTextStyle
    Dim dataStyles(20, 3) As String
    dataStyles(0, 1) = "Standard"
    dataStyles(0, 2) = "txt.shx"
    dataStyles(0, 3) = "chineset.shx"
    dataStyles(1, 1) = "EUDC"
    dataStyles(1, 2) = "EUDC.TTE"
    dataStyles(1, 3) = ""
    dataStyles(2, 1) = "標體"
    dataStyles(2, 2) = "KAIU.TTF"
    dataStyles(2, 3) = ""
    dataStyles(3, 1) = "MMP2005"
    dataStyles(3, 2) = ""
    dataStyles(3, 3) = ""
    dataStyles(4, 1) = "音符_數字"
    dataStyles(4, 2) = "SimSun.ttc"
    dataStyles(4, 3) = ""
    dataStyles(5, 1) = "型式_細明體"
    dataStyles(5, 2) = "MingLiU.ttc"
    'dataStyles(5, 2) = "PMingLiU.ttf"
    dataStyles(5, 3) = ""
    dataStyles(6, 1) = "字符"
    dataStyles(6, 2) = "MAESTRO.TTF"
    dataStyles(6, 3) = ""
    dataStyles(7, 1) = "華康粗黑"
    dataStyles(7, 2) = "DFFT_C7.ttc"
    'dataStyles(7, 2) = "DFLiHeiBold.ttf"
    dataStyles(7, 3) = ""
    dataStyles(8, 1) = "文字"
    dataStyles(8, 2) = "KAIU.TTF"
    dataStyles(8, 3) = ""
    dataStyles(9, 1) = "SimpErhu"
    dataStyles(9, 2) = "SimpErhuFont.ttf"
    dataStyles(9, 3) = ""

    'Dim i As Integer
'    For i = 0 To 9
'        Set textStyle = ThisDrawing.TextStyles.add(dataStyles(i, 1))
'        If dataStyles(i, 2) <> "" Then
'
'            Set textStyle = CreateTextStyle(dataStyles(i, 2), dataStyles(i, 1), FontType.BigFont)
'        End If
'        If dataStyles(i, 3) <> "" Then
'            textStyle.BigFontFile = dataStyles(i, 3)
'        End If
'    Next
End Sub
Private Sub inst_G(the_G As Glode, pt As Variant)
    '插入設定資料
    Dim mtxt As AcadMText
    Dim textObj As AcadText
    Dim textString As String
    Dim insertionPoint(0 To 2) As Double
    Dim height As Double
    
    ' Define the text object
    textString = VERSION & vbCrLf
    textString = textString & "size " & the_G.FontSize & vbCrLf
    
    textString = textString & "左空白 " & the_G.LeftSpace & "mm" & vbCrLf
    textString = textString & "右空白 " & the_G.RightSpace & "mm" & vbCrLf
    textString = textString & "小節到音符 " & the_G.BarToNote & "mm" & vbCrLf
    textString = textString & "聲部  " & the_G.TrackToTrack & "mm" & vbCrLf
    textString = textString & "每行  " & the_G.LineToLine & "mm" & vbCrLf
    textString = textString & "微調  " & the_G.MIN_X & "mm" & vbCrLf
    textString = textString & "拍微調 " & the_G.Beat_MIN_X
    
    
    insertionPoint(0) = pt(0) - 30: insertionPoint(1) = pt(1): insertionPoint(2) = pt(2)
    height = 3
    
    ' Create the text object in model space
    Set mtxt = ThisDrawing.ModelSpace.AddMText(insertionPoint, height, textString)
    mtxt.width = 40
    mtxt.styleName = "Standard"
    
End Sub

Private Sub put_many_text3()
  
    '放置文字本
    Dim pt As Variant
    
    ' Return a point using a prompt
    pt = ThisDrawing.Utility.GetPoint(, "\n選擇要插入的點 ：Enter insertion point: ")
    Call inst_G(G, pt)
'***********************************************************************************
    '畫出定位線-畫框;
    
    Dim plineObj As AcadPolyline
    Dim Pnt As New PointList
    
    Call Pnt.add(pt(0), pt(1) - 200, 0)
    Call Pnt.add(pt(0), pt(1) + G.FontSize * 9, 0)
    Call Pnt.add(pt(0) + G.PageWidth, pt(1) + G.FontSize * 9, 0)
    Call Pnt.add(pt(0) + G.PageWidth, pt(1) - 200, 0)
    Set plineObj = ThisDrawing.ModelSpace.AddPolyline(Pnt.list())
    plineObj.Layer = "Defpoints"
'*********************************************************************************
    '插入單一標題
    Dim objText As AcadText
    Dim inPT As Variant
    Dim ooPt As Variant
    inPT = pt
    inPT(0) = inPT(0) + (G.PageWidth / 2)
    inPT(1) = inPT(1) + G.FontSize * 5.5
    Set objText = ThisDrawing.ModelSpace.AddText(m_Buf.getTITLE, inPT, 6)
    ooPt = objText.insertionPoint
    objText.Layer = "TEXT"
    objText.Alignment = acAlignmentCenter
    objText.styleName = "文字"
    ooPt(0) = ooPt(0) + objText.insertionPoint(0)
    ooPt(1) = ooPt(1) + objText.insertionPoint(1)
    
    objText.Move objText.insertionPoint, ooPt
    
'*********************************************************************************
'建立主要的圖層
    Dim layerObj As AcadLayer
    Set layerObj = ThisDrawing.Layers.add(MAINLAYER)

    
    
'lin    Dim tmp_joinApp As New MTJoinDequeApp()
'lin    Dim tmp_joinIds As New AcDbObjectIdArray()
    Dim tmp_joinApp As Variant
    Dim tmp_joinIds As New Collection
    'double lastTemp ;
    Dim tmp_track As Integer
    Dim tmp_track_item As Long
    Dim num As Integer
    Dim A_TEMPO_add As Integer

    Dim tmp_delaytime As Double  '計算拍子 是要計上一個字的長度
    Dim tmp_AllTempo As Long
    Dim tmp_xy As point
    'Dim NewObj As NnmText
    Dim BNewObj As AcadBlockReference
    Dim tmp_name As String
    
    Dim cst As String
    Dim cst_no_fing As String
    Dim ptGripMid As Variant
    
    tmp_delaytime = 0
    tmp_AllTempo = 0
    
    tmp_name = G.fontName
    Dim tmp_erhu_fing As ErhuFing
    Dim midDownPt(2) As Double
    Dim mt_slur_left As MusicBlockGraphics
    Dim plineSlur As AcadLWPolyline
    Dim MBG As New MusicBlockGraphics
  
        For tmp_track = 0 To m_Buf.GetTrackSize() - 1
            'NewObj = Nothing
'lin            tmp_joinApp.clear()
            tmp_AllTempo = 0
            tmp_delaytime = 0
            num = 0
            A_TEMPO_add = 1

            For tmp_track_item = 0 To m_Buf.GetTrackBufferSize(tmp_track)

                '這是要連結線的，以 m_Mete2 為時值
                If num >= (PARTITION_DEF / (G.Mete2 / 4) * A_TEMPO_add) Then
                    If A_TEMPO_add = G.Mete Then
                        num = 0
                        A_TEMPO_add = 1
                    Else
                        A_TEMPO_add = A_TEMPO_add + 1
                    End If

                    If tmp_joinIds.count >= 1 Then
                        Dim pp As Long
                        ReDim tmp_joinApp(tmp_joinIds.count - 1)
                        For pp = 1 To tmp_joinIds.count
                            Set tmp_joinApp(pp - 1) = tmp_joinIds.item(pp)
                        Next
                            MBG.addMusicJoin tmp_joinApp

                    End If
                    Set tmp_joinIds = Nothing

                End If


                cst = m_Buf.GetData(tmp_track, tmp_track_item)
                If " " = Mid(cst, amt.iNote, 1) Or "" = Mid(cst, amt.iNote, 1) Then
                    Exit For
                End If

                tmp_AllTempo = tmp_AllTempo + tmp_delaytime
                Dim ppnt As New point
                Dim bbo As Boolean
                ppnt.x = pt(0)
                ppnt.Y = pt(1)
                ppnt.z = pt(2)
                If Mid(cst, amt.iNote, 1) = "." Then
                    Set tmp_xy = atTableDraw(ppnt, tmp_track, tmp_AllTempo, True)
                Else
                    Set tmp_xy = atTableDraw(ppnt, tmp_track, tmp_AllTempo, False)
                End If
                                
        
                
                Dim atPt As Variant
                atPt = tmp_xy.at
                atPt(0) = 0
                atPt(1) = 0
                atPt(2) = 0
                
                 atPt = tmp_xy.at
'**************************************************************************************'
'  插入MusicText 物件
'**************************************************************************************'
                If Me.chkOption1 = True Then
                    '(古箏用)
                    '圖塊用附號)
                    
                    ppnt.x = atPt(0)
                    ppnt.Y = atPt(1)
                    ppnt.z = atPt(2)
                    MBG.setDataText ppnt, cst, G.FontSize
                    Set BNewObj = MBG.InsterEnt '插入音符及指法

                    
                    
                ElseIf Me.chkOption2 = True Then

                '(二胡用)
                '這是沒有指法的
'                    AMT.iTONE = 1        ' * 行
'                    AMT.iFinge = 2    '這是指法行     _+)(*&
'                    AMT.iScale = 3    '這是高低音行   .,:;
'                    AMT.iNote = 4     '這為主行       1234567.|l
'                    AMT.iTempo = 5    '這是拍子       -=368acefz
'                    AMT.iTowFinge = 6    '這是指法行第二行  _+)(*&
'                    AMT.iSlur = 7        ' 連音符行    (3456)
                    cst_no_fing = Mid(cst, amt.iTONE, 1) & _
                                    " " & _
                                    Mid(cst, amt.iScale, 1) & _
                                    Mid(cst, amt.iNote, 1) & _
                                    Mid(cst, amt.iTempo, 1)

                    'Call NewObj.setData(atPt, cst_no_fing, G.fontName, G.FontSize)
                    'NewObj.Layer = "main"
                    tmp_erhu_fing.fing1 = 0
                    
                    tmp_erhu_fing.Push = ""
                    tmp_erhu_fing.InOut = ""

                    '取得關鍵字 -指法1
                    Select Case Mid(cst, amt.iFinge, 1)
                       Case "0": tmp_erhu_fing.fing1 = tmp_erhu_fing.fing1 + amt.f空弦 '空弦
                       Case "1": tmp_erhu_fing.fing1 = tmp_erhu_fing.fing1 + amt.f一指
                       Case "2": tmp_erhu_fing.fing1 = tmp_erhu_fing.fing1 + amt.f二指
                       Case "3": tmp_erhu_fing.fing1 = tmp_erhu_fing.fing1 + amt.f三指
                       Case "4": tmp_erhu_fing.fing1 = tmp_erhu_fing.fing1 + amt.f四指
                       Case "W", "w": tmp_erhu_fing.fing1 = tmp_erhu_fing.fing1 + amt.f揉弦
                       
                       Case "E", "e": tmp_erhu_fing.Push = "拉"
                       Case "V", "v": tmp_erhu_fing.Push = "推"
                       Case "Q", "q": tmp_erhu_fing.InOut = "內"
                       Case "A", "a": tmp_erhu_fing.InOut = "外"
                       Case Else
                    End Select
                    
                    '取得關鍵字 -指法2
                    Select Case Mid(cst, amt.iTowFinge, 1)
                       Case "0": tmp_erhu_fing.fing1 = tmp_erhu_fing.fing1 + amt.f空弦 '空弦
                       Case "1": tmp_erhu_fing.fing1 = tmp_erhu_fing.fing1 + amt.f一指
                       Case "2": tmp_erhu_fing.fing1 = tmp_erhu_fing.fing1 + amt.f二指
                       Case "3": tmp_erhu_fing.fing1 = tmp_erhu_fing.fing1 + amt.f三指
                       Case "4": tmp_erhu_fing.fing1 = tmp_erhu_fing.fing1 + amt.f四指
                       Case "W", "w": tmp_erhu_fing.fing1 = tmp_erhu_fing.fing1 + amt.f揉弦
                       
                       Case "E", "e": tmp_erhu_fing.Push = "拉"
                       Case "V", "v": tmp_erhu_fing.Push = "推"
                       Case "Q", "q": tmp_erhu_fing.InOut = "內"
                       Case "A", "a": tmp_erhu_fing.InOut = "外"
                       
                       Case Else
                    End Select
                    
                    ppnt.x = atPt(0)
                    ppnt.Y = atPt(1)
                    ppnt.z = atPt(2)
                    MBG.setDataText ppnt, cst, G.FontSize
                    Set BNewObj = MBG.InsterEnt '插入音符及指法
                    
                    
                    '插入指法 附號(二胡用)
                    InsertErhuFinge ppnt, tmp_erhu_fing, G.FontSize
                    
                End If
                    
'*******插入圓滑線'**************************************************************************************'

 
                'AMT.iSlur = 7        ' 連音符行    (3456)
                If Mid(cst, amt.iSlur, 1) = "[" Then
                    Set mt_slur_left = New MusicBlockGraphics
                    Set mt_slur_left = MBG.copy
                    
                ElseIf Mid(cst, amt.iSlur, 1) = "]" Then
'*******聚合線 畫弧'**************************************************************************************'
                    Dim points(0 To 7) As Double
                    
                    Dim points_s(0 To 5) As Double
                    Dim lenght As Double
                    ' Find the bulge of the third segment
                    Dim currentBulge As Double
                    Dim color As New AcadAcCmColor
                    
                    
                    Dim islurAddX As Double
                    Dim islurAddY As Double
                    Dim islurBx As Double
                    Dim islurBy As Double
                    
                    islurAddX = 0.6245 * MBG.TextSize
                    islurAddY = 0.4333 * MBG.TextSize
                    
                    islurBy = 0.45 * MBG.TextSize
                    
                                        
                    'lenght = Abs(mt_slur_left.Grip.gptLeft.x - MBG.Grip.gptRight.x)

                    'points(0) = mt_slur_left.Grip.atPt.x
                    'points(1) = mt_slur_left.Grip.gptMidUp.Y
                    'points(2) = points(0) + islurAddX
                    'points(3) = points(1) + islurAddY
                    'points(4) = points(2) + lenght - (islurAddX * 2)
                    'points(5) = points(3)
                    'points(6) = points(4) + islurAddX
                    'points(7) = points(1)
                    
                    '看是否弧線的距離太近
                    
                    lenght = Abs(mt_slur_left.Grip.gptMid.x - MBG.Grip.gptMid.x)
                    If lenght >= islurAddX * 2 Then
                    
                        points(0) = mt_slur_left.Grip.gptMid.x
                        points(1) = mt_slur_left.Grip.gptMidUp.Y + islurBy
                        points(2) = points(0) + islurAddX
                        points(3) = points(1) + islurAddY
                        points(4) = points(2) + lenght - (islurAddX * 2)
                        points(5) = points(3)
                        points(6) = points(4) + islurAddX
                        points(7) = points(1)
                        ' Create a lightweight Polyline object in model space
                       Set plineSlur = ThisDrawing.ModelSpace.AddLightWeightPolyline(points)
                
                       
                       currentBulge = plineObj.GetBulge(3)
                       ' Change the bulge of the third segment
                       plineSlur.SetBulge 0, (-0.5858 / 1.4142)
                       plineSlur.SetBulge 2, (-0.5858 / 1.4142)
                       plineSlur.SetWidth 0, 0, 0.1
                       plineSlur.SetWidth 1, 0.1, 0.1
                       plineSlur.SetWidth 2, 0.1, 0
                       plineSlur.Layer = "fige"
                       
                       color.ColorIndex = 3
                       plineSlur.TrueColor = color
                       plineSlur.Update
                                       
                    Else
                    '距離太近的畫線
                        points_s(0) = mt_slur_left.Grip.gptMid.x
                        points_s(1) = mt_slur_left.Grip.gptMidUp.Y + islurBy
                        points_s(2) = points_s(0) + (lenght / 2)
                        points_s(3) = points_s(1) + islurAddY
                        points_s(4) = points_s(2) + (lenght / 2)
                        points_s(5) = points_s(1)
                        ' Create a lightweight Polyline object in model space
                       Set plineSlur = ThisDrawing.ModelSpace.AddLightWeightPolyline(points_s)
                
                       
                       currentBulge = plineObj.GetBulge(3)
                       ' Change the bulge of the third segment
                       plineSlur.SetBulge 0, (-0.5858 / 1.4142)
                       plineSlur.SetBulge 1, (-0.5858 / 1.4142)
                       
                       plineSlur.SetWidth 0, 0, 0.1
                       plineSlur.SetWidth 1, 0.1, 0
                       plineSlur.Layer = "fige"
                       
                       color.ColorIndex = 3
                       plineSlur.TrueColor = color
                       plineSlur.Update
                    End If
                        

                    
                    
                    'Set mt_slur_left = Nothing
'*****************************************************************
                    
                End If
                
                '連結線用
                tmp_joinIds.add BNewObj
                Set BNewObj = Nothing

                Select Case Mid(cst, amt.iNote, 1)
                Case "|"
                    tmp_delaytime = 0
                Case "-"
                    tmp_delaytime = PARTITION_DEF
                Case "."
                    tmp_delaytime = tmp_delaytime / 2
                Case " "
                
                Case Else
                
                Dim tempo_hj As String
                Dim tempo_ll As Variant
                
                tempo_hj = " -2=45368aAcCfFgGzZ"
                tempo_ll = Array(1, 2, 2, 4, 4, 5, 3, 6, 8, 10, 10, 12, 12, 15, 15, 16, 16, 32, 32)
                
                Dim ii As Integer
                Dim cn As String
                    For ii = 0 To Len(tempo_hj) - 1
                        cn = Mid(tempo_hj, ii + 1, 1)
                        If cn = Mid(cst, amt.iTempo, 1) Then
                            tmp_delaytime = PARTITION_DEF / tempo_ll(ii)
                            Exit For
                        Else
                            tmp_delaytime = 0
                        End If
                    Next ii
                End Select

                num = num + CInt(Fix(tmp_delaytime))
            Next tmp_track_item
        Next tmp_track

End Sub

Private Function InsertMusicText(insertionPoint() As Double, cst As String, size As Double)
'插入音附
    Dim textObj As AcadText
    Dim blockRefObj  As AcadBlockReference
    Dim textString As String
    Dim alignmentPoint(0 To 2) As Double
    Dim height As Double
    Dim midDownPt(0 To 2) As Double
    
    
    insertionPoint (0)
    insertionPoint (1)
    insertionPoint (2)
    
    Dim ipos As Integer
    Dim yAdd As Double
        '取得關鍵字  主音 AMT.iNote
    Select Case Mid(cst, amt.iNote, 1)
       Case "0": MFS.sNote = "M-NOTE0"
       Case "1": MFS.sNote = "M-NOTE1"
       Case "2": MFS.sNote = "M-NOTE2"
       Case "3": MFS.sNote = "M-NOTE3"
       Case "4": MFS.sNote = "M-NOTE4"
       Case "5": MFS.sNote = "M-NOTE5"
       Case "6": MFS.sNote = "M-NOTE6"
       Case "7": MFS.sNote = "M-NOTE7"
       Case ".": MFS.sNote = "M-NOTE."
       Case "-": MFS.sNote = "M-NOTE-"
       Case " ": MFS.sNote = ""
       Case Else
            MFS.sNote = ""
    End Select
    Dim midGirPnt(2) As Double
    
    If MFS.sNote <> "" Then
        Call ThisDrawing.ModelSpace.InsertBlock(insertionPoint, MFS.sNote, size, size, size, 0)
        

    End If

End Function

Private Sub CommandButton1_Click()
Me.Hide
TESTSTAR
End Sub
Public Sub TESTSTAR()
    '放置文字本
    Dim pt As Variant
    Dim insertionPoint(0 To 2) As Double
    
    ' Return a point using a prompt
    pt = ThisDrawing.Utility.GetPoint(, "\n選擇要插入的點 ：Enter insertion point: ")
    
    insertionPoint(0) = pt(0)
    insertionPoint(1) = pt(1)
    insertionPoint(2) = pt(2)
    InsertMusicStar insertionPoint, 3.5
End Sub




Private Function InsertErhuFinge(midDownPt As point, this_ef As ErhuFing, size As Double)
'插入二胡指法
    Dim textObj As AcadText
    Dim blockRefObj  As AcadBlockReference
    Dim textString As String
    Dim insertionPoint(0 To 2) As Double, alignmentPoint(0 To 2) As Double
    Dim height As Double
    

    insertionPoint(0) = midDownPt.x
    insertionPoint(1) = midDownPt.Y
    insertionPoint(2) = midDownPt.z
    
    Dim ipos As Integer
    Dim yAdd As Double
    ipos = 0
    yAdd = 0.7 '指法的向上增量
    If this_ef.fing1 <> 0 Then
        
        '看是否是圖塊
        If this_ef.fing1 And amt.f空弦 Then
            'Call ThisDrawing.ModelSpace.InsertBlock(insertionPoint, "二胡_空", 0.75, 0.75, 0.75, 0)
            textString = "\U+5B80"
            height = size * 0.47
            alignmentPoint(0) = insertionPoint(0) + (amt.A_TEXT_WIDTH * size / 2)
            alignmentPoint(1) = insertionPoint(1) + size * 2.13 + (ipos * yAdd * size)
            alignmentPoint(2) = insertionPoint(2)
            
            Set textObj = ThisDrawing.ModelSpace.AddText(textString, insertionPoint, height)
            textObj.Alignment = acAlignmentCenter
            textObj.TextAlignmentPoint = alignmentPoint
            textObj.styleName = "音符_數字"
            textObj.Layer = "裝飾符號"
        ipos = ipos + 1
        End If
        If this_ef.fing1 And amt.f揉弦 Then
            'textString = "\U+5B80"
            height = size * 0.47
            alignmentPoint(0) = insertionPoint(0) + (amt.A_TEXT_WIDTH * size / 2)
            alignmentPoint(1) = insertionPoint(1) + size * 2.13 + (ipos * yAdd * size)
            alignmentPoint(2) = insertionPoint(2)
            
            Set blockRefObj = ThisDrawing.ModelSpace.InsertBlock(alignmentPoint, "二胡_搰揉", 1#, 1#, 1#, 0)
            blockRefObj.Layer = "裝飾符號"
        ipos = ipos + 1
        End If
        '不是 就插入文字
        textString = ""
        If this_ef.fing1 And amt.f一指 Then
            textString = "Ⅰ"
        ElseIf this_ef.fing1 And amt.f二指 Then
            textString = "Ⅱ"
        ElseIf this_ef.fing1 And amt.f三指 Then
            textString = "Ⅲ"
        ElseIf this_ef.fing1 And amt.f四指 Then
            textString = "Ⅳ"
        End If
        If textString <> "" Then
            height = size * 0.47
            alignmentPoint(0) = insertionPoint(0) + (amt.A_TEXT_WIDTH * size / 2)
            alignmentPoint(1) = insertionPoint(1) + size * 2.13 + (ipos * yAdd * size)
            alignmentPoint(2) = insertionPoint(2)
            
            ' Create the text object in model space
            Set textObj = ThisDrawing.ModelSpace.AddText(textString, insertionPoint, height)
            textObj.Alignment = acAlignmentCenter
            textObj.TextAlignmentPoint = alignmentPoint
            textObj.styleName = "音符_數字"
            textObj.Layer = "SimpErhu符號"
            ipos = ipos + 1
        End If
        
    End If
    
    If this_ef.InOut <> "" Then
    '內外
        textString = this_ef.InOut
        height = size * 0.47
        
        alignmentPoint(0) = insertionPoint(0) + (amt.A_TEXT_WIDTH * size / 2)
        alignmentPoint(1) = insertionPoint(1) + (size * 2.13) + (ipos * yAdd * size)
        alignmentPoint(2) = insertionPoint(2)
        
        
        ' Create the text object in model space
        Set textObj = ThisDrawing.ModelSpace.AddText(textString, insertionPoint, height)
        textObj.Alignment = acAlignmentCenter
        textObj.TextAlignmentPoint = alignmentPoint
        textObj.styleName = "音符_數字"
        textObj.Layer = "裝飾符號"
        ipos = ipos + 1
    End If
    
        


    If this_ef.Push <> "" Then

        alignmentPoint(0) = insertionPoint(0) + (amt.A_TEXT_WIDTH * size / 2)
        alignmentPoint(1) = insertionPoint(1) + (size * 2.13) + (ipos * yAdd * size)
        alignmentPoint(2) = insertionPoint(2)

        If this_ef.Push = "拉" Then
            textString = "b拉"
        ElseIf this_ef.Push = "推" Then
            textString = "b推"
        End If
        
        Set blockRefObj = ThisDrawing.ModelSpace.InsertBlock(alignmentPoint, textString, size, size, size, 0)
       
        'blockRefObj.styleName = "SimpErhu"
        blockRefObj.Layer = "SimpErhu符號"
'
        ipos = ipos + 1
    End If
    
    
'    If this_ef.InOut <> "" Then
'    '內 外
'       '不是 就插入文字
'            textString = this_ef.InOut
'            height = size * 0.47
'            alignmentPoint(0) = insertionPoint(0)
'            alignmentPoint(1) = insertionPoint(1) + (size * 2.13) + (ipos * yAdd * size)
'            alignmentPoint(2) = insertionPoint(2)
'            ' Create the text object in model space
'            Set textObj = ThisDrawing.ModelSpace.AddText(textString, insertionPoint, height)
'            textObj.Alignment = acAlignmentCenter
'            textObj.TextAlignmentPoint = alignmentPoint
'            textObj.styleName = "音符_數字"
'            textObj.Layer = "裝飾符號"
''
'        ipos = ipos + 1
'    End If
'



End Function




Private Function atTableDraw(ByVal the_pt As point, ByVal the_track As Integer, ByVal the_alltempo As Long, ByVal the_isDorp As Boolean) As point

'atTableDraw()
'*the_pt 原點
'*the_pt 現在是第幾軌
'*the_allTempo 現在的拍長是多少
'*the_isDorp 現在是否是符點音符
'


    atTableDraw_bar the_pt, the_track, the_alltempo
    
    Dim ROW_ALL_DEF As Integer
    Dim tmp_modTempo As Integer
    Dim row As Integer


    Dim tmp_modCol As Integer
    Dim col As Integer
    Dim col_b As Integer


    ROW_ALL_DEF = (G.Bar * G.Mete * PARTITION_DEF / (G.Mete2 / 4))
    tmp_modTempo = the_alltempo Mod ROW_ALL_DEF '全部除掉總單位時 後，看還有多少的 單位時
    row = (the_alltempo - tmp_modTempo) \ ROW_ALL_DEF

    tmp_modCol = tmp_modTempo Mod (PARTITION_DEF / (G.Mete2 / 4))
    col = (tmp_modTempo - tmp_modCol) / (PARTITION_DEF / (G.Mete2 / 4)) '取得每行的第幾拍
    col_b = (col Mod G.Mete)  '取得每小節的第幾拍

    '傳出每節的相對位置
    Dim tmp_xbarInterval As Double
    tmp_xbarInterval = (G.PageWidth - G.LeftSpace - G.RightSpace) / ((G.Bar * G.Mete))

    Static lastPoint As New point
    Dim pp As New point
    'col 是每一行的第幾拍，是以一拍為單位來數
    'tmp_modCol 是每一拍的第幾個字的位置
    pp.x = G.LeftSpace + G.BarToNote + col * tmp_xbarInterval
    pp.x = pp.x + (CDbl(tmp_modCol) / CDbl(PARTITION_DEF / (4))) * (amt.LINE_LEN * G.FontSize) '除於 4分之一拍 的問題

    pp.Y = (G.TrackToTrack) * the_track + ((G.TrackToTrack) * (G.Many - 1) + G.LineToLine) * row
    pp.Y = -pp.Y
    pp.x = pp.x + the_pt.x

    '每節單位拍，的微調
    '例  1 5    2 6             1 5  2 6
    '    ----   ----  ->前進成  ---- ----
    '    123456789AB            123456789AB
    pp.x = pp.x + CDbl(col_b) * G.Beat_MIN_X '微調
    '每一單位拍，的微調
    '例  1  5 3   2  6 4             1 53     2 64
    '    ---====  ---====  ->前進成  --==     --==
    '    123456789ABCDEF             123456789ABCDEF
    Static ismodcol As Integer
    If tmp_modCol > 0 Then
        ismodcol = ismodcol + 1
        pp.x = pp.x + ismodcol * G.MIN_X  '微調
    Else
        ismodcol = 0
    End If
    pp.Y = pp.Y + the_pt.Y
    If the_isDorp Then '如果是符點音符，就前近一半
        pp.x = (lastPoint.x + pp.x) / 2
    End If
    
    '是否2個字太近壓到了
    '移至1個字的寬度
    If Abs(lastPoint.x - pp.x) <= amt.A_TEXT_WIDTH * G.FontSize Then
        pp.x = lastPoint.x + amt.A_TEXT_WIDTH * G.FontSize * 1.05
    End If
    
    Set lastPoint = pp
    Set atTableDraw = pp
End Function

Private Function atTableDraw_bar(ByVal the_pt As point, ByVal the_track As Integer, ByVal the_alltempo As Long)
   
    Dim tmp_pLWPoly As AcadPolyline
    'Dim initPoint As New AcGePoint2d()
    Dim startPt As New point
    Dim endPt As New point
    Dim ptlist As New PointList
    
    Dim tmp_trackitem As Integer
    Dim tmp_bardist As Double '一節的距離
    Dim tmp_rowspacing As Double '每行到每行的距離

    tmp_bardist = (G.PageWidth - G.LeftSpace - G.RightSpace) / G.Bar
    tmp_rowspacing = (G.TrackToTrack * (G.Many - 1) + G.LineToLine)
    '這是要畫小節線
    'ROW_ALL_DEF 是每行的總單位數應該多少，如 每小節2/4拍，每行有 7 個小節，則每行的 總單位時應該是 (240*2)*7=3360
    'row 第幾行
    'colunm 第幾欄(在第幾行的第幾欄)
    Dim ROW_ALL_DEF As Integer
    Dim tmp_modTempo As Integer
    Dim row As Integer

    Dim tmp_modCol As Integer
    Dim col As Integer
    Dim col_b As Integer


    ROW_ALL_DEF = (G.Bar * G.Mete * PARTITION_DEF / (G.Mete2 / 4))
    tmp_modTempo = the_alltempo Mod ROW_ALL_DEF '全部除掉總單位時 後，看還有多少的 單位時
    row = (the_alltempo - tmp_modTempo) \ ROW_ALL_DEF

    tmp_modCol = tmp_modTempo Mod (PARTITION_DEF / (G.Mete2 / 4))
    col = (tmp_modTempo - tmp_modCol) / (PARTITION_DEF / (G.Mete2 / 4)) '取得每行的第幾拍
    col_b = (col Mod G.Mete)  '取得每小節的第幾拍
    
    If the_track = 0 Then '只有第一軌才要畫
        If col = 0 And tmp_modCol = 0 Then '這是在第一小節

            startPt.x = the_pt.x + G.LeftSpace
            startPt.Y = -((amt.LINE_PASE + amt.DROP_UP) * G.FontSize) + tmp_rowspacing * row
            startPt.Y = -startPt.Y + the_pt.Y

            endPt.x = the_pt.x + G.LeftSpace
            endPt.Y = G.TrackToTrack * (G.Many - 1) + tmp_rowspacing * row
            endPt.Y = -endPt.Y + the_pt.Y

            ptlist.clean
            ptlist.addpt startPt
            ptlist.addpt endPt
            Set tmp_pLWPoly = ThisDrawing.ModelSpace.AddPolyline(ptlist.list)
            tmp_pLWPoly.ConstantWidth = amt.BAR_WITCH * G.FontSize / 4.6
            tmp_pLWPoly.Layer = "bar"
        End If

        If (col Mod G.Mete) = 0 And (tmp_modCol = 0) Then
            Dim j As Integer
            For j = 0 To G.Many - 1


                startPt.x = the_pt.x + G.LeftSpace + tmp_bardist + col / G.Mete * tmp_bardist

                startPt.Y = -((amt.LINE_PASE + amt.DROP_UP) * G.FontSize) + (G.TrackToTrack * j) + (tmp_rowspacing * row)

                startPt.Y = -startPt.Y + the_pt.Y


                endPt.x = the_pt.x + G.LeftSpace + tmp_bardist + col / G.Mete * tmp_bardist

                endPt.Y = (G.TrackToTrack * j) + (tmp_rowspacing * row)

                endPt.Y = -endPt.Y + the_pt.Y

                ptlist.clean
                ptlist.addpt startPt
                ptlist.addpt endPt
                Set tmp_pLWPoly = ThisDrawing.ModelSpace.AddPolyline(ptlist.list)
                tmp_pLWPoly.ConstantWidth = amt.BAR_WITCH * G.FontSize / 4.6
                tmp_pLWPoly.Layer = "bar"
            Next j
            'm_pLWPoly->setThickness(plineInfo.m_thick);
            'm_pLWPoly->setConstantWidth(plineInfo.m_width);

        End If


    End If

End Function


Private Sub UserForm_Initialize()
    AcadConnect

    Dim dd As Double
    Dim i As Integer
    '字型設定
    Me.cobFontName.AddItem "EUDC"
    Me.cobFontName.AddItem "細明體"
    Me.cobFontName.AddItem "華康行書體"
    Me.cobFontName.AddItem "標楷體"
    
    '字型大小設定
    For dd = 2 To 8 Step 0.5
        Me.cobFontSize.AddItem dd
    Next
    
    '幾聲部設定
    For i = 1 To 8
        Me.cobMany.AddItem i
    Next
    
    '幾拍設定
    Me.cobMete.AddItem "1/4"
    Me.cobMete.AddItem "2/4"
    Me.cobMete.AddItem "3/4"
    Me.cobMete.AddItem "4/4"
    Me.cobMete.AddItem "1/8"
    Me.cobMete.AddItem "3/8"
    Me.cobMete.AddItem "5/8"
    Me.cobMete.AddItem "7/8"
    
    
    
    '每行要幾小節設定
    For i = 2 To 12
        Me.cobBar.AddItem i
    Next
    
    Me.cobFontName.text = "EUDC"
    Me.cobFontSize.text = 3.5
    Me.cobMany.text = 1
    Me.cobMete.text = "4/4"
    Me.cobBar.text = 4

    Me.tbPageWidth = 210
    Me.tbLeftSpace = 14
    Me.tbRightSpace = 14
    Me.tbBarToNote = 2
    Me.tbTrackToTrack = 14
    Me.tbLineToLine = 18
    Me.tbMIN_X = 0.25
    
    AMT_LOAD '這個重要，設定初始資料
End Sub

Attribute VB_Name = "frmInsText"
Attribute VB_Base = "0{166F429A-2158-4465-B3E3-3766D2D1CE88}{9288A683-2D79-4E0A-87E8-DB3814C55EAD}"
Attribute VB_GlobalNameSpace = False
Attribute VB_Creatable = False
Attribute VB_PredeclaredId = True
Attribute VB_Exposed = False
Attribute VB_TemplateDerived = False
Attribute VB_Customizable = False
Option Explicit

Private Sub CommandButton1_Click()
    ' This example prompts for user input of a point. By using the
    ' InitializeUserInput method to define a keyword list, the example can also
    ' return keywords entered by the user.
    
    
    'Me.Hide
    ' Define the valid keywords
    Dim keywordList As String
    keywordList = "1 2 3 4 0"
    Dim strT As String
    
    Dim textObj As AcadText
    Dim textString As String
    Dim insertionPoint(0 To 2) As Double, alignmentPoint(0 To 2) As Double

    Dim height As Double
    Me.Hide
GoToLook:
'On Error GoTo ErrorHandler
On Error Resume Next

    ' Call InitializeUserInput to set up the keywords
    ThisDrawing.Utility.InitializeUserInput 129, keywordList
    ' Get the user input
    Dim returnPnt As Variant
    returnPnt = ThisDrawing.Utility.GetPoint(, "0 1 2 3 4 E(拉) V(推) Q(內) W(外) C(清除): ")
    
    If Err Then
        '**Description 這個要改的
         If StrComp(Err.Description, "使用者輸入的是關鍵字", 1) = 0 Then
         ' One of the keywords was entered
             Dim inputString As String
             Err.clear
             inputString = ThisDrawing.Utility.GetInput
             '取得關鍵字
             Select Case inputString
                Case "0": strT = "b空絃"  '空弦
                Case "1": strT = "Ⅰ"
                Case "2": strT = "Ⅱ"
                Case "3": strT = "Ⅲ"
                Case "4": strT = "Ⅳ"
                Case Else
                    Dim ss As String
                    Dim data As Double
                    ss = Mid(inputString, 1, 1)
                    Select Case ss
                        Case "E", "e": lbPush_d ("拉")
                        Case "V", "v": lbPush_d ("推")
                        Case "Q", "q": lbInOut_d ("內")
                        Case "W", "w": lbInOut_d ("外")
                        Case "T", "t":
                        Case "S", "s":
                            data = Mid(inputString, 2, 10)
                            Me.tbSize = data
                        Case "X", "x":
                            data = Mid(inputString, 2, 10)
                            Me.tbX = data
                        Case "Y", "y":
                            data = Mid(inputString, 2, 10)
                            Me.tbY = data
                        Case "C", "c":
                        '清除全部
                            Me.lbInOut = ""
                            Me.lbInOut.SpecialEffect = fmSpecialEffectEtched
                            
                            Me.lbPush = ""
                            Me.lbPush.SpecialEffect = fmSpecialEffectEtched
                            
                            Me.tbT.text = ""
                            strT = ""
                        Case Else
                            Exit Sub
                    End Select
             End Select
             
             Me.tbT = strT
             
             GoTo GoToLook
         Else
             MsgBox "Error selecting the point: " & Err.Description
             'Err.clear
         End If
    Else
        ' Display point coordinates
        'MsgBox "The WCS of the point is: " & returnPnt(0) & ", " & returnPnt(1) & ", " & returnPnt(2), , "GetInput Example"
         
        ' Define the text object
        insertionPoint(0) = returnPnt(0) + Me.tbX
        insertionPoint(1) = returnPnt(1) + Me.tbY
        insertionPoint(2) = returnPnt(2)
        
        alignmentPoint(0) = insertionPoint(0)
        alignmentPoint(1) = insertionPoint(1)
        alignmentPoint(2) = insertionPoint(2)
        
        Dim ipos As Integer
        Dim yAdd As Double
        ipos = 0
        yAdd = 3 '指法的向上增量
        If Me.tbT <> "" Then
            If Mid(Me.tbT, 1, 1) = "b" Then
            '看是否是圖塊
                Select Case Me.tbT
                    Case "b空絃"
                        'Call ThisDrawing.ModelSpace.InsertBlock(insertionPoint, "二胡_空", 0.75, 0.75, 0.75, 0)
                        textString = "\U+5B80"
                        height = Me.tbSize
                        Set textObj = ThisDrawing.ModelSpace.AddText(textString, insertionPoint, height)
                        textObj.Alignment = acAlignmentCenter
                        textObj.TextAlignmentPoint = alignmentPoint
                        textObj.styleName = "音符_數字"
                        textObj.Layer = "裝飾符號"
                        

                    Case Else
                End Select
            Else
            '不是 就插入文字
                textString = Me.tbT
                height = Me.tbSize
                ' Create the text object in model space
                Set textObj = ThisDrawing.ModelSpace.AddText(textString, insertionPoint, height)
                textObj.Alignment = acAlignmentCenter
                textObj.TextAlignmentPoint = alignmentPoint
                textObj.styleName = "音符_數字"
                textObj.Layer = "裝飾符號"
            End If
            
            ipos = ipos + 1
        End If
        
        If Me.lbInOut.Caption <> "" Then
        
            textString = lbInOut.Caption
            height = Me.tbSize
            
                
            insertionPoint(0) = returnPnt(0) + Me.tbX
            insertionPoint(1) = returnPnt(1) + Me.tbY + (yAdd * ipos)
            insertionPoint(2) = returnPnt(2)
            
            alignmentPoint(0) = insertionPoint(0)
            alignmentPoint(1) = insertionPoint(1)
            alignmentPoint(2) = insertionPoint(2)
            
            
            ' Create the text object in model space
            Set textObj = ThisDrawing.ModelSpace.AddText(textString, insertionPoint, height)
            textObj.Alignment = acAlignmentCenter
            textObj.TextAlignmentPoint = alignmentPoint
            textObj.styleName = "音符_數字"
            textObj.Layer = "裝飾符號"
            ipos = ipos + 1
        End If
        
        Dim MtextObj As AcadMText
        If Me.lbPush.Caption <> "" Then

'            If Me.lbPush.Caption = "拉" Then
'                textString = "扱"
'            ElseIf Me.lbPush.Caption = "推" Then
'                textString = "憨"
'            End If
''
'            height = Me.tbSize * 2
'
'            insertionPoint(0) = returnPnt(0) + Me.tbX
'            insertionPoint(1) = returnPnt(1) + Me.tbY + (yAdd * ipos)
'            insertionPoint(2) = returnPnt(2)
'
'            alignmentPoint(0) = insertionPoint(0)
'            alignmentPoint(1) = insertionPoint(1)
'            alignmentPoint(2) = insertionPoint(2)
'
'            Set textObj = ThisDrawing.ModelSpace.AddText(textString, insertionPoint, height)
'            textObj.StyleName = "MMP2005"
'            textObj.Layer = "MMP2005符號"
'            textObj.Alignment = acAlignmentCenter
'            textObj.TextAlignmentPoint = alignmentPoint
'


            If Me.lbPush.Caption = "拉" Then
                textString = "\U+020C"
            ElseIf Me.lbPush.Caption = "推" Then
                textString = "\U+020A"
            End If
            
            height = Me.tbSize * 3.6
            
                
            insertionPoint(0) = returnPnt(0) + Me.tbX - 0.31
            insertionPoint(1) = returnPnt(1) + Me.tbY + (yAdd * ipos) - (Me.tbSize * 2.8)
            insertionPoint(2) = returnPnt(2)
            
            alignmentPoint(0) = insertionPoint(0)
            alignmentPoint(1) = insertionPoint(1)
            alignmentPoint(2) = insertionPoint(2)
            
            Set textObj = ThisDrawing.ModelSpace.AddText(textString, insertionPoint, height)
            textObj.styleName = "SimpErhu"
            textObj.Layer = "SimpErhu符號"
            textObj.Alignment = acAlignmentCenter
            textObj.TextAlignmentPoint = alignmentPoint
            
            ipos = ipos + 1
        End If
        
        
        
        'Err.clear
        GoTo GoToLook
    End If
ErrorHandler:

    
End Sub


Private Sub CommandButton2_Click()
'置換 推拉文字，改為 圖塊
On Error Resume Next
    Dim Object As Object
    Dim PickedPoint As Variant, TransMatrix As Variant, ContextData As Variant
    
        
TRYAGAIN:
        Me.Hide
While 1
    ' Get information about selected object
    ThisDrawing.Utility.GetSubEntity Object, PickedPoint, TransMatrix, ContextData


    Dim objText As AcadText
    Dim objBlock As AcadBlockReference
    Dim pt As Variant
    Dim SStr As String
    Dim insPt(2) As Double
        If (Object.ObjectName = "AcDbText") Then
            Set objText = Object
            
            If objText.textString = "\U+020A" Then
                insPt(0) = objText.insertionPoint(0) + 1.51
                insPt(1) = objText.insertionPoint(1) + 4.7
                insPt(2) = objText.insertionPoint(2)
                Set objBlock = ThisDrawing.ModelSpace.InsertBlock(insPt, "b推", 4, 4, 4, 0)
                objBlock.Layer = "裝飾符號"
                objText.Delete
            ElseIf objText.textString = "\U+020C" Then
                insPt(0) = objText.insertionPoint(0) + 1.51
                insPt(1) = objText.insertionPoint(1) + 4.65
                insPt(2) = objText.insertionPoint(2)
                Set objBlock = ThisDrawing.ModelSpace.InsertBlock(insPt, "b拉", 4, 4, 4, 0)
                objBlock.Layer = "裝飾符號"
                objText.Delete
            End If
        Else
            Exit Sub
        End If
Wend
    
End Sub

Private Sub lbPush_Click()
    
    
    If Me.lbPush.Caption = "拉" Then
        Me.lbPush.Caption = "推"
        Me.lbPush.SpecialEffect = fmSpecialEffectFlat
    ElseIf Me.lbPush.Caption = "推" Then
        Me.lbPush.Caption = ""
        Me.lbPush.SpecialEffect = fmSpecialEffectEtched
    Else
        Me.lbPush.Caption = "拉"
        Me.lbPush.SpecialEffect = fmSpecialEffectFlat
    End If
End Sub
Private Sub lbPush_d(data As String)
    If data = "推" Then
        Me.lbPush.Caption = "推"
        Me.lbPush.SpecialEffect = fmSpecialEffectFlat
    ElseIf data = "拉" Then
        Me.lbPush.Caption = "拉"
        Me.lbPush.SpecialEffect = fmSpecialEffectFlat
    End If
End Sub
Private Sub lbInOut_Click()
    If Me.lbInOut.Caption = "外" Then
        Me.lbInOut.Caption = "內"
        Me.lbInOut.SpecialEffect = fmSpecialEffectFlat
    ElseIf Me.lbInOut.Caption = "內" Then
        Me.lbInOut.Caption = ""
        Me.lbInOut.SpecialEffect = fmSpecialEffectEtched
    Else
        Me.lbInOut.Caption = "外"
        Me.lbInOut.SpecialEffect = fmSpecialEffectFlat
    End If
End Sub

Private Sub lbInOut_d(data As String)
    If data = "內" Then
        Me.lbInOut.Caption = "內"
        Me.lbInOut.SpecialEffect = fmSpecialEffectFlat
    ElseIf data = "外" Then
        Me.lbInOut.Caption = "外"
        Me.lbInOut.SpecialEffect = fmSpecialEffectFlat
    End If
End Sub

Attribute VB_Name = "frmMIDIFILE"
Attribute VB_Base = "0{39205114-3B82-412C-B8EA-709FFB713E95}{A50C5A05-055E-42F1-8759-516B65FD635E}"
Attribute VB_GlobalNameSpace = False
Attribute VB_Creatable = False
Attribute VB_PredeclaredId = True
Attribute VB_Exposed = False
Attribute VB_TemplateDerived = False
Attribute VB_Customizable = False
Option Explicit
    Dim ptn0(10) As Byte
    Dim ptn1(4) As Byte
    Dim ptn2(3) As Byte
    Dim ptn_len(3) As Byte  '這是記 ptn0,ptn1,ptn2 的長度
Sub setMain()
    'MIDI檔標誌MThd
     ptn0(1) = AscW("M")
     ptn0(2) = AscW("T")
     ptn0(3) = AscW("h")
     ptn0(4) = AscW("d")
     ptn0(5) = 0
     ptn0(6) = 0
     ptn0(7) = 0
     ptn0(8) = 6
     ptn0(9) = 0
     ptn0(10) = 1
     
     '磁軌標誌MTrk
     ptn1(1) = AscW("M")
     ptn1(2) = AscW("T")
     ptn1(3) = AscW("r")
     ptn1(4) = AscW("k")
     
     '磁軌結束資訊
     ptn2(1) = &HFF
     ptn2(2) = &H2F
     ptn2(3) = &H0
     
     '這是記 ptn0,ptn1,ptn2 的長度
     ptn_len(1) = 10: ptn_len(2) = 4: ptn_len(3) = 3:
    'Public Shared ptn_tbl()() As Byte = {ptn0, ptn1, ptn2}
    
End Sub
Private Sub CommandButton1_Click()
    setMain
    
    Dim vbaPATH As String
    Dim imagePATH As String
    Dim pos As Integer
    '取得 dvb 的目錄
    vbaPATH = ThisDrawing.Application.VBE.ActiveVBProject.FileName
    pos = InStrRev(vbaPATH, "\")
    imagePATH = Mid(vbaPATH, 1, pos)

    Dim MIDI_FILE As Integer
    Dim path_1 As String
    Dim i
    MIDI_FILE = 1
    path_1 = imagePATH & "test3.txt"
    
    Open path_1 For Binary Access Write As #MIDI_FILE
    For i = 0 To ptn_len(1)
        Put #MIDI_FILE, , ptn0(i)
    Next
    Put #MIDI_FILE, , 12
    Put #MIDI_FILE, , 130
    Put #MIDI_FILE, , 12
    Put #MIDI_FILE, , 13
    Put #MIDI_FILE, , "Apple"
    Put #MIDI_FILE, , "Banana"
    Put #MIDI_FILE, , "Cat"
    Put #MIDI_FILE, , "Dog"
    Put #MIDI_FILE, , "Erase"
    Put #MIDI_FILE, , "Foolish"
    Put #MIDI_FILE, , "Hot"
    Close #MIDI_FILE
End Sub

Attribute VB_Name = "frmMusical"
Attribute VB_Base = "0{8B4C14AC-9DDE-4344-9B75-3563BB2A52CF}{F5D8A6B6-7F32-4BBF-8E4F-12D8CE8D0552}"
Attribute VB_GlobalNameSpace = False
Attribute VB_Creatable = False
Attribute VB_PredeclaredId = True
Attribute VB_Exposed = False
Attribute VB_TemplateDerived = False
Attribute VB_Customizable = False
Private Sub CommandButton1_Click()
    '插入單一Text
    Dim MusicText As NnmText
    Dim basePnt(0 To 2) As Double
    Dim cenPnt(0 To 2) As Double
    Dim returnPnt As Variant
    Dim pt As Variant
    Dim rad As Integer
    Me.Hide
    returnPnt = ThisDrawing.Utility.GetPoint(basePnt, "\n選擇要插入的點")
    

    'Set SEOBJ = New SmileyEntity
    pt = returnPnt
    Set MusicText = ThisDrawing.ModelSpace.AddCustomObject("MUSICTEXT")
    'Call MusicText.setNewObject(returnPnt, 1)
    Call MusicText.setData(pt, "ba!1=z", "MMP2005", 44)
    returnPnt(0) = returnPnt(0) + 31.83
    
End Sub

Private Sub CommandButton2_Click()
    '插入多個Text
    Dim MusicText As NnmText
    Dim basePnt(0 To 2) As Double
    Dim cenPnt(0 To 2) As Double
    Dim returnPnt As Variant
    Dim pt As Variant
    Dim rad As Integer
    Me.Hide
    returnPnt = ThisDrawing.Utility.GetPoint(basePnt, "\n選擇要插入的點")
    

    'Set SEOBJ = New SmileyEntity
    pt = returnPnt
    pt(0) = 0: pt(1) = 0: pt(2) = 0:
    Set MusicText = ThisDrawing.ModelSpace.AddCustomObject("MUSICTEXT")
    'Call MusicText.setNewObject(returnPnt, 1)
    Call MusicText.setData(returnPnt, "bf!1=z", "MMP2005", 44)
    returnPnt(0) = returnPnt(0) + 31.83
    Set MusicText = ThisDrawing.ModelSpace.AddCustomObject("MUSICTEXT")
    Call MusicText.setNewObject(returnPnt, 1)
    Call MusicText.setData(returnPnt, " A?2=c", "MMP2005", 44)
    returnPnt(0) = returnPnt(0) + 31.83
    Set MusicText = ThisDrawing.ModelSpace.AddCustomObject("MUSICTEXT")
    Call MusicText.setNewObject(returnPnt, 1)
    Call MusicText.setData(returnPnt, "#t.3=a", "MMP2005", 44)
    
End Sub

Private Sub CommandButton33_Click()
'取得物件 MusicText
'用x 軸來鏈結
On Error GoTo EndJoin

    Dim ent As Object
    Me.Hide

StartJoin:
    Dim SSetColl As AcadSelectionSets
    Set SSetColl = ThisDrawing.SelectionSets
    
    ' Create a SelectionSet named "TEST" in the current drawing
    Dim ssetObj As AcadSelectionSet
  

    If SSetColl.count > 0 Then
        SSetColl.item(0).Delete
    End If
    Set ssetObj = SSetColl.add("TEST")

    ssetObj.SelectOnScreen
    
    '排序陣列
    Dim TheArray As Variant
    Dim TheArrayEnt As Variant
    Dim coI As Integer
    Dim i As Long
    
    ' Add the dimstyle to the dimstyles collection
    coI = 0
  ' 找出圖面中的每一個選集
    For Each ent In ssetObj
        If (ent.ObjectName = "MusicText") Then
            coI = coI + 1
        End If
    Next
    
    '只有一個，不用排序了
    If coI < 1 Then
        GoTo StartJoin
    End If
    
    ReDim TheArray(coI - 1)
    ReDim TheArrayEnt(coI - 1)
    
    coI = 0
    Dim MTobj As NnmText
    Dim pt As Variant
    For Each ent In ssetObj
        If (ent.ObjectName = "MusicText") Then
            pt = ent.insertionPoint()
            TheArray(coI) = pt(0)
            Set TheArrayEnt(coI) = ent
            coI = coI + 1
        End If
    Next
    
    
    
    '排序開始
    SelectionSortMaxTow TheArray, TheArrayEnt
    
    For i = 0 To UBound(TheArray)
        If i = 0 Then
            TheArrayEnt(i).LeftLink = 0
            TheArrayEnt(i).RightLink = TheArrayEnt(i + 1).ObjectID
        ElseIf i = UBound(TheArray) Then
            TheArrayEnt(i).LeftLink = TheArrayEnt(i - 1).ObjectID
            TheArrayEnt(i).RightLink = 0
        Else
            TheArrayEnt(i).RightLink = TheArrayEnt(i + 1).ObjectID
        End If
        TheArrayEnt(i).Update
    Next
GoTo StartJoin

EndJoin:
End Sub

Private Sub CommandButton3_Click()

'取得物件 MusicText
'用x 軸來鏈結
On Error GoTo EndJoin

    Dim ent As Object
    Me.Hide

StartJoin:
    Dim SSetColl As AcadSelectionSets
    Set SSetColl = ThisDrawing.SelectionSets
    
    ' Create a SelectionSet named "TEST" in the current drawing
    Dim ssetObj As AcadSelectionSet
  

    If SSetColl.count > 0 Then
        SSetColl.item(0).Delete
    End If
    Set ssetObj = SSetColl.add("TEST")

    ssetObj.SelectOnScreen
    
    '排序陣列
    Dim TheArray As Variant
    Dim TheArrayEnt As Variant
    Dim coI As Integer
    Dim i As Long
    
    ' Add the dimstyle to the dimstyles collection
    coI = 0
  ' 找出圖面中的每一個選集
    For Each ent In ssetObj
        If (ent.ObjectName = "MusicText") Then
            coI = coI + 1
        End If
    Next
    
    ReDim TheArray(coI - 1)
    ReDim TheArrayEnt(coI - 1)
    
    coI = 0
    Dim MTobj As NnmText
    Dim pt As Variant
    For Each ent In ssetObj
        If (ent.ObjectName = "MusicText") Then
            pt = ent.insertionPoint()
            TheArray(coI) = pt(0)
            Set TheArrayEnt(coI) = ent
            coI = coI + 1
        End If
    Next
    
    Me.addMusicJoin TheArrayEnt
EndJoin:
End Sub

Private Sub CommandButton4_Click()
'清除 MusicText 的鏈結
On Error Resume Next
    Dim ent As Object

   
    Dim SSetColl As AcadSelectionSets
    Set SSetColl = ThisDrawing.SelectionSets
    
    ' Create a SelectionSet named "TEST" in the current drawing
    Dim ssetObj As AcadSelectionSet
  
    If SSetColl.count > 0 Then
        SSetColl.item(0).Delete
    End If
    Set ssetObj = SSetColl.add("TEST")
    Me.Hide
    ssetObj.SelectOnScreen
    
    '排序陣列
    Dim TheArray As Variant
    Dim TheArrayEnt As Variant
    Dim coI As Integer
    Dim i As Long
    
    ' Add the dimstyle to the dimstyles collection
    coI = 0
  ' 找出圖面中的每一個選集
    For Each ent In ssetObj
        If (ent.ObjectName = "MusicText") Then
            ent.RightLink = 0
            ent.LeftLink = 0
        End If
    Next
End Sub


Public Function addMusicJoin(ByVal the_Ids As Variant)

'取得物件 MusicText
'用x 軸來鏈結
On Error Resume Next

    Dim ent As Object
    
    '排序陣列
    Dim TheArray As Variant
    Dim TheArrayEnt As Variant
    Dim coI As Integer
    Dim i As Long
    
    ' Add the dimstyle to the dimstyles collection
    coI = 0
  ' 找出圖面中的每一個選集
    For i = 0 To UBound(the_Ids, 1)
        If the_Ids(i).ObjectName = "MusicText" Then
            coI = coI + 1
        End If
    Next

    
    '只有一個，不用排序了
    If coI < 1 Then
        Exit Function
    End If
    
    ReDim TheArray(coI - 1)
    ReDim TheArrayEnt(coI - 1)
    
    coI = 0
    Dim MTobj As NnmText
    Dim pt As Variant
    
    For i = 0 To UBound(the_Ids, 1)
        Set ent = the_Ids(i)
        If (ent.ObjectName = "MusicText") Then
            pt = ent.insertionPoint()
            TheArray(coI) = pt(0)
            Set TheArrayEnt(coI) = ent
            coI = coI + 1
            
            
            Dim minExt As Variant
            Dim maxExt As Variant
    
            ent.GetBoundingBox minExt, maxExt
            Set MTobj = ent
            minExt = MTobj.GripLeft()
            
            
        End If
    Next
    
    
    
    '排序開始
    SelectionSortMaxTow TheArray, TheArrayEnt
    
    For i = 0 To UBound(TheArray)
        If i = 0 Then
            TheArrayEnt(i).LeftLink = 0
            TheArrayEnt(i).RightLink = TheArrayEnt(i + 1).ObjectID
        ElseIf i = UBound(TheArray) Then
            TheArrayEnt(i).LeftLink = TheArrayEnt(i - 1).ObjectID
            TheArrayEnt(i).RightLink = 0
        Else
            TheArrayEnt(i).RightLink = TheArrayEnt(i + 1).ObjectID
        End If
        TheArrayEnt(i).Update
    Next


EndJoin:
End Function

Sub getGrip()

End Sub
        

Public Function eraseMTlink(ByVal the_id As Variant)
End Function

Private Sub CommandButton5_Click()

Dim ttt As NnmText
Dim minExt As Variant
    Dim maxExt As Variant
    
    
    lineObj.GetBoundingBox

    ttt.GetBoundingBox minExt, maxExt
End Sub


Private Sub CommandButton6_Click()

'取得 grip 數值

On Error Resume Next
    Dim Object As Object
    Dim PickedPoint As Variant, TransMatrix As Variant, ContextData As Variant
    
        
TRYAGAIN:
        Me.Hide

    ' Get information about selected object
    ThisDrawing.Utility.GetSubEntity Object, PickedPoint, TransMatrix, ContextData


    Dim MTobj As NnmText
    Dim pt As Variant
    Dim SStr As String
    
        If (Object.ObjectName = "MusicText") Then
            Set MTobj = Object
            
            pt = MTobj.GripLeft()
            SStr = "GripLeft = " & Format(pt(0), "0.00") & ", " & Format(pt(1), "0.00") & vbCrLf
            
            pt = MTobj.GripMid()
            SStr = SStr & "nGripMid = " & Format(pt(0), "0.00") & ", " & Format(pt(1), "0.00") & vbCrLf
            
            pt = MTobj.GripRight()
            SStr = SStr & "nGripRight = " & Format(pt(0), "0.00") & ", " & Format(pt(1), "0.00") & vbCrLf
             
            pt = MTobj.GripLeftDown()
            SStr = SStr & "nGripLeftDown = " & Format(pt(0), "0.00") & ", " & Format(pt(1), "0.00") & vbCrLf
            
            pt = MTobj.GripMidUp()
            SStr = SStr & "nGripMidUp = " & Format(pt(0), "0.00") & ", " & Format(pt(1), "0.00") & vbCrLf
            
            
            ThisDrawing.Utility.prompt SStr
        End If
End Sub







Private Sub CommandButton7_Click()
    ' This example returns the current layer
    ' and then adds a new layer.
    ' Finally, it returns the layer to the previous setting.
    Dim currLayer As AcadLayer
    Dim newLayer As AcadLayer
    
    ' Return the current layer of the active document
    Set currLayer = ThisDrawing.ActiveLayer
    MsgBox "The current layer is " & currLayer.name, vbInformation, "ActiveLayer Example"
    
    ' Create a Layer and make it the active layer
    Dim i As Integer
    For i = 0 To ThisDrawing.Layers.count - 1
        Set newLayer = ThisDrawing.Layers(i)
        Me.TextBox1 = Me.TextBox1 & "datalayer(i,1) = """ & newLayer.name & """ : datalayer(i,2) =  " & newLayer.TrueColor.ColorIndex & vbCrLf
        
        
    Next
    
End Sub

Private Sub CommandButton8_Click()
    Dim TextColl As AcadTextStyles
    Set TextColl = ThisDrawing.TextStyles
    
    ' Create a Text style named "TEST" in the current drawing
    Dim textStyle As AcadTextStyle
    
    Dim i As Integer
    For i = 0 To ThisDrawing.TextStyles.count - 1
        Set textStyle = ThisDrawing.TextStyles(i)
        Me.TextBox1 = Me.TextBox1 & "dataStyles(" & i & ",1)=""" & textStyle.name & """" & vbCrLf _
            & "dataStyles(" & i & ",2)=""" & textStyle.fontFile & """" & vbCrLf _
            & "dataStyles(" & i & ",3)=""" & textStyle.BigFontFile & """" & vbCrLf
    Next
    
    
End Sub



Private Sub CommandButton9_Click()
    Dim str As Variant
    Dim i As Integer
    str = GetWindowsFonts
    
    For i = 0 To UBound(str)
        Me.TextBox1 = Me.TextBox1 & str(i) & vbCrLf
    Next
End Sub

Attribute VB_Name = "frmPoline2Txt"
Attribute VB_Base = "0{A1817E75-A7EE-4452-A2E1-7AFEAE8EDC2E}{AFC5B001-9EE5-45EA-BF1E-F61ED9C26DA7}"
Attribute VB_GlobalNameSpace = False
Attribute VB_Creatable = False
Attribute VB_PredeclaredId = True
Attribute VB_Exposed = False
Attribute VB_TemplateDerived = False
Attribute VB_Customizable = False
Option Explicit


    Dim g_object As AcadLWPolyline
Function get_mulitpoint() As Integer
    Dim str As String
    Dim i As Integer
    Dim getPT As Double
    Dim ina As Integer
    str = ""
    If (g_object.ObjectName <> "AcDbPolyline") Then
        get_mulitpoint = 1
        Exit Function
    End If
    Dim pointWCS(2) As Double
    Dim pointUCS As Variant
    pointWCS(0) = 0#
    pointWCS(1) = 0#
    pointWCS(2) = 0#
    


    For i = 0 To UBound(g_object.Coordinates)
        getPT = g_object.Coordinates(i)
        If (i Mod 2) = 0 Then
            pointWCS(0) = getPT
            pointUCS = ThisDrawing.Utility.TranslateCoordinates(pointWCS, acWorld, acUCS, False)
            ina = pointUCS(0)
        Else
            pointWCS(1) = getPT
            pointUCS = ThisDrawing.Utility.TranslateCoordinates(pointWCS, acWorld, acUCS, False)
            ina = pointUCS(1)
        End If
        
        If i = 0 Then
            str = ina
        Else
            str = str & "," & ina
        End If
        If Len(str) > 200 Then
            ThisDrawing.Utility.prompt (str)
            str = ""
        End If
    Next
    ThisDrawing.Utility.prompt (str)
    Me.TextBox1 = Me.TextBox1 & str
    get_mulitpoint = 0
End Function

Sub Example_SelectOnScreen() 'AutoCAD 取得 LWPolyLine 的各點
 ' Have the user enter a point
    Dim pointG As Variant
    pointG = ThisDrawing.Utility.GetPoint(, "Enter a point to translate:")
    

    Dim ucsObj As AcadUCS
    Dim origin(0 To 2) As Double
    Dim xAxisPnt(0 To 2) As Double
    Dim yAxisPnt(0 To 2) As Double
    
    ' Define the UCS
    xAxisPnt(0) = pointG(0) + 5: xAxisPnt(1) = pointG(1): xAxisPnt(2) = pointG(2)
    yAxisPnt(0) = pointG(0): yAxisPnt(1) = pointG(1) + 5: yAxisPnt(2) = pointG(2)
    
    ' Add the UCS to the UserCoordinatesSystems collection
    Set ucsObj = ThisDrawing.UserCoordinateSystems.add(pointG, xAxisPnt, yAxisPnt, "New_UCS")
    ThisDrawing.ActiveUCS = ucsObj


    
    ' Create the selection set
    Dim ssetObj As AcadSelectionSet
    'Set ssetObj = ThisDrawing.SelectionSets.Add("TEST_SSET")
    If ThisDrawing.SelectionSets.count = 0 Then
        Set ssetObj = ThisDrawing.SelectionSets.add("TEST_SSET")
    Else
        Set ssetObj = ThisDrawing.SelectionSets.item(0)
        ssetObj.clear
    
    End If
    
    ' Add objects to a selection set by prompting user to select on the screen
    ssetObj.SelectOnScreen
    ssetObj.item (0)
    Dim returnPnt As Variant
    Dim str As String
    Dim strAll As String
    Dim i As Integer
    Dim ina As Integer
    Dim counta As Integer
    counta = ssetObj.count()
    
    str = ""
    strAll = ""
    ThisDrawing.Utility.prompt ("drawXY=")
    
    ' Return a point using a prompt
    ' Translate the point into UCS coordinates
    For i = 0 To counta - 1
        Set g_object = ssetObj.item(i)
        ina = get_mulitpoint
        If (i <> counta - 1) And (ina = 0) Then
            ThisDrawing.Utility.prompt (",o,")
            
            Me.TextBox1 = Me.TextBox1 & ",o,"
        End If
    Next


End Sub



Sub scale_SelectOnScreen() 'AutoCAD 取得 LWPolyLine 的各點
 ' Have the user enter a point
    Dim pointG As Variant
    pointG = ThisDrawing.Utility.GetPoint(, "Enter a point to translate:")
    

    Dim ucsObj As AcadUCS
    Dim origin(0 To 2) As Double
    Dim xAxisPnt(0 To 2) As Double
    Dim yAxisPnt(0 To 2) As Double
    
    ' Define the UCS
    origin(0) = pointG(0): origin(1) = pointG(1): origin(2) = pointG(2)
    xAxisPnt(0) = pointG(0) + 5: xAxisPnt(1) = pointG(1): xAxisPnt(2) = pointG(2)
    yAxisPnt(0) = pointG(0): yAxisPnt(1) = pointG(1) + 5: yAxisPnt(2) = pointG(2)
    


    
    ' Create the selection set
    Dim ssetObj As AcadSelectionSet
    'Set ssetObj = ThisDrawing.SelectionSets.Add("TEST_SSET")
    If ThisDrawing.SelectionSets.count = 0 Then
        Set ssetObj = ThisDrawing.SelectionSets.add("TEST_SSET")
    Else
        Set ssetObj = ThisDrawing.SelectionSets.item(0)
        ssetObj.clear
    
    End If
    
    ' Add objects to a selection set by prompting user to select on the screen
    ssetObj.SelectOnScreen
    ssetObj.item (0)
    Dim returnPnt As Variant
    Dim str As String
    Dim dd As AcadLWPolyline
    Dim i As Integer
    Dim ina As Integer
    Set dd = ssetObj.item(0)
    str = ""
    ' Return a point using a prompt
        ' Translate the point into UCS coordinates
    Dim pointWCS(2) As Double
    Dim pointUCS As Variant
    pointWCS(0) = 0#
    pointWCS(1) = 0#
    pointWCS(2) = 0#
    

    dd.ScaleEntity pointG, 1.03179

    'ThisDrawing.Utility.Prompt (str)
    Me.TextBox1 = str

End Sub



Private Sub CommandButton1_Click()
    Me.TextBox1 = ""
    Me.Hide
    Example_SelectOnScreen
    Me.Show
End Sub

Private Sub CommandButton2_Click()

'使用 VB 建立線： (工程引用'AutoCad 2004 Type Library')
     On Error Resume Next
'    Dim acadApp As AcadApplication
'    Set acadApp = GetObject(, "AutoCAD.Application.16")
'    If Err Then
'        Err.clear
'        Set acadApp = CreateObject("AutoCAD.Application.16")
'        If Err Then
'            MsgBox Err.Description
'            Exit Sub
'        End If
'    End If
'    acadApp.Visible = True
'    Dim acadDoc As AcadDocument
'    Set acadDoc = acadApp.ActiveDocument
    

    Dim plineObj As AcadPolyline
    Dim stXY() As String
    Dim ReadData() As String
    Dim pt(1000, 2) As Double
    Dim ptlist() As Double
  
    
    Dim ssst As String
    ssst = Replace(Me.TextBox1, vbCrLf, ",")
    ssst = Replace(ssst, vbTab, ",")
    ssst = Replace(ssst, ",", ",")
    ssst = Replace(ssst, "  ", ",")
    ssst = Replace(ssst, "  ", ",")
    
    ReadData = Split(ssst, ",")
    
    Dim i As Integer
    Dim posI As Integer
    Dim chkXY As Integer
    
    posI = 0
    chkXY = 0
    For i = 0 To UBound(ReadData)
        If ReadData(i) <> "" Then
            If chkXY = 0 Then
                pt(posI, 0) = ReadData(i)
                chkXY = 1
            Else
                pt(posI, 1) = ReadData(i)
                posI = posI + 1
                chkXY = 0
            End If
        End If
    Next
    If posI <= 1 Then
        Exit Sub
    End If
    ReDim ptlist((posI * 3) - 1)
    Dim iScale As Double
    iScale = tbSCALE
    If iScale = 0 Then
        iScale = 1
    End If
    
    For i = 0 To posI
        ptlist(i * 3) = pt(i, 0) * iScale
        ptlist(i * 3 + 1) = pt(i, 1) * iScale
    Next
    
    Dim pointG As Variant
    pointG = ThisDrawing.Utility.GetPoint(, "要畫的原點:")
    
    Dim ucsObj As AcadUCS
    Dim origin(0 To 2) As Double
    Dim xAxisPnt(0 To 2) As Double
    Dim yAxisPnt(0 To 2) As Double
    
    ' Define the UCS
    xAxisPnt(0) = pointG(0) + 5: xAxisPnt(1) = pointG(1): xAxisPnt(2) = pointG(2)
    yAxisPnt(0) = pointG(0): yAxisPnt(1) = pointG(1) + 5: yAxisPnt(2) = pointG(2)
    
    ' Add the UCS to the UserCoordinatesSystems collection
    Set ucsObj = ThisDrawing.UserCoordinateSystems.add(pointG, xAxisPnt, yAxisPnt, "New_UCS")
    ThisDrawing.ActiveUCS = ucsObj
    
    
    Set plineObj = ThisDrawing.ModelSpace.AddPolyline(ptlist)
    
    
    ZoomAll
    
'    Set acadDoc = Nothing
'    Set acadApp = Nothing
   
End Sub

Attribute VB_Name = "point"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit


Public x As Double
Public Y As Double
Public z As Double

Sub c(xPt As Variant, yPt As Variant, zPt As Variant)
        x = xPt
        Y = yPt
        z = zPt
End Sub
Sub a(varPt As Variant)
    If UBound(varPt) = 2 Then
        x = varPt(0)
        Y = varPt(1)
        z = varPt(2)
    End If
    
End Sub

Function at() As Double()
    Dim dd(0 To 2) As Double
    dd(0) = x
    dd(1) = Y
    dd(2) = z
     at = dd
End Function
Function copy() As point
    Dim pp As point
    Set pp = New point
    pp.c x, Y, z
    Set copy = pp
End Function

Attribute VB_Name = "preferences"
Option Explicit

Type AMusicType
    DEFINE_FontFileName  As String          '預設字型的名字
    DEFINE_TEXT_SIZE As Double          '預設字型的大小

    
    A_TEXT_WIDTH   As Double   '預設一個字的寬度  字形的 百分比

    LINE_PASE As Double '//這是從原點 要高 字形的 百分比
    LINE_JUMP   As Double                   '每一個拍線和拍線的間格 字形的 百分比
    LINE_THICKNESS   As Double                   '這是拍線的厚度 字形的 百分比
    LINE_LEN   As Double                   '這是拍線的長度 字形的 百分比

    DROP_UP   As Double                   '高八度的位置  字形的 百分比
    DROP_DOWN   As Double                   '低八度的位置  字形的 百分比
    DROP_CIRCLE_RADIUS_SIZE   As Double                   '圓的 直徑 SIZE 字形的 百分比
    DROP_INTERVAL  As Double                   '每八度的間距 字形的 百分比
    DROP_ADD_LINE_INTERVAL  As Double                   '下點 多一條線點要下去多少  字形的 百分比

    BAR_WITCH As Double    '小節線的粗細

    'IsGiFill As Boolean                 '在閉合的圖形元素上產生填充區域
    IsGiFill As Boolean                 '是否填充區域
    IsDebugDialog As Boolean                 '是否叫出 DebugDialog

    IsDrawCursory As Boolean                 '是否 繪自定的點
    mHowData As Integer        '有多少行資料
    
    iTONE As Integer         ' * 行
    iFinge As Integer    '這是指法行     _+)(*&
    iScale  As Integer     '這是過低音行   .,:;
    iNote  As Integer      '這為主行       1234567.|l
    iTempo  As Integer    '這是拍子       -=368acefz
    iTowFinge  As Integer     '這是指法行第二行  _+)(*&
    iSlur  As Integer         ' 連音符行    (3456)
    
    L_BUF_MD  As Integer   '這是看Buf_md要多少行
    L_WHAT  As Integer    '這是指法看要放在那一行
    
    
    
    f一指 As Integer
    f二指 As Integer
    f三指 As Integer
    f四指 As Integer
    f空弦 As Integer
    f揉弦 As Integer
    
    '2015/1/10 設定圖塊的資料，駐點的位置不一樣
    
    bkMidHight As Double    '物件中間下點的高度
    bkMidUpHight As Double    '物件中間上點的高度
    
    bkInster_Line_H As Double    '物件原點跟拍線的高度
    

End Type

Public amt As AMusicType


'MusicTextBlock  畫圖塊用資料

Public Type MusicFing
    sTONE As String        ' 升降記號 行
    sFinge As String   '這是指法行     _+)(*&
    sScale As String   '這是高低音行   .,:;
    sNote As String   '這為主行       1234567.|l
    sTempo As String   '這是拍子       -=368acefz
    sTowFinge As String   '這是指法行第二行  _+)(*&
    sSlur As String
    
    iScale As Integer     '這是高低音行   .,:;
    iNote As Integer     '這為主行       1234567.|l
    iTempo As Integer    '這是拍子       -=368acefz
    mfPosition As point    '這是看這第一指法字上下移多少
    mfTowPosition As point '這是看這第二指法字上下移多少
End Type


'音附的駐點位置
Public Type GripPoints
    gptMid As point       '在正中間
    gptLeftDown As point     '在左下
    gptMidUp As point     '在中上
    gptLeft As point      '在左中
    gptRight As point      '在右中
    atPt As point           '備注點
End Type

    
    ''''''''''''''''''''''''''''''''''
Sub AMT_LOAD()
    Dim DEFINE_TEXT_SIZE  As Double
    amt.DEFINE_FontFileName = "細明體"              '預設字型的名字
    amt.DEFINE_TEXT_SIZE = 1000              '預設字型的大小
    DEFINE_TEXT_SIZE = 1000
    
    amt.A_TEXT_WIDTH = 726# / DEFINE_TEXT_SIZE               '預設一個字的寬度  字形的 百分比
    
    amt.LINE_PASE = 592.2 / DEFINE_TEXT_SIZE            '這是從原點 要高 字形的 百分比
    amt.LINE_JUMP = 139.7 / DEFINE_TEXT_SIZE            '每一個拍線和拍線的間格 字形的 百分比
    amt.LINE_THICKNESS = 55.9 / DEFINE_TEXT_SIZE            '這是拍線的厚度 字形的 百分比
    amt.LINE_LEN = 723.5 / DEFINE_TEXT_SIZE            '這是拍線的長度 字形的 百分比
    
    amt.DROP_UP = 1950# / DEFINE_TEXT_SIZE             '高八度的位置  字形的 百分比
    amt.DROP_DOWN = 500# / DEFINE_TEXT_SIZE             '低八度的位置  字形的 百分比
    amt.DROP_CIRCLE_RADIUS_SIZE = 200# / DEFINE_TEXT_SIZE / 2           '圓的 直徑 SIZE 字形的 百分比
    amt.DROP_INTERVAL = 290# / DEFINE_TEXT_SIZE             '每八度的間距 字形的 百分比
    amt.DROP_ADD_LINE_INTERVAL = 150# / DEFINE_TEXT_SIZE               '下點 多一條線點要下去多少  字形的 百分比
    
    amt.BAR_WITCH = 340 / DEFINE_TEXT_SIZE                '小節線的粗細

    '//bool  IsGiFill    =true;//在閉合的圖形元素上產生填充區域
    amt.IsGiFill = False '是否填充區域
    amt.IsDebugDialog = False      '是否叫出 DebugDialog

    amt.IsDrawCursory = True    '是否 繪自定的點

    amt.mHowData = 9    '有9行的資料

    amt.iTONE = 1        ' * 行
    amt.iFinge = 2    '這是指法行     _+)(*&
    amt.iScale = 3    '這是高低音行   .,:;
    amt.iNote = 4     '這為主行       1234567.|l
    amt.iTempo = 5    '這是拍子       -=368acefz
    amt.iTowFinge = 6    '這是指法行第二行  _+)(*&
    amt.iSlur = 7        ' 連音符行    (3456)
    
    amt.L_BUF_MD = 9  '這是看Buf_md要多少行
    amt.L_WHAT = 8    '這是指法看要放在那一行

    '二胡用
    amt.f一指 = 1
    amt.f二指 = 2
    amt.f三指 = 4
    amt.f四指 = 8
    amt.f空弦 = 16
    amt.f揉弦 = 32
    
    
    
    '2015/1/10 設定圖塊的資料，駐點的位置不一樣
    amt.bkMidHight = 690# / DEFINE_TEXT_SIZE      '物件中間下點的高度
    amt.bkMidUpHight = 1690# / DEFINE_TEXT_SIZE     '物件中間上點的高度
    amt.bkInster_Line_H = 97.8 / DEFINE_TEXT_SIZE    '物件原點跟拍線的高度
End Sub

Attribute VB_Name = "ttfdump"
Attribute VB_Base = "0{FE278BEB-B3AA-419D-874D-739C1CB52DDA}{DCD1CD26-04DD-4616-A008-F0AE08FDA795}"
Attribute VB_GlobalNameSpace = False
Attribute VB_Creatable = False
Attribute VB_PredeclaredId = True
Attribute VB_Exposed = False
Attribute VB_TemplateDerived = False
Attribute VB_Customizable = False
Option Explicit

Dim xylist As New PointList

Private Sub comDrawing_Click()
    Dim pt As Variant
    Dim xyString As String
    Dim sX As String
    Dim sY As String
    Dim i As Long
    
    Me.Hide
    ' Return a point using a prompt
    pt = ThisDrawing.Utility.GetPoint(, "\n選擇要插入的點 ：Enter insertion point: ")
    '畫出定位線;
    
    For i = 0 To xylist.size - 1
        sX = xylist.at(i).x + pt(0)
        sY = xylist.at(i).Y + pt(1)
        xyString = xyString & sX & "," & sY & " "
    Next
    
    ThisDrawing.SendCommand "line " & xyString
    
End Sub

Private Sub CommandButton1_Click()
    Dim ARR As Variant
    Dim SearchString, SearchChar, MyPos
    
    SearchChar = "abs"    ' 要尋找字串 "abs"。
    Dim i As Long
    Dim Y As Long
    Dim pt As New point
    Dim SStr As String
    ARR = Split(Me.TextBox1.text, vbCrLf)

    xylist.clean
    Me.TextBox2.text = ""
    For i = 0 To UBound(ARR) - 1
        If InStr(1, ARR(i), "ABS", 1) <> 0 Then
            SearchString = ARR(i)   ' 被搜尋的字串。
            ' 小寫 p 和大寫 P 在 [文字比對] 下是一樣的。
            MyPos = InStr(1, SearchString, SearchChar, 1)
            ARR(i) = Mid(ARR(i), MyPos, Len(ARR(i)))    '取得 ABS()的資料
            
                
            SStr = Replace(ARR(i), " ", "")       '空白移除
            
            Set pt = getABS_XY(SStr)
            Call xylist.addpt(pt)
        End If
        Me.TextBox2 = Me.TextBox2 & pt.x & "," & pt.Y & vbCrLf
        'Me.TextBox2 = Me.TextBox2.text & vbCrLf & ARR(i) '看資料
    Next
'
'    For i = 0 To UBound(ARR) - 1
'        Me.TextBox2 = Me.TextBox2.text & vbCrLf & ARR(i)
'    Next
End Sub

Private Function getABS_XY(dataXY As String) As point
'取得括弧內的 xy 資料
    Dim fpos As Integer
    Dim mpos As Integer
    Dim lpos As Integer
    Dim i As Integer
    Dim sX As String
    Dim sY As String
    Dim tPt As New point
    
    fpos = InStr(1, dataXY, "(")
    mpos = InStr(1, dataXY, ",")
    lpos = InStr(fpos, dataXY, ")")
    
    sX = Mid(dataXY, fpos + 1, mpos - fpos - 1)
    sY = Mid(dataXY, mpos + 1, lpos - mpos - 1)
    tPt.x = CDbl(sX)
    tPt.Y = CDbl(sY)
    Set getABS_XY = tPt
End Function

Attribute VB_Name = "減字譜用"
Option Explicit


Public Sub select_qin()
On Error Resume Next
Dim k As Integer
For k = 0 To 500
    Dim ent As Object

    'Dim tmp_ent() As Variant
    
   
    Dim SSetColl As AcadSelectionSets
    Set SSetColl = ThisDrawing.SelectionSets
    
    ' Create a SelectionSet named "TEST" in the current drawing
    Dim ssetObj As AcadSelectionSet
    
  
    If SSetColl.count > 0 Then
        SSetColl.item(0).Delete
    End If
    
    Set ssetObj = SSetColl.add("TEST")
    

    ssetObj.SelectOnScreen
    If ssetObj.count = 0 Then
    
       Exit Sub
    End If
    '找出圖面中的每一個選集
    ReDim tmp_ent(ssetObj.count - 1)
    Dim lll As AcadLine
    
    
    Dim minExt As Variant
    Dim maxExt As Variant
    Dim minPT(2) As Double
    Dim maxPT(2) As Double
    Dim midPT(2) As Double
    Dim toPT(2) As Double
    Dim aa1 As AcadText
    Dim i As Integer
    Dim pos_y As Double
    i = 0
    For Each ent In ssetObj
        '取得最大最小
        ent.GetBoundingBox minExt, maxExt
        If i = 0 Then
            minPT(0) = minExt(0): minPT(1) = minExt(1)
            maxPT(0) = maxExt(0): maxPT(1) = maxExt(1)
        Else
            If minPT(0) > minExt(0) Then
                minPT(0) = minExt(0)
            End If
            If minPT(1) > minExt(1) Then
                minPT(1) = minExt(1)
            End If
            
        End If
        i = i + 1
    Next
    
    '移動
    toPT(0) = 60000 * k: toPT(1) = 20000:
    For Each ent In ssetObj
        '取得最大最小
        
        ent.Move minPT, toPT
    Next
    
Next
End Sub
